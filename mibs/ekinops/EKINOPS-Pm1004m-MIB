-- *****************************************************************
-- EKINOPS-Pm1004m.TXT:  MIB
--
--MIB Part Number:3MI00015AHAE 
--MIB Version:02
--
-- Copyright (c) 2016 by Ekinops
-- All rights reserved.
-- 
-- *****************************************************************

EKINOPS-Pm1004m-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress                
        		FROM SNMPv2-SMI
 	TEXTUAL-CONVENTION,
	DisplayString
                FROM SNMPv2-TC;

modulePm1004m MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.net"
  DESCRIPTION
          "Creation"
	REVISION "200712140000Z"
	DESCRIPTION
	  "Helps on objects, Ports Labels"
	REVISION "200903190000Z"
	DESCRIPTION
	  "Perf and J0 insertion"
	REVISION "200904060000Z"
	DESCRIPTION
	  "Storm info suppress"
	REVISION "200904090000Z"
	DESCRIPTION
	  "Add DCC ans MAINTENANCE control"
	REVISION "200909300000Z"
	DESCRIPTION
	  "Add CondType parameters"
	REVISION "201002180000Z"
	DESCRIPTION
	  "Probcause,AlarmType - NMS"
	REVISION "201006140000Z"
	DESCRIPTION
	  "Add OTX-TLH features"
	REVISION "201011090000Z"
	DESCRIPTION
	  "Formulas in comments and Event on XFP init"
	REVISION "201207030000Z"
	DESCRIPTION
	  "Minor cosmetic updates"
	REVISION "201304020000Z"
	DESCRIPTION
	  "S1,K1,K2 suppress"
	REVISION "201403270000Z"
	DESCRIPTION
	  "Probcause,AlarmType - NMS completion"
	REVISION "201412220000Z"
	DESCRIPTION
	  "Labels cosmetic updates"
	REVISION "201605190000Z"
	DESCRIPTION
	  "New AlarmType – synthesisAlarm (12)"
	REVISION "201606020000Z"
	DESCRIPTION
	  "Capabilities objects of Table 5"
        ::= { ekinops 29 }



--- *****************************************************
---     LEAF LEVEL 2
--- *****************************************************


pm1004malarms OBJECT IDENTIFIER ::= { modulePm1004m 2 }	
pm1004mAlmOther OBJECT IDENTIFIER ::= { pm1004malarms 1 }
pm1004mAlmOtherNurg OBJECT IDENTIFIER ::= { pm1004mAlmOther 1 }
pm1004mAlmOtherUrg OBJECT IDENTIFIER ::= { pm1004mAlmOther 2 }
pm1004mAlmOtherCrit OBJECT IDENTIFIER ::= { pm1004mAlmOther 3 }

pm1004mAlmClient OBJECT IDENTIFIER ::= { pm1004malarms 2 }
pm1004mAlmClientNurg OBJECT IDENTIFIER ::= { pm1004mAlmClient 1 }
pm1004mAlmClientUrg OBJECT IDENTIFIER ::= { pm1004mAlmClient 2 }
pm1004mAlmClientCrit OBJECT IDENTIFIER ::= { pm1004mAlmClient 3 }
	
pm1004mAlmLine OBJECT IDENTIFIER ::= { pm1004malarms 3 }
pm1004mAlmLineNurg OBJECT IDENTIFIER ::= { pm1004mAlmLine 1 }
pm1004mAlmLineUrg OBJECT IDENTIFIER ::= { pm1004mAlmLine 2 }
pm1004mAlmLineCrit OBJECT IDENTIFIER ::= { pm1004mAlmLine 3 }





pm1004mmeasures OBJECT IDENTIFIER ::= { modulePm1004m 3 }	
pm1004mMesrOther OBJECT IDENTIFIER ::= { pm1004mmeasures 1 }	
pm1004mMesrClient OBJECT IDENTIFIER ::= { pm1004mmeasures 2 }	
pm1004mMesrLine OBJECT IDENTIFIER ::= { pm1004mmeasures 3 }	




pm1004mcounters OBJECT IDENTIFIER ::= { modulePm1004m 4 }
pm1004mCntOther OBJECT IDENTIFIER ::= { pm1004mcounters 1 }
pm1004mCntClient OBJECT IDENTIFIER ::= { pm1004mcounters 2 }
pm1004mCntLine OBJECT IDENTIFIER ::= { pm1004mcounters 3 }


pm1004mcontrolsWrite OBJECT IDENTIFIER ::= { modulePm1004m 6 }
pm1004mCtrlOther OBJECT IDENTIFIER ::= { pm1004mcontrolsWrite 1 }
pm1004mCtrlClient OBJECT IDENTIFIER ::= { pm1004mcontrolsWrite 2 }
pm1004mCtrlLine OBJECT IDENTIFIER ::= { pm1004mcontrolsWrite 3 }

pm1004mri OBJECT IDENTIFIER ::= { modulePm1004m 7 }
pm1004mriTable OBJECT IDENTIFIER ::= { pm1004mri 1 }

pm1004mdownload OBJECT IDENTIFIER ::= { modulePm1004m 8 }
pm1004mDwlOther OBJECT IDENTIFIER ::= { pm1004mdownload 1 }
pm1004mDwlClient OBJECT IDENTIFIER ::= { pm1004mdownload 2 }
pm1004mDwlLine OBJECT IDENTIFIER ::= { pm1004mdownload 3 }


pm1004mConfig OBJECT IDENTIFIER ::= { modulePm1004m 9 }

pm1004mtraps OBJECT IDENTIFIER ::= { modulePm1004m 10 }

pm1004mMonitoring OBJECT IDENTIFIER ::= { modulePm1004m 11}

pm1004mMonOther OBJECT IDENTIFIER ::= { pm1004mMonitoring 1 }
pm1004mMonSync OBJECT IDENTIFIER ::= { pm1004mMonOther 1 }
pm1004mMonTimeStamp OBJECT IDENTIFIER ::= { pm1004mMonOther 2 }

pm1004mMonClient OBJECT IDENTIFIER ::= { pm1004mMonitoring 2 }
pm1004mMonClientPerformance OBJECT IDENTIFIER ::= { pm1004mMonClient 1 }
pm1004mMonClientTraceIdentifier OBJECT IDENTIFIER ::= { pm1004mMonClient 2 }

pm1004mMonLine OBJECT IDENTIFIER ::= { pm1004mMonitoring 3 }
pm1004mMonLinePerformance OBJECT IDENTIFIER ::= { pm1004mMonLine 1 }
pm1004mMonLineTraceIdentifier OBJECT IDENTIFIER ::= { pm1004mMonLine 2 }

--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************


Pm1004mOtxMode ::= TEXTUAL-CONVENTION
    STATUS      current
    DESCRIPTION "Different modes on OTX-TLH on client and line ports"
    SYNTAX INTEGER {
		otx80mode(1),
		otx60mode(2),
		otxadjustmode(4),
           }

Pm1004mOtxGrid ::= TEXTUAL-CONVENTION
    STATUS      current
    DESCRIPTION "Different grids on OTX-TLH on client and line ports"
    SYNTAX INTEGER {
		otxgrid200(200),
		otxgrid100(100),
		otxgrid50(50),
           }

Pm1004mAdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10),
           }

Pm1004mOtxChannel ::= TEXTUAL-CONVENTION
    STATUS      current
    DESCRIPTION "Channel selection on OTX-TLH on client and line ports"
    SYNTAX INTEGER {

           }



--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm1004mRinvReloadInventory OBJECT-TYPE
  SYNTAX EkiOnOff
  MAX-ACCESS read-write
  STATUS current
  DESCRIPTION
        "Reload the inventory: This OID triggers an 
         inventory reload."
  ::= { pm1004mri 2 }

pm1004mRinvHwPlatform OBJECT-TYPE
  SYNTAX DisplayString
  MAX-ACCESS read-only
  STATUS current
  DESCRIPTION
        "HW platform description: This OID contains the 
         description of the Hardware platform."
  ::= { pm1004mri 3 }
  
pm1004mRinvModulePlatform OBJECT-TYPE
  SYNTAX DisplayString
  MAX-ACCESS read-only
  STATUS current
  DESCRIPTION
        "Module platform description: This OID contains the 
         description of the Module."
  ::= { pm1004mri 4 }
  
pm1004mRinvSwPlatform OBJECT-TYPE
  SYNTAX DisplayString
  MAX-ACCESS read-only
  STATUS current
  DESCRIPTION
        "SW platform description: This OID contains the 
         description of the Software platform."
  ::= { pm1004mri 5 }
  
pm1004mRinvGwPlatform OBJECT-TYPE
  SYNTAX DisplayString
  MAX-ACCESS read-only
  STATUS current
  DESCRIPTION
        "GW platform desciption: This OID contains the 
         description of the Gateware platform."
  ::= { pm1004mri 6 }


pm1004mRinvSfpTable OBJECT-TYPE
      SYNTAX  SEQUENCE OF Pm1004mRinvSfpEntry
      MAX-ACCESS  not-accessible
      STATUS  current
      DESCRIPTION
              "List of the SFPs on the selected module"
      ::= { pm1004mriTable 1 }

pm1004mRinvSfpEntry OBJECT-TYPE
        SYNTAX  Pm1004mRinvSfpEntry
        MAX-ACCESS  not-accessible
        STATUS  current
        DESCRIPTION
              "Row definition for the SFP table"
        INDEX   { pm1004mRinvSfpIndex }
        ::= { pm1004mRinvSfpTable 1 }
    


Pm1004mRinvSfpEntry::=
        SEQUENCE {
          pm1004mRinvSfpIndex 
              Integer32,
          pm1004mRinvsfp
              DisplayString
        }


    pm1004mRinvSfpIndex OBJECT-TYPE
        SYNTAX  Integer32(1..16)
        MAX-ACCESS  read-only
        STATUS  current
        DESCRIPTION
              "Index for SFP table"
        ::= { pm1004mRinvSfpEntry 1 }


    pm1004mRinvsfp OBJECT-TYPE
        SYNTAX  DisplayString
        MAX-ACCESS  read-only
        STATUS  current
        DESCRIPTION
              "Inventory for the SFP: This OID contains the inventory for the SFP"
        ::= { pm1004mRinvSfpEntry 2 }




pm1004mRinvLineTable OBJECT-TYPE
      SYNTAX  SEQUENCE OF Pm1004mRinvLineEntry
      MAX-ACCESS  not-accessible
      STATUS  current
      DESCRIPTION
              "List of the XFPs on the selected module"
      ::= { pm1004mriTable 2 }

pm1004mRinvLineEntry OBJECT-TYPE
        SYNTAX  Pm1004mRinvLineEntry
        MAX-ACCESS  not-accessible
        STATUS  current
        DESCRIPTION
              "Row definition for the XFP table"
        INDEX   { pm1004mRinvLineIndex }
        ::= { pm1004mRinvLineTable 1 }
    


Pm1004mRinvLineEntry::=
        SEQUENCE {
          pm1004mRinvLineIndex 
              Integer32,
          pm1004mRinvxfpLine
              DisplayString
        }


    pm1004mRinvLineIndex OBJECT-TYPE
        SYNTAX  Integer32(1..16)
        MAX-ACCESS  read-only
        STATUS  current
        DESCRIPTION
              "Index for XFP table"
        ::= { pm1004mRinvLineEntry 1 }


    pm1004mRinvxfpLine OBJECT-TYPE
        SYNTAX  DisplayString
        MAX-ACCESS  read-only
        STATUS  current
        DESCRIPTION
              "Inventory for the XFP: This OID contains the inventory for the XFP"
        ::= { pm1004mRinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm1004mAlmsynthAlm0 OBJECT IDENTIFIER ::= { pm1004mAlmOtherCrit 0 }




pm1004mAlmDefFuseB OBJECT-TYPE
	  SYNTAX EkiOnOff
	  MAX-ACCESS read-only
	  STATUS current
	  DESCRIPTION
        "
        Fuse B Fail :This OID indicates 
        that the fuse of the power input 
        B is in fail condition  <Help>
          Status of the Fuse B <Condtype> 
        DEF_FUSE_B <Probcause> powerProblem 
        (36) <Alarmtype> equipmentAlarm 
        (5) <Polarity> (2) 
        "
	  ::= { pm1004mAlmsynthAlm0 16 }



pm1004mAlmDefFuseA OBJECT-TYPE
	  SYNTAX EkiOnOff
	  MAX-ACCESS read-only
	  STATUS current
	  DESCRIPTION
        "
        Fuse A Fail :This OID indicates 
        that the fuse of the power input 
        A is in fail condition  <Help>
          Status of the Fuse A <Condtype> 
        DEF_FUSE_A <Probcause> powerProblem 
        (36) <Alarmtype> equipmentAlarm 
        (5) <Polarity> (2) 
        "
	  ::= { pm1004mAlmsynthAlm0 15 }



pm1004mAlmModGlobFail OBJECT-TYPE
	  SYNTAX EkiOnOff
	  MAX-ACCESS read-only
	  STATUS current
	  DESCRIPTION
        "
        Module Failure :This OID is set 
        on detection of a failure originating 
        from the PM <Condtype> MOD_GLOB_FAIL 
        <Probcause> equipmentMalfunction 
        (16) <Alarmtype> synthesisAlarm 
        (12)  <Polarity> (2) 
        "
	  ::= { pm1004mAlmsynthAlm0 9 }



--- *****************************************************
---     LEAF for the synthAlm2 article
--- *****************************************************
pm1004mAlmsynthAlm2 OBJECT IDENTIFIER ::= { pm1004mAlmOtherNurg 2 }




pm1004mAlmMaintenanceOn OBJECT-TYPE
	  SYNTAX EkiOnOff
	  MAX-ACCESS read-only
	  STATUS current
	  DESCRIPTION
        "
        Maintenance Mode :This OID indicates 
        that the PM is in maintenance mode. 
         <Help>  This alarm indicates that 
        the maintenance mode is enabled 
        on the PM <Condtype> MAINTENANCE_ON 
        <Probcause> other (1) <Alarmtype> 
        other (1) <Polarity> (2) 
        "
	  ::= { pm1004mAlmsynthAlm2 5 }



pm1004mAlmCorrelatOff OBJECT-TYPE
	  SYNTAX EkiOnOff
	  MAX-ACCESS read-only
	  STATUS current
	  DESCRIPTION
        "
        Not Used :This OID, when set,
         indicates that alarm correlation 
        is not being performed. <Condtype> 
        CORRELAT_OFF <Probcause> other
         (1) <Alarmtype> other (1) <Polarity> 
        (2) 
        "
	  ::= { pm1004mAlmsynthAlm2 4 }



pm1004mAlmConfTableLoad OBJECT-TYPE
	  SYNTAX EkiOnOff
	  MAX-ACCESS read-only
	  STATUS current
	  DESCRIPTION
        "
        PM Configuration Load :This OID 
         is at 1 during the loading of
         configuration tables in the modules 
        RAM. <Condtype> CONF_TABLE_LOAD 
        <Probcause> other (1) <Alarmtype> 
        other (1) <Polarity> (2) 
        "
	  ::= { pm1004mAlmsynthAlm2 3 }



pm1004mAlmInvUpload OBJECT-TYPE
	  SYNTAX EkiOnOff
	  MAX-ACCESS read-only
	  STATUS current
	  DESCRIPTION
        "
        Inventory Upload :This OID is
         at 1 during the uploading of PM 
        inventory information. <Condtype> 
        INV_UPLOAD <Probcause> other (1) 
        <Alarmtype> other (1) <Polarity> 
        (2) 
        "
	  ::= { pm1004mAlmsynthAlm2 2 }



pm1004mAlmConfTableSave OBJECT-TYPE
	  SYNTAX EkiOnOff
	  MAX-ACCESS read-only
	  STATUS current
	  DESCRIPTION
        "
        PM Configuration Save :This OID 
        is at 1 during the saving of a
         new configuration table in the 
        module Flash memory. <Condtype> 
        CONF_TABLE_SAVE <Probcause> other 
        (1) <Alarmtype> other (1) <Polarity> 
        (2) 
        "
	  ::= { pm1004mAlmsynthAlm2 1 }



--- *********************************************************
---     TABLE for the pm1004mAlmsynthAlmLine articles
--- *********************************************************

pm1004mAlmsynthAlmLineTable OBJECT-TYPE
	SYNTAX  SEQUENCE OF Pm1004mAlmsynthAlmLineEntry
	MAX-ACCESS not-accessible
	STATUS current
	DESCRIPTION
        "
        List of pm1004mAlmsynthAlmLine 
        Article
        "
	::= { pm1004mAlmLineCrit 7 }


pm1004mAlmsynthAlmLineEntry OBJECT-TYPE
	SYNTAX Pm1004mAlmsynthAlmLineEntry
	MAX-ACCESS not-accessible
	STATUS current
	DESCRIPTION
        "
        Row definition for the pm1004mAlmsynthAlmLine 
        table
        "
	INDEX   { pm1004mAlmsynthAlmLineIndex }
	::= { pm1004mAlmsynthAlmLineTable 1 }


Pm1004mAlmsynthAlmLineEntry ::=
	SEQUENCE {
	pm1004mAlmsynthAlmLineIndex
		INTEGER,
	pm1004mAlmLineActivePortn
		EkiOnOff,
	pm1004mAlmLineFailPortn
		EkiOnOff,
	pm1004mAlmLineDdmAlmPortn
		EkiOnOff,
	pm1004mAlmLineDdmWarningPortn
		EkiOnOff,
	pm1004mAlmUpRdiInsPortn
		EkiOnOff,
	pm1004mAlmLineLocalOosPortn
		EkiOnOff,
	pm1004mAlmXfpTxOffPortn
		EkiOnOff,
	pm1004mAlmLineHwFailPortn
		EkiOnOff,
	pm1004mAlmXfpInitNotComplPortn
		EkiOnOff,
	pm1004mAlmXfpAbsentPortn
		EkiOnOff
	}


pm1004mAlmsynthAlmLineIndex OBJECT-TYPE
	SYNTAX  INTEGER(0..128)
	MAX-ACCESS  read-only
	STATUS current
	DESCRIPTION
        "
        Index definition for the pm1004mAlmsynthAlmLine 
        table
        "
	::= { pm1004mAlmsynthAlmLineEntry 1 }


pm1004mAlmLineActivePortn OBJECT-TYPE
	SYNTAX  EkiOnOff
	MAX-ACCESS read-only
	STATUS current
	DESCRIPTION
        "
        Line Active :This bit indicates 
        the line #n is active on receive 
        side  <Help>  This status indicates 
        whether the line is active or standby. 
        <Condtype> LINE_ACTIVE <Probcause> 
        informationalStatus(1000) <Alarmtype> 
        other (1) <Polarity> (2) 
        "
	::= { pm1004mAlmsynthAlmLineEntry 17 }


pm1004mAlmLineFailPortn OBJECT-TYPE
	SYNTAX  EkiOnOff
	MAX-ACCESS read-only
	STATUS current
	DESCRIPTION
        "
        Line Port Failure :This OID indicates 
        a failure on the line port <Condtype> 
        LINE_FAIL <Probcause> equipmentMalfunction 
        (16) <Alarmtype> synthesisAlarm 
        (12)  <Polarity> (2) 
        "
	::= { pm1004mAlmsynthAlmLineEntry 13 }


pm1004mAlmLineDdmAlmPortn OBJECT-TYPE
	SYNTAX  EkiOnOff
	MAX-ACCESS read-only
	STATUS current
	DESCRIPTION
        "
        Alarm On Line Optical Module DDM 
        :This OID indicates an alarm is 
        present coming out of Line optical 
        interface DDM  <Help>  This alarm 
        indicates if a DDM Alarm has been 
        detected on the line transceiver 
        <Condtype> LINE_DDM_ALM <Probcause> 
        equipmentMalfunction (16) <Alarmtype> 
        synthesisAlarm (12)  <Polarity> 
        (2) 
        "
	::= { pm1004mAlmsynthAlmLineEntry 11 }


pm1004mAlmLineDdmWarningPortn OBJECT-TYPE
	SYNTAX  EkiOnOff
	MAX-ACCESS read-only
	STATUS current
	DESCRIPTION
        "
        Warning On Line Optical Module 
        DDM :This OID indicates a warning 
        is present coming out of Line optical 
        interface DDM  <Help>  This alarm 
        indicates if a DDM Warning has
         been detected on the line transceiver 
        <Condtype> LINE_DDM_WARNING <Probcause> 
        equipmentMalfunction (16) <Alarmtype> 
        synthesisAlarm (12)  <Polarity> 
        (2) 
        "
	::= { pm1004mAlmsynthAlmLineEntry 10 }


pm1004mAlmUpRdiInsPortn OBJECT-TYPE
	SYNTAX  EkiOnOff
	MAX-ACCESS read-only
	STATUS current
	DESCRIPTION
        "
        MS-RDI/L-RDI Inserted On Line
         :This OID indicates an upstream 
        MS-RDI/L-RDI has been inserted
         in the outgoing OC192/STM64 signal. 
          <Help>  This status indicates 
        if a MS-RDI/L-RDI is currently
         inserted on the line interface. 
        <Condtype> UP_RDI_INS <Probcause> 
        informationalStatus(1000) <Alarmtype> 
        other (1) <Polarity> (2) 
        "
	::= { pm1004mAlmsynthAlmLineEntry 9 }


pm1004mAlmLineLocalOosPortn OBJECT-TYPE
	SYNTAX  EkiOnOff
	MAX-ACCESS read-only
	STATUS current
	DESCRIPTION
        "
        Line Port In Service :This OID 
        indicates that the Line port is 
        In Service (1) of Out or Service 
        (2)  <Help>  This status indicates 
        if the line port is in service
         <Condtype> LINE_LOCAL_OOS <Probcause> 
        informationalStatus(1000) <Alarmtype> 
        other (1) <Polarity> (2) 
        "
	::= { pm1004mAlmsynthAlmLineEntry 7 }


pm1004mAlmXfpTxOffPortn OBJECT-TYPE
	SYNTAX  EkiOnOff
	MAX-ACCESS read-only
	STATUS current
	DESCRIPTION
        "
        Line Optical Module Laser Shutdown 
        :This OID indicates the line optical 
        output power is on  <Help>  This 
        status indicates if the line transceiver 
        laser is ON or OFF <Condtype> XFP_TX_OFF 
        <Probcause> other (1) <Alarmtype> 
        equipmentAlarm (5) <Polarity> (2) 
        "
	::= { pm1004mAlmsynthAlmLineEntry 6 }


pm1004mAlmLineHwFailPortn OBJECT-TYPE
	SYNTAX  EkiOnOff
	MAX-ACCESS read-only
	STATUS current
	DESCRIPTION
        "
        Line Port HW Failure :This OID 
        indicates a failure on line port, 
        most probably caused by a HW issue 
        <Condtype> LINE_HW_FAIL <Probcause> 
        equipmentMalfunction (16) <Alarmtype> 
        synthesisAlarm (12)  <Polarity> 
        (2) 
        "
	::= { pm1004mAlmsynthAlmLineEntry 5 }


pm1004mAlmXfpInitNotComplPortn OBJECT-TYPE
	SYNTAX  EkiOnOff
	MAX-ACCESS read-only
	STATUS current
	DESCRIPTION
        "
        Line Optical Module Ready :This 
        OID indicates that the optical
         interface (XFP or OTX) is not
         operational.  <Help>  This status 
        indicates if the line transceiver 
        has been correctly initialized
         <Condtype> XFP_INIT_NOT_COMPL
         <Probcause> equipmentMalfunction 
        (16) <Alarmtype> equipmentAlarm 
        (5) <Polarity> (2) <Event> ObjectCDINV
        "
	::= { pm1004mAlmsynthAlmLineEntry 3 }


pm1004mAlmXfpAbsentPortn OBJECT-TYPE
	SYNTAX  EkiOnOff
	MAX-ACCESS read-only
	STATUS current
	DESCRIPTION
        "
        Line Optical Module Absent :This 
        OID indicates that the line optical 
        interface (XFP or OTX) is not plugged 
        in.  <Help>  This alarm indicates 
        if the line transceiver is present. 
        <Condtype> XFP_ABSENT <Probcause> 
        inputOutputDeviceError (24) <Alarmtype> 
        equipmentAlarm (5) <Polarity> (2) 
        <Event> ObjectCDINV
        "
	::= { pm1004mAlmsynthAlmLineEntry 2 }


--- *********************************************************
---     TABLE for the pm1004mAlmsynthAlmPort articles
--- *********************************************************

pm1004mAlmsynthAlmPortTable OBJECT-TYPE
	SYNTAX  SEQUENCE OF Pm1004mAlmsynthAlmPortEntry
	MAX-ACCESS not-accessible
	STATUS current
	DESCRIPTION
        "
        List of pm1004mAlmsynthAlmPort 
        Article
        "
	::= { pm1004mAlmClientCrit 8 }


pm1004mAlmsynthAlmPortEntry OBJECT-TYPE
	SYNTAX Pm1004mAlmsynthAlmPortEntry
	MAX-ACCESS not-accessible
	STATUS current
	DESCRIPTION
        "
        Row definition for the pm1004mAlmsynthAlmPort 
        table
        "
	INDEX   { pm1004mAlmsynthAlmPortIndex }
	::= { pm1004mAlmsynthAlmPortTable 1 }


Pm1004mAlmsynthAlmPortEntry ::=
	SEQUENCE {
	pm1004mAlmsynthAlmPortIndex
		INTEGER,
	pm1004mAlmUpCsfPortn
		EkiOnOff,
	pm1004mAlmFailAccPortn
		EkiOnOff,
	pm1004mAlmSfpDdmAlmPortn
		EkiOnOff,
	pm1004mAlmSfpDdmWarningPortn
		EkiOnOff,
	pm1004mAlmDwCaisPortn
		EkiOnOff,
	pm1004mAlmClientRemoteOosPortn
		EkiOnOff,
	pm1004mAlmClientLocalOosPortn
		EkiOnOff,
	pm1004mAlmDwLsdPortn
		EkiOnOff,
	pm1004mAlmHwFailAccPortn
		EkiOnOff,
	pm1004mAlmDdmAbsentPortn
		EkiOnOff,
	pm1004mAlmSfpAbsentPortn
		EkiOnOff
	}


pm1004mAlmsynthAlmPortIndex OBJECT-TYPE
	SYNTAX  INTEGER(0..128)
	MAX-ACCESS  read-only
	STATUS current
	DESCRIPTION
        "
        Index definition for the pm1004mAlmsynthAlmPort 
        table
        "
	::= { pm1004mAlmsynthAlmPortEntry 1 }


pm1004mAlmUpCsfPortn OBJECT-TYPE
	SYNTAX  EkiOnOff
	MAX-ACCESS read-only
	STATUS current
	DESCRIPTION
        "
        Client Signal Fail Inserted :This 
        OID indicates a CSF has been inserted 
        in the upstream client port.  <Help> 
         This status indicates if a Client 
        Signal Fail is currently inserted 
        on the line signal for this client 
        port <Condtype> UP_CSF_1 <Probcause> 
        other (1) <Alarmtype> other (1) 
        <Polarity> (2) 
        "
	::= { pm1004mAlmsynthAlmPortEntry 17 }


pm1004mAlmFailAccPortn OBJECT-TYPE
	SYNTAX  EkiOnOff
	MAX-ACCESS read-only
	STATUS current
	DESCRIPTION
        "
        Client Access Fail :This OID indicates 
        a failure on the Client port <Condtype> 
        FAIL_ACC_1 <Probcause> equipmentMalfunction 
        (16) <Alarmtype> synthesisAlarm 
        (12)  <Polarity> (2) 
        "
	::= { pm1004mAlmsynthAlmPortEntry 13 }


pm1004mAlmSfpDdmAlmPortn OBJECT-TYPE
	SYNTAX  EkiOnOff
	MAX-ACCESS read-only
	STATUS current
	DESCRIPTION
        "
        Alarm On Client SFP DDM :This
         OID indicates an alarm is being 
        received from the Client SFP DDM 
         <Help>  This alarm indicates if 
        a DDM Alarm has been detected on 
        the client transceiver <Condtype> 
        SFP_DDM_ALM_1 <Probcause> equipmentMalfunction 
        (16) <Alarmtype> synthesisAlarm 
        (12)  <Polarity> (2) 
        "
	::= { pm1004mAlmsynthAlmPortEntry 11 }


pm1004mAlmSfpDdmWarningPortn OBJECT-TYPE
	SYNTAX  EkiOnOff
	MAX-ACCESS read-only
	STATUS current
	DESCRIPTION
        "
        Warning On Client SFP DDM :This 
        OID indicates a warning is being 
        received from the Client SFP DDM 
         <Help>  This alarm indicates if 
        a DDM Warning has been detected 
        on the client transceiver <Condtype> 
        SFP_DDM_WARNING_1 <Probcause> equipmentMalfunction 
        (16) <Alarmtype> synthesisAlarm 
        (12)  <Polarity> (2) 
        "
	::= { pm1004mAlmsynthAlmPortEntry 10 }


pm1004mAlmDwCaisPortn OBJECT-TYPE
	SYNTAX  EkiOnOff
	MAX-ACCESS read-only
	STATUS current
	DESCRIPTION
        "
        Client AIS Inserted :This OID
         indicates a CAIS has been inserted 
        on the output client port.  <Help> 
         This status indicates if a Client 
        Alarm Indication Signal is currently 
        inserted on the client interface 
        <Condtype> DW_CAIS_1 <Probcause> 
        informationalStatus(1000) <Alarmtype> 
        other (1) <Polarity> (2) 
        "
	::= { pm1004mAlmsynthAlmPortEntry 9 }


pm1004mAlmClientRemoteOosPortn OBJECT-TYPE
	SYNTAX  EkiOnOff
	MAX-ACCESS read-only
	STATUS current
	DESCRIPTION
        "
        Remote Client Port In Service
         :This OID indicates that the remote 
        Client port is In Service (1) or 
        Out of Service (2)  <Help>  This 
        status indicates if the remote
         client port is in service <Condtype> 
        CLIENT_REMOTE_OOS <Probcause> informationalStatus(1000) 
        <Alarmtype> other (1) <Polarity> 
        (2) 
        "
	::= { pm1004mAlmsynthAlmPortEntry 8 }


pm1004mAlmClientLocalOosPortn OBJECT-TYPE
	SYNTAX  EkiOnOff
	MAX-ACCESS read-only
	STATUS current
	DESCRIPTION
        "
        Local Client Port In Service :This 
        OID indicates that the local Client 
        port is In Service (1) or Out of 
        Service (2)  <Help>  This status 
        indicates if the local client port 
        is in service <Condtype> CLIENT_LOCAL_OOS 
        <Probcause> informationalStatus(1000) 
        <Alarmtype> other (1) <Polarity> 
        (2) 
        "
	::= { pm1004mAlmsynthAlmPortEntry 7 }


pm1004mAlmDwLsdPortn OBJECT-TYPE
	SYNTAX  EkiOnOff
	MAX-ACCESS read-only
	STATUS current
	DESCRIPTION
        "
        Client SFP Laser Shutdown :This 
        OID indicates the Client SFP transmitter 
        output is ON.   <Help>  This status 
        indicates if the client transceiver 
        laser is ON or OFF <Condtype> DW_LSD_1 
        <Probcause> other (1) <Alarmtype> 
        equipmentAlarm (5) <Polarity> (2) 
        "
	::= { pm1004mAlmsynthAlmPortEntry 6 }


pm1004mAlmHwFailAccPortn OBJECT-TYPE
	SYNTAX  EkiOnOff
	MAX-ACCESS read-only
	STATUS current
	DESCRIPTION
        "
        Client HW Fail :This OID indicates 
        a failure on client port, most
         probably caused by a HW issue. 
        <Condtype> HW_FAIL_ACC_1 <Probcause> 
        equipmentMalfunction (16) <Alarmtype> 
        synthesisAlarm (12)  <Polarity> 
        (2) 
        "
	::= { pm1004mAlmsynthAlmPortEntry 5 }


pm1004mAlmDdmAbsentPortn OBJECT-TYPE
	SYNTAX  EkiOnOff
	MAX-ACCESS read-only
	STATUS current
	DESCRIPTION
        "
        DDM Supported On Client SFP :This 
        OID indicates that the Client SFP 
        module supports the Digital Diagnostic 
        Monitoring function  <Help>  This 
        status indicates if the client
         transceiver includes the DDM feature 
        <Condtype> DDM_ABSENT_1 <Probcause> 
        informationalStatus(1000) <Alarmtype> 
        other (1) <Polarity> (2) 
        "
	::= { pm1004mAlmsynthAlmPortEntry 3 }


pm1004mAlmSfpAbsentPortn OBJECT-TYPE
	SYNTAX  EkiOnOff
	MAX-ACCESS read-only
	STATUS current
	DESCRIPTION
        "
        Client SFP Absent :This OID indicates 
        that the SFP module is not present 
        in the client port.  <Help>  This 
        alarm indicates if the client transceiver 
        is present. <Condtype> SFP_ABSENT_1 
        <Probcause> inputOutputDeviceError 
        (24) <Alarmtype> equipmentAlarm 
        (5) <Polarity> (2) <Event> ObjectCDINV
        "
	::= { pm1004mAlmsynthAlmPortEntry 2 }


--- *********************************************************
---     TABLE for the pm1004mAlmaccessioAlm articles
--- *********************************************************

pm1004mAlmaccessioAlmTable OBJECT-TYPE
	SYNTAX  SEQUENCE OF Pm1004mAlmaccessioAlmEntry
	MAX-ACCESS not-accessible
	STATUS current
	DESCRIPTION
        "
        List of pm1004mAlmaccessioAlm
         Article
        "
	::= { pm1004mAlmClientCrit 16 }


pm1004mAlmaccessioAlmEntry OBJECT-TYPE
	SYNTAX Pm1004mAlmaccessioAlmEntry
	MAX-ACCESS not-accessible
	STATUS current
	DESCRIPTION
        "
        Row definition for the pm1004mAlmaccessioAlm 
        table
        "
	INDEX   { pm1004mAlmaccessioAlmIndex }
	::= { pm1004mAlmaccessioAlmTable 1 }


Pm1004mAlmaccessioAlmEntry ::=
	SEQUENCE {
	pm1004mAlmaccessioAlmIndex
		INTEGER,
	pm1004mAlmUpLosPortn
		EkiOnOff,
	pm1004mAlmDwLasFailPortn
		EkiOnOff
	}


pm1004mAlmaccessioAlmIndex OBJECT-TYPE
	SYNTAX  INTEGER(0..128)
	MAX-ACCESS  read-only
	STATUS current
	DESCRIPTION
        "
        Index definition for the pm1004mAlmaccessioAlm 
        table
        "
	::= { pm1004mAlmaccessioAlmEntry 1 }


pm1004mAlmUpLosPortn OBJECT-TYPE
	SYNTAX  EkiOnOff
	MAX-ACCESS read-only
	STATUS current
	DESCRIPTION
        "
        Client Input Loss Of Signal :This 
        OID indicates that no signal is 
        present on the SFP of the client 
        port  <Help>  This alarm indicates 
        if an optical signal is detected 
        on the client transceiver input 
        <Condtype> UP_LOS_1 <Probcause> 
        receiveFailure (41) <Alarmtype> 
        physicalViolation (9) <Polarity> 
        (2) 
        "
	::= { pm1004mAlmaccessioAlmEntry 5 }


pm1004mAlmDwLasFailPortn OBJECT-TYPE
	SYNTAX  EkiOnOff
	MAX-ACCESS read-only
	STATUS current
	DESCRIPTION
        "
        Client SFP Tx Failed :This OID 
        indicates that the transmitter
         fails for the SFP plugged into 
        the client port (this alarm reports 
        the transmitter failure alarm generated 
        by the SFPs)  <Help>  This alarm 
        indicates if the laser of the client 
        transceiver is in <Condtype> DW_LAS_FAIL_1 
        <Probcause> transmitterFailure
         (56) <Alarmtype> equipmentAlarm 
        (5) <Polarity> (2) 
        "
	::= { pm1004mAlmaccessioAlmEntry 2 }


--- *********************************************************
---     TABLE for the pm1004mAlmsfpAlmDdm articles
--- *********************************************************

pm1004mAlmsfpAlmDdmTable OBJECT-TYPE
	SYNTAX  SEQUENCE OF Pm1004mAlmsfpAlmDdmEntry
	MAX-ACCESS not-accessible
	STATUS current
	DESCRIPTION
        "
        List of pm1004mAlmsfpAlmDdm Article
        "
	::= { pm1004mAlmClientUrg 32 }


pm1004mAlmsfpAlmDdmEntry OBJECT-TYPE
	SYNTAX Pm1004mAlmsfpAlmDdmEntry
	MAX-ACCESS not-accessible
	STATUS current
	DESCRIPTION
        "
        Row definition for the pm1004mAlmsfpAlmDdm 
        table
        "
	INDEX   { pm1004mAlmsfpAlmDdmIndex }
	::= { pm1004mAlmsfpAlmDdmTable 1 }


Pm1004mAlmsfpAlmDdmEntry ::=
	SEQUENCE {
	pm1004mAlmsfpAlmDdmIndex
		INTEGER,
	pm1004mAlmRxPwrHighAlaPortn
		EkiOnOff,
	pm1004mAlmRxPwrLowAlaPortn
		EkiOnOff,
	pm1004mAlmTempHighAlaPortn
		EkiOnOff,
	pm1004mAlmTempLowAlaPortn
		EkiOnOff,
	pm1004mAlmVccHighAlaPortn
		EkiOnOff,
	pm1004mAlmVccLowAlaPortn
		EkiOnOff,
	pm1004mAlmTxBiasHighAlaPortn
		EkiOnOff,
	pm1004mAlmTxBiasLowAlaPortn
		EkiOnOff,
	pm1004mAlmTxPwrHighAlaPortn
		EkiOnOff,
	pm1004mAlmTxPwrLowAlaPortn
		EkiOnOff
	}


pm1004mAlmsfpAlmDdmIndex OBJECT-TYPE
	SYNTAX  INTEGER(0..128)
	MAX-ACCESS  read-only
	STATUS current
	DESCRIPTION
        "
        Index definition for the pm1004mAlmsfpAlmDdm 
        table
        "
	::= { pm1004mAlmsfpAlmDdmEntry 1 }


pm1004mAlmRxPwrHighAlaPortn OBJECT-TYPE
	SYNTAX  EkiOnOff
	MAX-ACCESS read-only
	STATUS current
	DESCRIPTION
        "
        Client SFP Rx Power High :Alarm 
        indicating that the SFP input power 
        of port is higher than the threshold 
        value written in the SFP EEPROM 
        <Condtype> RX_PWR_HIGH_ALA_1 <Probcause> 
        receiveFailure (41) <Alarmtype> 
        equipmentAlarm (5) <Polarity> (2) 
        "
	::= { pm1004mAlmsfpAlmDdmEntry 17 }


pm1004mAlmRxPwrLowAlaPortn OBJECT-TYPE
	SYNTAX  EkiOnOff
	MAX-ACCESS read-only
	STATUS current
	DESCRIPTION
        "
        Client SFP Rx Power Low :Alarm 
        indicating that the SFP input power 
        of port is lower than the threshold 
        value written in the SFP EEPROM 
        <Condtype> RX_PWR_LOW_ALA_1 <Probcause> 
        receiveFailure (41) <Alarmtype> 
        equipmentAlarm (5) <Polarity> (2) 
        "
	::= { pm1004mAlmsfpAlmDdmEntry 16 }


pm1004mAlmTempHighAlaPortn OBJECT-TYPE
	SYNTAX  EkiOnOff
	MAX-ACCESS read-only
	STATUS current
	DESCRIPTION
        "
        Client SFP Temp High :Alarm indicating 
        that the SFP temperature of port 
        is higher than the threshold value 
        written in the SFP EEPROM <Condtype> 
        TEMP_HIGH_ALA_1 <Probcause> temperatureUnacceptable 
        (51) <Alarmtype> equipmentAlarm 
        (5) <Polarity> (2) 
        "
	::= { pm1004mAlmsfpAlmDdmEntry 9 }


pm1004mAlmTempLowAlaPortn OBJECT-TYPE
	SYNTAX  EkiOnOff
	MAX-ACCESS read-only
	STATUS current
	DESCRIPTION
        "
        Client SFP Temp Low :Alarm indicating 
        that the SFP temperature of port 
        is lower than the threshold value 
        written in the SFP EEPROM <Condtype> 
        TEMP_LOW_ALA_1 <Probcause> temperatureUnacceptable 
        (51) <Alarmtype> equipmentAlarm 
        (5) <Polarity> (2) 
        "
	::= { pm1004mAlmsfpAlmDdmEntry 8 }


pm1004mAlmVccHighAlaPortn OBJECT-TYPE
	SYNTAX  EkiOnOff
	MAX-ACCESS read-only
	STATUS current
	DESCRIPTION
        "
        Client SFP Power Supply High :Alarm 
        indicating that the SFP power supply 
        of port is higher than the threshold 
        value written in the SFP EEPROM 
         <Condtype> VCC_HIGH_ALA_1 <Probcause> 
        powerProblem (36) <Alarmtype> equipmentAlarm 
        (5) <Polarity> (2) 
        "
	::= { pm1004mAlmsfpAlmDdmEntry 7 }


pm1004mAlmVccLowAlaPortn OBJECT-TYPE
	SYNTAX  EkiOnOff
	MAX-ACCESS read-only
	STATUS current
	DESCRIPTION
        "
        Client SFP Power Supply Low :Alarm 
        indicating that the SFP power supply 
        of port is lower than the threshold 
        value written in the SFP EEPROM 
         <Condtype> VCC_LOW_ALA_1 <Probcause> 
        powerProblem (36) <Alarmtype> equipmentAlarm 
        (5) <Polarity> (2) 
        "
	::= { pm1004mAlmsfpAlmDdmEntry 6 }


pm1004mAlmTxBiasHighAlaPortn OBJECT-TYPE
	SYNTAX  EkiOnOff
	MAX-ACCESS read-only
	STATUS current
	DESCRIPTION
        "
        Client SFP Bias High :Alarm indicating 
        that the SFP laser bias current 
        of port is higher than the threshold 
        value written in the SFP EEPROM 
        <Condtype> TX_BIAS_HIGH_ALA_1 <Probcause> 
        transmitterFailure (56) <Alarmtype> 
        equipmentAlarm (5) <Polarity> (2) 
        "
	::= { pm1004mAlmsfpAlmDdmEntry 5 }


pm1004mAlmTxBiasLowAlaPortn OBJECT-TYPE
	SYNTAX  EkiOnOff
	MAX-ACCESS read-only
	STATUS current
	DESCRIPTION
        "
        Client SFP Bias Low :Alarm indicating 
        that the SFP laser bias current 
        of port is lower than the threshold 
        value written in the SFP EEPROM 
        <Condtype> TX_BIAS_LOW_ALA_1 <Probcause> 
        transmitterFailure (56) <Alarmtype> 
        equipmentAlarm (5) <Polarity> (2) 
        "
	::= { pm1004mAlmsfpAlmDdmEntry 4 }


pm1004mAlmTxPwrHighAlaPortn OBJECT-TYPE
	SYNTAX  EkiOnOff
	MAX-ACCESS read-only
	STATUS current
	DESCRIPTION
        "
        Client SFP Tx Power High :Alarm 
        indicating that the SFP output
         power of port is higher than the 
        threshold value written in the
         SFP EEPROM <Condtype> TX_PWR_HIGH_ALA_1 
        <Probcause> transmitterFailure
         (56) <Alarmtype> equipmentAlarm 
        (5) <Polarity> (2) 
        "
	::= { pm1004mAlmsfpAlmDdmEntry 3 }


pm1004mAlmTxPwrLowAlaPortn OBJECT-TYPE
	SYNTAX  EkiOnOff
	MAX-ACCESS read-only
	STATUS current
	DESCRIPTION
        "
        Client SFP Tx Power Low :Alarm 
        indicating that the SFP output
         power of port is lower than the 
        threshold value written in the
         SFP EEPROM <Condtype> TX_PWR_LOW_ALA_1 
        <Probcause> transmitterFailure
         (56) <Alarmtype> equipmentAlarm 
        (5) <Polarity> (2) 
        "
	::= { pm1004mAlmsfpAlmDdmEntry 2 }


--- *********************************************************
---     TABLE for the pm1004mAlmsfpWarnDdm articles
--- *********************************************************

pm1004mAlmsfpWarnDdmTable OBJECT-TYPE
	SYNTAX  SEQUENCE OF Pm1004mAlmsfpWarnDdmEntry
	MAX-ACCESS not-accessible
	STATUS current
	DESCRIPTION
        "
        List of pm1004mAlmsfpWarnDdm Article
        "
	::= { pm1004mAlmClientNurg 48 }


pm1004mAlmsfpWarnDdmEntry OBJECT-TYPE
	SYNTAX Pm1004mAlmsfpWarnDdmEntry
	MAX-ACCESS not-accessible
	STATUS current
	DESCRIPTION
        "
        Row definition for the pm1004mAlmsfpWarnDdm 
        table
        "
	INDEX   { pm1004mAlmsfpWarnDdmIndex }
	::= { pm1004mAlmsfpWarnDdmTable 1 }


Pm1004mAlmsfpWarnDdmEntry ::=
	SEQUENCE {
	pm1004mAlmsfpWarnDdmIndex
		INTEGER,
	pm1004mAlmRxPwrHighWngPortn
		EkiOnOff,
	pm1004mAlmRxPwrLowWngPortn
		EkiOnOff,
	pm1004mAlmTempHighWngPortn
		EkiOnOff,
	pm1004mAlmTempLowWngPortn
		EkiOnOff,
	pm1004mAlmVccHighWngPortn
		EkiOnOff,
	pm1004mAlmVccLowWngPortn
		EkiOnOff,
	pm1004mAlmTxBiasHighWngPortn
		EkiOnOff,
	pm1004mAlmTxBiasLowWngPortn
		EkiOnOff,
	pm1004mAlmTxPwrHighWngPortn
		EkiOnOff,
	pm1004mAlmTxPwLowWngPortn
		EkiOnOff
	}


pm1004mAlmsfpWarnDdmIndex OBJECT-TYPE
	SYNTAX  INTEGER(0..128)
	MAX-ACCESS  read-only
	STATUS current
	DESCRIPTION
        "
        Index definition for the pm1004mAlmsfpWarnDdm 
        table
        "
	::= { pm1004mAlmsfpWarnDdmEntry 1 }


pm1004mAlmRxPwrHighWngPortn OBJECT-TYPE
	SYNTAX  EkiOnOff
	MAX-ACCESS read-only
	STATUS current
	DESCRIPTION
        "
        Client SFP Rx Power High Warning 
        :Warning indicating that the SFP 
        input power of port is higher than 
        the threshold value written in
         the SFP EEPROM <Condtype> RX_PWR_HIGH_WNG_1 
        <Probcause> receiveFailure (41) 
        <Alarmtype> equipmentAlarm (5)
         <Polarity> (2) 
        "
	::= { pm1004mAlmsfpWarnDdmEntry 17 }


pm1004mAlmRxPwrLowWngPortn OBJECT-TYPE
	SYNTAX  EkiOnOff
	MAX-ACCESS read-only
	STATUS current
	DESCRIPTION
        "
        Client SFP Rx Power Low Warning 
        :Warning indicating that the SFP 
        input power of port is lower than 
        the threshold value written in
         the SFP EEPROM <Condtype> RX_PWR_LOW_WNG_1 
        <Probcause> receiveFailure (41) 
        <Alarmtype> equipmentAlarm (5)
         <Polarity> (2) 
        "
	::= { pm1004mAlmsfpWarnDdmEntry 16 }


pm1004mAlmTempHighWngPortn OBJECT-TYPE
	SYNTAX  EkiOnOff
	MAX-ACCESS read-only
	STATUS current
	DESCRIPTION
        "
        Client SFP Temp High Warning :Warning 
        indicating that the SFP temperature 
        of port is higher than the threshold 
        value written in the SFP EEPROM 
        <Condtype> TEMP_HIGH_WNG_1 <Probcause> 
        temperatureUnacceptable (51) <Alarmtype> 
        equipmentAlarm (5) <Polarity> (2) 
        "
	::= { pm1004mAlmsfpWarnDdmEntry 9 }


pm1004mAlmTempLowWngPortn OBJECT-TYPE
	SYNTAX  EkiOnOff
	MAX-ACCESS read-only
	STATUS current
	DESCRIPTION
        "
        Client SFP Temp Low Warning :Warning 
        indicating that the SFP temperature 
        of port is lower than the threshold 
        value written in the SFP EEPROM 
        <Condtype> TEMP_LOW_WNG_1 <Probcause> 
        temperatureUnacceptable (51) <Alarmtype> 
        equipmentAlarm (5) <Polarity> (2) 
        "
	::= { pm1004mAlmsfpWarnDdmEntry 8 }


pm1004mAlmVccHighWngPortn OBJECT-TYPE
	SYNTAX  EkiOnOff
	MAX-ACCESS read-only
	STATUS current
	DESCRIPTION
        "
        Client SFP Power Supply High Warning 
        :Warning indicating that the SFP 
        power supply of port is higher
         than the threshold value written 
        in the SFP EEPROM  <Condtype> VCC_HIGH_WNG_1 
        <Probcause> powerProblem (36) <Alarmtype> 
        equipmentAlarm (5) <Polarity> (2) 
        "
	::= { pm1004mAlmsfpWarnDdmEntry 7 }


pm1004mAlmVccLowWngPortn OBJECT-TYPE
	SYNTAX  EkiOnOff
	MAX-ACCESS read-only
	STATUS current
	DESCRIPTION
        "
        Client SFP Power Supply Low Warning 
        :Warning indicating that the SFP 
        power supply of port is lower than 
        the threshold value written in
         the SFP EEPROM  <Condtype> VCC_LOW_WNG_1 
        <Probcause> powerProblem (36) <Alarmtype> 
        equipmentAlarm (5) <Polarity> (2) 
        "
	::= { pm1004mAlmsfpWarnDdmEntry 6 }


pm1004mAlmTxBiasHighWngPortn OBJECT-TYPE
	SYNTAX  EkiOnOff
	MAX-ACCESS read-only
	STATUS current
	DESCRIPTION
        "
        Client SFP Bias High Warning :Warning 
        indicating that the SFP laser bias 
        current of port is higher than
         the threshold value written in 
        the SFP EEPROM <Condtype> TX_BIAS_HIGH_WNG_1 
        <Probcause> transmitterFailure
         (56) <Alarmtype> equipmentAlarm 
        (5) <Polarity> (2) 
        "
	::= { pm1004mAlmsfpWarnDdmEntry 5 }


pm1004mAlmTxBiasLowWngPortn OBJECT-TYPE
	SYNTAX  EkiOnOff
	MAX-ACCESS read-only
	STATUS current
	DESCRIPTION
        "
        Client SFP Bias Low Warning :Warning 
        indicating that the SFP laser bias 
        current of port is lower than the 
        threshold value written in the
         SFP EEPROM <Condtype> TX_BIAS_LOW_WNG_1 
        <Probcause> transmitterFailure
         (56) <Alarmtype> equipmentAlarm 
        (5) <Polarity> (2) 
        "
	::= { pm1004mAlmsfpWarnDdmEntry 4 }


pm1004mAlmTxPwrHighWngPortn OBJECT-TYPE
	SYNTAX  EkiOnOff
	MAX-ACCESS read-only
	STATUS current
	DESCRIPTION
        "
        Client SFP Tx Power High Warning 
        :Warning indicating that the SFP 
        output power of port is higher
         than the threshold value written 
        in the SFP EEPROM <Condtype> TX_PWR_HIGH_WNG_1 
        <Probcause> transmitterFailure
         (56) <Alarmtype> equipmentAlarm 
        (5) <Polarity> (2) 
        "
	::= { pm1004mAlmsfpWarnDdmEntry 3 }


pm1004mAlmTxPwLowWngPortn OBJECT-TYPE
	SYNTAX  EkiOnOff
	MAX-ACCESS read-only
	STATUS current
	DESCRIPTION
        "
        Client SFP Tx Power Low Warning 
        :Warning indicating that the SFP 
        output power of port is lower than 
        the threshold value written in
         the SFP EEPROM <Condtype> TX_PW_LOW_WNG_1 
        <Probcause> transmitterFailure
         (56) <Alarmtype> equipmentAlarm 
        (5) <Polarity> (2) 
        "
	::= { pm1004mAlmsfpWarnDdmEntry 2 }


--- *********************************************************
---     TABLE for the pm1004mAlmmapperDeAlm articles
--- *********************************************************

pm1004mAlmmapperDeAlmTable OBJECT-TYPE
	SYNTAX  SEQUENCE OF Pm1004mAlmmapperDeAlmEntry
	MAX-ACCESS not-accessible
	STATUS current
	DESCRIPTION
        "
        List of pm1004mAlmmapperDeAlm
         Article
        "
	::= { pm1004mAlmClientCrit 72 }


pm1004mAlmmapperDeAlmEntry OBJECT-TYPE
	SYNTAX Pm1004mAlmmapperDeAlmEntry
	MAX-ACCESS not-accessible
	STATUS current
	DESCRIPTION
        "
        Row definition for the pm1004mAlmmapperDeAlm 
        table
        "
	INDEX   { pm1004mAlmmapperDeAlmIndex }
	::= { pm1004mAlmmapperDeAlmTable 1 }


Pm1004mAlmmapperDeAlmEntry ::=
	SEQUENCE {
	pm1004mAlmmapperDeAlmIndex
		INTEGER,
	pm1004mAlmDwBufferOvlPortn
		EkiOnOff,
	pm1004mAlmDwCsfDetPortn
		EkiOnOff,
	pm1004mAlmUpBufferOvlPortn
		EkiOnOff,
	pm1004mAlmUpAccOosPortn
		EkiOnOff
	}


pm1004mAlmmapperDeAlmIndex OBJECT-TYPE
	SYNTAX  INTEGER(0..128)
	MAX-ACCESS  read-only
	STATUS current
	DESCRIPTION
        "
        Index definition for the pm1004mAlmmapperDeAlm 
        table
        "
	::= { pm1004mAlmmapperDeAlmEntry 1 }


pm1004mAlmDwBufferOvlPortn OBJECT-TYPE
	SYNTAX  EkiOnOff
	MAX-ACCESS read-only
	STATUS current
	DESCRIPTION
        "
        Client Downstream Buffer Overload 
        :This OID indicates that the de-mapper 
        buffer for client port is in overload. 
         <Help>  This alarm indicates if 
        there is a downstream FIFO overload 
        for this client port <Condtype> 
        DW_BUFFER_OVL_1 <Probcause> equipmentMalfunction 
        (16) <Alarmtype> equipmentAlarm 
        (5) <Polarity> (2) 
        "
	::= { pm1004mAlmmapperDeAlmEntry 15 }


pm1004mAlmDwCsfDetPortn OBJECT-TYPE
	SYNTAX  EkiOnOff
	MAX-ACCESS read-only
	STATUS current
	DESCRIPTION
        "
        Client Signal Fail Detected :This 
        OID indicates that a CSF has been 
        detected on client port in the
         downstream direction   <Help>
          This alarm indicates if a Client 
        Signal Fail has been detected in 
        the incoming line frame for this 
        client port <Condtype> DW_CSF_DET_1 
        <Probcause> receiveFailure (41) 
        <Alarmtype> equipmentAlarm (5)
         <Polarity> (2) 
        "
	::= { pm1004mAlmmapperDeAlmEntry 12 }


pm1004mAlmUpBufferOvlPortn OBJECT-TYPE
	SYNTAX  EkiOnOff
	MAX-ACCESS read-only
	STATUS current
	DESCRIPTION
        "
        Client Upstream Buffer Overload 
        :This OID indicates that the rate 
        adaptation buffer for client port 
        is in overload.  <Help>  This alarm 
        indicates if there is a upstream 
        FIFO overload for this client port 
        <Condtype> UP_BUFFER_OVL_1 <Probcause> 
        receiveFailure (41) <Alarmtype> 
        integrityViolation (7) <Polarity> 
        (2) 
        "
	::= { pm1004mAlmmapperDeAlmEntry 11 }


pm1004mAlmUpAccOosPortn OBJECT-TYPE
	SYNTAX  EkiOnOff
	MAX-ACCESS read-only
	STATUS current
	DESCRIPTION
        "
        Client Loss Of Frame :This OID 
        indicates the upstream client input 
        port is in Loss of Frame condition 
         <Help>  This alarm indicates if 
        there is a Loss of Frame is detected 
        on the client input signal <Condtype> 
        UP_ACC_OOS_1 <Probcause> receiveFailure 
        (41) <Alarmtype> integrityViolation 
        (7) <Polarity> (2) 
        "
	::= { pm1004mAlmmapperDeAlmEntry 2 }


--- *********************************************************
---     TABLE for the pm1004mAlmk1K2Client articles
--- *********************************************************

pm1004mAlmk1K2ClientTable OBJECT-TYPE
	SYNTAX  SEQUENCE OF Pm1004mAlmk1K2ClientEntry
	MAX-ACCESS not-accessible
	STATUS current
	DESCRIPTION
        "
        List of pm1004mAlmk1K2Client Article
        "
	::= { pm1004mAlmClientNurg 96 }


pm1004mAlmk1K2ClientEntry OBJECT-TYPE
	SYNTAX Pm1004mAlmk1K2ClientEntry
	MAX-ACCESS not-accessible
	STATUS current
	DESCRIPTION
        "
        Row definition for the pm1004mAlmk1K2Client 
        table
        "
	INDEX   { pm1004mAlmk1K2ClientIndex }
	::= { pm1004mAlmk1K2ClientTable 1 }


Pm1004mAlmk1K2ClientEntry ::=
	SEQUENCE {
	pm1004mAlmk1K2ClientIndex
		INTEGER,
	pm1004mAlmk1K2ClientPortn
		INTEGER 
	}


pm1004mAlmk1K2ClientIndex OBJECT-TYPE
	SYNTAX  INTEGER(0..128)
	MAX-ACCESS  read-only
	STATUS current
	DESCRIPTION
        "
        Index definition for the pm1004mAlmk1K2Client 
        table
        "
	::= { pm1004mAlmk1K2ClientEntry 1 }


pm1004mAlmk1K2ClientPortn OBJECT-TYPE
	SYNTAX  INTEGER (0..65535)
	MAX-ACCESS read-only
	STATUS current
	DESCRIPTION
        "
        Client K1-K2 Extracted Value :This 
        OID gives the value of K1 (LSB) 
        and K2 (MSB) extracted from the 
        overhead of the received OC-48c/STM-16c 
        signal <Condtype> CLIENT_1_K1_8 
        <Probcause> other (1) <Alarmtype> 
        other (1) <Polarity> (2)
        "
	::= { pm1004mAlmk1K2ClientEntry 2 }


--- *********************************************************
---     TABLE for the pm1004mAlmaccessioSdhAlarm articles
--- *********************************************************

pm1004mAlmaccessioSdhAlarmTable OBJECT-TYPE
	SYNTAX  SEQUENCE OF Pm1004mAlmaccessioSdhAlarmEntry
	MAX-ACCESS not-accessible
	STATUS current
	DESCRIPTION
        "
        List of pm1004mAlmaccessioSdhAlarm 
        Article
        "
	::= { pm1004mAlmClientCrit 104 }


pm1004mAlmaccessioSdhAlarmEntry OBJECT-TYPE
	SYNTAX Pm1004mAlmaccessioSdhAlarmEntry
	MAX-ACCESS not-accessible
	STATUS current
	DESCRIPTION
        "
        Row definition for the pm1004mAlmaccessioSdhAlarm 
        table
        "
	INDEX   { pm1004mAlmaccessioSdhAlarmIndex }
	::= { pm1004mAlmaccessioSdhAlarmTable 1 }


Pm1004mAlmaccessioSdhAlarmEntry ::=
	SEQUENCE {
	pm1004mAlmaccessioSdhAlarmIndex
		INTEGER,
	pm1004mAlmClientOofPortn
		EkiOnOff,
	pm1004mAlmClientRdiDetPortn
		EkiOnOff,
	pm1004mAlmClientAisDetPortn
		EkiOnOff,
	pm1004mAlmTxLossOfLockPortn
		EkiOnOff,
	pm1004mAlmRxLossOfLockPortn
		EkiOnOff,
	pm1004mAlmFifoErrPortn
		EkiOnOff
	}


pm1004mAlmaccessioSdhAlarmIndex OBJECT-TYPE
	SYNTAX  INTEGER(0..128)
	MAX-ACCESS  read-only
	STATUS current
	DESCRIPTION
        "
        Index definition for the pm1004mAlmaccessioSdhAlarm 
        table
        "
	::= { pm1004mAlmaccessioSdhAlarmEntry 1 }


pm1004mAlmClientOofPortn OBJECT-TYPE
	SYNTAX  EkiOnOff
	MAX-ACCESS read-only
	STATUS current
	DESCRIPTION
        "
        Client Out Of Frame :This OID
         indicates that an Out Of Frame 
        condition has been detected on
         the OC-48/STM-16 client input
         stream   <Help>  This alarm indicates 
        if there is a Out of Frame is detected 
        on the client input signal <Condtype> 
        CLIENT_OOF_1 <Probcause> receiveFailure 
        (41) <Alarmtype> integrityViolation 
        (7) <Polarity> (2) 
        "
	::= { pm1004mAlmaccessioSdhAlarmEntry 8 }


pm1004mAlmClientRdiDetPortn OBJECT-TYPE
	SYNTAX  EkiOnOff
	MAX-ACCESS read-only
	STATUS current
	DESCRIPTION
        "
        Client MS-RDI :This OID indicates 
        that a MS-RDI has been detected 
        on the client input stream  <Help> 
         This alarm indicates if there
         is a MS-RDI/L-RDI is detected
         on the client input signal <Condtype> 
        CLIENT_RDI_DET_1 <Probcause> remoteNodeTransmissionError 
        (43) <Alarmtype> other (1) <Polarity> 
        (2) 
        "
	::= { pm1004mAlmaccessioSdhAlarmEntry 7 }


pm1004mAlmClientAisDetPortn OBJECT-TYPE
	SYNTAX  EkiOnOff
	MAX-ACCESS read-only
	STATUS current
	DESCRIPTION
        "
        Client MS-AIS :This OID indicates 
        that a MS-AIS has been detected 
        on the client input stream  <Help> 
         This alarm indicates if there
         is a MS-AIS/L-AIS is detected
         on the client input signal <Condtype> 
        CLIENT_AIS_DET_1 <Probcause> receiveFailure 
        (41) <Alarmtype> operationalViolation 
        (8) <Polarity> (2) 
        "
	::= { pm1004mAlmaccessioSdhAlarmEntry 6 }


pm1004mAlmTxLossOfLockPortn OBJECT-TYPE
	SYNTAX  EkiOnOff
	MAX-ACCESS read-only
	STATUS current
	DESCRIPTION
        "
        Client Tx Clock Lock Error :This 
        OID indicates that the transmit 
        clock of the client transceiver 
        is not locke <Condtype> TX_LOSS_OF_LOCK_1 
        <Probcause> transmitterFailure
         (56) <Alarmtype> equipmentAlarm 
        (5) <Polarity> (2) 
        "
	::= { pm1004mAlmaccessioSdhAlarmEntry 5 }


pm1004mAlmRxLossOfLockPortn OBJECT-TYPE
	SYNTAX  EkiOnOff
	MAX-ACCESS read-only
	STATUS current
	DESCRIPTION
        "
        Client Rx Clock Lock Error :This 
        OID indicates the recovered receive 
        clock of the client transceiver 
        is not locked <Condtype> RX_LOSS_OF_LOCK_1 
        <Probcause> receiveFailure (41) 
        <Alarmtype> equipmentAlarm (5)
         <Polarity> (2) 
        "
	::= { pm1004mAlmaccessioSdhAlarmEntry 4 }


pm1004mAlmFifoErrPortn OBJECT-TYPE
	SYNTAX  EkiOnOff
	MAX-ACCESS read-only
	STATUS current
	DESCRIPTION
        "
        Client Transceiver Fifo Error
         :This OID indicates that an error 
        has been detected in the FIFO of 
        the client transceiver <Condtype> 
        FIFO_ERR_1 <Probcause> transmitterFailure 
        (56) <Alarmtype> equipmentAlarm 
        (5) <Polarity> (2) 
        "
	::= { pm1004mAlmaccessioSdhAlarmEntry 3 }


--- *********************************************************
---     TABLE for the pm1004mAlmj0Alarm articles
--- *********************************************************

pm1004mAlmj0AlarmTable OBJECT-TYPE
	SYNTAX  SEQUENCE OF Pm1004mAlmj0AlarmEntry
	MAX-ACCESS not-accessible
	STATUS current
	DESCRIPTION
        "
        List of pm1004mAlmj0Alarm Article
        "
	::= { pm1004mMonClientTraceIdentifier 2112 }


pm1004mAlmj0AlarmEntry OBJECT-TYPE
	SYNTAX Pm1004mAlmj0AlarmEntry
	MAX-ACCESS not-accessible
	STATUS current
	DESCRIPTION
        "
        Row definition for the pm1004mAlmj0Alarm 
        table
        "
	INDEX   { pm1004mAlmj0AlarmIndex }
	::= { pm1004mAlmj0AlarmTable 1 }


Pm1004mAlmj0AlarmEntry ::=
	SEQUENCE {
	pm1004mAlmj0AlarmIndex
		INTEGER,
	pm1004mAlmCrc7ErrorPortn
		EkiOnOff,
	pm1004mAlmJ0TiiAlarmPortn
		EkiOnOff,
	pm1004mAlmJ0TimAlarmPortn
		EkiOnOff
	}


pm1004mAlmj0AlarmIndex OBJECT-TYPE
	SYNTAX  INTEGER(0..128)
	MAX-ACCESS  read-only
	STATUS current
	DESCRIPTION
        "
        Index definition for the pm1004mAlmj0Alarm 
        table
        "
	::= { pm1004mAlmj0AlarmEntry 1 }


pm1004mAlmCrc7ErrorPortn OBJECT-TYPE
	SYNTAX  EkiOnOff
	MAX-ACCESS read-only
	STATUS current
	DESCRIPTION
        "
        CRC Error On Trace Identifier
         :This OID indicates that a CRC 
        error has been detected in the
         stable Trace Identifier on the 
        client input stream <Condtype>
         CRC7_ERROR_1 <Probcause> other 
        (1) <Alarmtype> other (1) <Polarity> 
        (2) 
        "
	::= { pm1004mAlmj0AlarmEntry 4 }


pm1004mAlmJ0TiiAlarmPortn OBJECT-TYPE
	SYNTAX  EkiOnOff
	MAX-ACCESS read-only
	STATUS current
	DESCRIPTION
        "
        Trace Identifier Unstable :This 
        OID indicates the Trace Identifier 
        is unstable on the client input 
        stream <Condtype> J0_TII_ALARM_1 
        <Probcause> other (1) <Alarmtype> 
        other (1) <Polarity> (2) 
        "
	::= { pm1004mAlmj0AlarmEntry 3 }


pm1004mAlmJ0TimAlarmPortn OBJECT-TYPE
	SYNTAX  EkiOnOff
	MAX-ACCESS read-only
	STATUS current
	DESCRIPTION
        "
        Trace Identifier Mismatch :This 
        OID indicates a Trace Identifier 
        Mismatch has been detected on the 
        client input stream <Condtype>
         J0_TIM_ALARM_1 <Probcause> other 
        (1) <Alarmtype> other (1) <Polarity> 
        (2) 
        "
	::= { pm1004mAlmj0AlarmEntry 2 }


--- *********************************************************
---     TABLE for the pm1004mAlmdfrmAlm articles
--- *********************************************************

pm1004mAlmdfrmAlmTable OBJECT-TYPE
	SYNTAX  SEQUENCE OF Pm1004mAlmdfrmAlmEntry
	MAX-ACCESS not-accessible
	STATUS current
	DESCRIPTION
        "
        List of pm1004mAlmdfrmAlm Article
        "
	::= { pm1004mAlmLineCrit 128 }


pm1004mAlmdfrmAlmEntry OBJECT-TYPE
	SYNTAX Pm1004mAlmdfrmAlmEntry
	MAX-ACCESS not-accessible
	STATUS current
	DESCRIPTION
        "
        Row definition for the pm1004mAlmdfrmAlm 
        table
        "
	INDEX   { pm1004mAlmdfrmAlmIndex }
	::= { pm1004mAlmdfrmAlmTable 1 }


Pm1004mAlmdfrmAlmEntry ::=
	SEQUENCE {
	pm1004mAlmdfrmAlmIndex
		INTEGER,
	pm1004mAlmDwLofPortn
		EkiOnOff,
	pm1004mAlmDwOofPortn
		EkiOnOff,
	pm1004mAlmDwRdiDetPortn
		EkiOnOff,
	pm1004mAlmDwAisDetPortn
		EkiOnOff
	}


pm1004mAlmdfrmAlmIndex OBJECT-TYPE
	SYNTAX  INTEGER(0..128)
	MAX-ACCESS  read-only
	STATUS current
	DESCRIPTION
        "
        Index definition for the pm1004mAlmdfrmAlm 
        table
        "
	::= { pm1004mAlmdfrmAlmEntry 1 }


pm1004mAlmDwLofPortn OBJECT-TYPE
	SYNTAX  EkiOnOff
	MAX-ACCESS read-only
	STATUS current
	DESCRIPTION
        "
        SONET/SDH Line Loss Of Frame :This 
        OID indicates that a Loss Of Frame 
        has been detected on the input
         signal  <Help>  This alarm indicates 
        if there is a Loss of Frame is
         detected on the line input signal 
        <Condtype> DW_LOF_1 <Probcause> 
        receiveFailure (41) <Alarmtype> 
        integrityViolation (7) <Polarity> 
        (2) 
        "
	::= { pm1004mAlmdfrmAlmEntry 5 }


pm1004mAlmDwOofPortn OBJECT-TYPE
	SYNTAX  EkiOnOff
	MAX-ACCESS read-only
	STATUS current
	DESCRIPTION
        "
        SONET/SDH Line Out Of Frame :This 
        OID indicates that an Out Of Frame 
        has been detected on the input
         signal  <Help>  This alarm indicates 
        if there is a Out of Frame is detected 
        on the line input signal <Condtype> 
        DW_OOF_1 <Probcause> receiveFailure 
        (41) <Alarmtype> integrityViolation 
        (7) <Polarity> (2) 
        "
	::= { pm1004mAlmdfrmAlmEntry 4 }


pm1004mAlmDwRdiDetPortn OBJECT-TYPE
	SYNTAX  EkiOnOff
	MAX-ACCESS read-only
	STATUS current
	DESCRIPTION
        "
        MS-RDI/L-RDI Detected On Line
         Input :This OID indicates that 
        an MS-RDI has been detected on
         the input signal  <Help>  This 
        alarm indicates if there is a RDI 
        is detected on the line input signal 
        <Condtype> DW_RDI_DET_1 <Probcause> 
        remoteNodeTransmissionError (43) 
        <Alarmtype> other (1) <Polarity> 
        (2) 
        "
	::= { pm1004mAlmdfrmAlmEntry 3 }


pm1004mAlmDwAisDetPortn OBJECT-TYPE
	SYNTAX  EkiOnOff
	MAX-ACCESS read-only
	STATUS current
	DESCRIPTION
        "
        MS-AIS/L-AIS Detected On Line
         Input :This OID indicates that 
        an MS-AIS has been detected on
         the input signal  <Help>  This 
        alarm indicates if there is a AIS 
        is detected on the line input signal 
        <Condtype> DW_AIS_DET_1 <Probcause> 
        receiveFailure (41) <Alarmtype> 
        operationalViolation (8) <Polarity> 
        (2) 
        "
	::= { pm1004mAlmdfrmAlmEntry 2 }


--- *********************************************************
---     TABLE for the pm1004mAlmdfrmBer articles
--- *********************************************************

pm1004mAlmdfrmBerTable OBJECT-TYPE
	SYNTAX  SEQUENCE OF Pm1004mAlmdfrmBerEntry
	MAX-ACCESS not-accessible
	STATUS current
	DESCRIPTION
        "
        List of pm1004mAlmdfrmBer Article
        "
	::= { pm1004mAlmLineUrg 129 }


pm1004mAlmdfrmBerEntry OBJECT-TYPE
	SYNTAX Pm1004mAlmdfrmBerEntry
	MAX-ACCESS not-accessible
	STATUS current
	DESCRIPTION
        "
        Row definition for the pm1004mAlmdfrmBer 
        table
        "
	INDEX   { pm1004mAlmdfrmBerIndex }
	::= { pm1004mAlmdfrmBerTable 1 }


Pm1004mAlmdfrmBerEntry ::=
	SEQUENCE {
	pm1004mAlmdfrmBerIndex
		INTEGER,
	pm1004mAlmLineDegradePortn
		EkiOnOff,
	pm1004mAlmLineSignalFailPortn
		EkiOnOff,
	pm1004mAlmLineSignalDegradePortn
		EkiOnOff
	}


pm1004mAlmdfrmBerIndex OBJECT-TYPE
	SYNTAX  INTEGER(0..128)
	MAX-ACCESS  read-only
	STATUS current
	DESCRIPTION
        "
        Index definition for the pm1004mAlmdfrmBer 
        table
        "
	::= { pm1004mAlmdfrmBerEntry 1 }


pm1004mAlmLineDegradePortn OBJECT-TYPE
	SYNTAX  EkiOnOff
	MAX-ACCESS read-only
	STATUS current
	DESCRIPTION
        "
        Fixed Line Signal Degrade :This 
        OID indicates that the line input 
        signal is DEGRADE. The assetion 
        hysteresis is fixed to 10-8 (assertion) 
        and 10-9 (de-assertion) <Condtype> 
        LINE_DEGRADE_1 <Probcause> degradedSignal 
        (13) <Alarmtype> qualityOfServiceAlarm 
        (3) <Polarity> (2) 
        "
	::= { pm1004mAlmdfrmBerEntry 6 }


pm1004mAlmLineSignalFailPortn OBJECT-TYPE
	SYNTAX  EkiOnOff
	MAX-ACCESS read-only
	STATUS current
	DESCRIPTION
        "
        Custom Line Signal Fail :This
         OID indicates that the line input 
        signal is FAIL. The assertion hysteresis 
        can be customized by the host <Condtype> 
        LINE_SIGNAL_FAIL_1 <Probcause>
         receiveFailure (41) <Alarmtype> 
        integrityViolation (7) <Polarity> 
        (2) 
        "
	::= { pm1004mAlmdfrmBerEntry 3 }


pm1004mAlmLineSignalDegradePortn OBJECT-TYPE
	SYNTAX  EkiOnOff
	MAX-ACCESS read-only
	STATUS current
	DESCRIPTION
        "
        Custom Line Signal Degrade :This 
        OID indicates that the line input 
        signal is DEGRADE. The assertion 
        hysteresis can customized by the 
        host <Condtype> LINE_SIGNAL_DEGRADE_1 
        <Probcause> degradedSignal (13) 
        <Alarmtype> qualityOfServiceAlarm 
        (3) <Polarity> (2) 
        "
	::= { pm1004mAlmdfrmBerEntry 2 }


--- *********************************************************
---     TABLE for the pm1004mAlmlineSyncAlarms articles
--- *********************************************************

pm1004mAlmlineSyncAlarmsTable OBJECT-TYPE
	SYNTAX  SEQUENCE OF Pm1004mAlmlineSyncAlarmsEntry
	MAX-ACCESS not-accessible
	STATUS current
	DESCRIPTION
        "
        List of pm1004mAlmlineSyncAlarms 
        Article
        "
	::= { pm1004mAlmLineCrit 133 }


pm1004mAlmlineSyncAlarmsEntry OBJECT-TYPE
	SYNTAX Pm1004mAlmlineSyncAlarmsEntry
	MAX-ACCESS not-accessible
	STATUS current
	DESCRIPTION
        "
        Row definition for the pm1004mAlmlineSyncAlarms 
        table
        "
	INDEX   { pm1004mAlmlineSyncAlarmsIndex }
	::= { pm1004mAlmlineSyncAlarmsTable 1 }


Pm1004mAlmlineSyncAlarmsEntry ::=
	SEQUENCE {
	pm1004mAlmlineSyncAlarmsIndex
		INTEGER,
	pm1004mAlmDwLosPortn
		EkiOnOff,
	pm1004mAlmUpLockerrPortn
		EkiOnOff,
	pm1004mAlmDwLockerrPortn
		EkiOnOff
	}


pm1004mAlmlineSyncAlarmsIndex OBJECT-TYPE
	SYNTAX  INTEGER(0..128)
	MAX-ACCESS  read-only
	STATUS current
	DESCRIPTION
        "
        Index definition for the pm1004mAlmlineSyncAlarms 
        table
        "
	::= { pm1004mAlmlineSyncAlarmsEntry 1 }


pm1004mAlmDwLosPortn OBJECT-TYPE
	SYNTAX  EkiOnOff
	MAX-ACCESS read-only
	STATUS current
	DESCRIPTION
        "
        Line Input Loss Of Signal :This 
        OID indicates a loss of signal
         on the 10 Gb/s input.  <Help>
          This alarm indicates if an optical 
        signal is detected on the line
         transceiver input <Condtype> DW_LOS 
        <Probcause> receiveFailure (41) 
        <Alarmtype> physicalViolation (9) 
        <Polarity> (2) 
        "
	::= { pm1004mAlmlineSyncAlarmsEntry 17 }


pm1004mAlmUpLockerrPortn OBJECT-TYPE
	SYNTAX  EkiOnOff
	MAX-ACCESS read-only
	STATUS current
	DESCRIPTION
        "
        Upstream Clock Lock Error :This 
        OID indicates that the serializer 
        output 10 Gb/s clock multiplier 
        unit is not locked. <Condtype>
         UP_LOCKERR <Probcause> receiveFailure 
        (41) <Alarmtype> equipmentAlarm 
        (5) <Polarity> (2) 
        "
	::= { pm1004mAlmlineSyncAlarmsEntry 14 }


pm1004mAlmDwLockerrPortn OBJECT-TYPE
	SYNTAX  EkiOnOff
	MAX-ACCESS read-only
	STATUS current
	DESCRIPTION
        "
        Downstream Clock Lock Error :This 
        OID indicates that the deserializer 
        input 10 Gb/s clock recovery is 
        not locked. <Condtype> DW_LOCKERR 
        <Probcause> receiveFailure (41) 
        <Alarmtype> equipmentAlarm (5)
         <Polarity> (2) 
        "
	::= { pm1004mAlmlineSyncAlarmsEntry 13 }


--- *****************************************************
---     LEAF for the modInitFailLevel2 article
--- *****************************************************
pm1004mAlmmodInitFailLevel2 OBJECT IDENTIFIER ::= { pm1004mAlmOtherUrg 194 }




pm1004mAlmSwInitFail OBJECT-TYPE
	  SYNTAX EkiOnOff
	  MAX-ACCESS read-only
	  STATUS current
	  DESCRIPTION
        "
        SW Init Fail :This OID indicates 
        that the SW intialization has caused 
        unknown intial conditions  <Help> 
         This alarm indicates if the SW 
        module is correctly initialized 
        <Condtype> SW_INIT_FAIL <Probcause> 
        softwareError (47) <Alarmtype>
         processingErrorAlarm (4) <Polarity> 
        (2) 
        "
	  ::= { pm1004mAlmmodInitFailLevel2 5 }



pm1004mAlmResetHwInitFail OBJECT-TYPE
	  SYNTAX EkiOnOff
	  MAX-ACCESS read-only
	  STATUS current
	  DESCRIPTION
        "
        Reset HW Init Fail :This OID indicates 
        that the HW intialization has caused 
        unknown intial conditions  <Help> 
         This alarm indicates if the HW 
        has been correctly initialized
         <Condtype> RESET_HW_INIT_FAIL
         <Probcause> softwareError (47) 
        <Alarmtype> processingErrorAlarm 
        (4) <Polarity> (2) 
        "
	  ::= { pm1004mAlmmodInitFailLevel2 4 }



pm1004mAlmBootUndone OBJECT-TYPE
	  SYNTAX EkiOnOff
	  MAX-ACCESS read-only
	  STATUS current
	  DESCRIPTION
        "
        Boot Undone :This OID indicates 
        that the boot has not been correctly 
        achieved  <Help>  This alarm indicates 
        if the module has correctly boot 
        <Condtype> BOOT_UNDONE <Probcause> 
        softwareError (47) <Alarmtype>
         processingErrorAlarm (4) <Polarity> 
        (2) 
        "
	  ::= { pm1004mAlmmodInitFailLevel2 3 }



pm1004mAlmNextColdBootForced OBJECT-TYPE
	  SYNTAX EkiOnOff
	  MAX-ACCESS read-only
	  STATUS current
	  DESCRIPTION
        "
        Next Cold Boot Forced :This OID 
        indicates that the next Reset will 
        be forced Cold  <Help>  This alarm 
        indicates that the next reset of 
        the module will be forced to cold 
        reset <Condtype> NEXT_COLD_BOOT_FORCED 
        <Probcause> informationalStatus(1000) 
        <Alarmtype> other (1) <Polarity> 
        (2) 
        "
	  ::= { pm1004mAlmmodInitFailLevel2 2 }



pm1004mAlmLedFail OBJECT-TYPE
	  SYNTAX EkiOnOff
	  MAX-ACCESS read-only
	  STATUS current
	  DESCRIPTION
        "
        Led Fail :This OID indicates that 
        Led register has not been correctly 
        initalized  <Help>  This alarm
         indicates if the module LEDs are 
        correctly initialized <Condtype> 
        LED_FAIL <Probcause> softwareError 
        (47) <Alarmtype> processingErrorAlarm 
        (4) <Polarity> (2) 
        "
	  ::= { pm1004mAlmmodInitFailLevel2 1 }



--- *****************************************************
---     LEAF for the modInitFailLevel3 article
--- *****************************************************
pm1004mAlmmodInitFailLevel3 OBJECT IDENTIFIER ::= { pm1004mAlmOtherUrg 195 }




pm1004mAlmClient4InitFail OBJECT-TYPE
	  SYNTAX EkiOnOff
	  MAX-ACCESS read-only
	  STATUS current
	  DESCRIPTION
        "
        Client4 Init Fail :This OID indicates 
        that Client 4 registers subset
         has not been correctly initialized 
         <Help>  This alarm indicates if 
        the client port 4 is correctly
         initialized <Condtype> CLIENT4_INIT_FAIL 
        <Probcause> softwareError (47)
         <Alarmtype> processingErrorAlarm 
        (4) <Polarity> (2) 
        "
	  ::= { pm1004mAlmmodInitFailLevel3 12 }



pm1004mAlmClient3InitFail OBJECT-TYPE
	  SYNTAX EkiOnOff
	  MAX-ACCESS read-only
	  STATUS current
	  DESCRIPTION
        "
        Client3 Init Fail :This OID indicates 
        that Client 3 registers subset
         has not been correctly initialized 
         <Help>  This alarm indicates if 
        the client port 3 is correctly
         initialized <Condtype> CLIENT3_INIT_FAIL 
        <Probcause> softwareError (47)
         <Alarmtype> processingErrorAlarm 
        (4) <Polarity> (2) 
        "
	  ::= { pm1004mAlmmodInitFailLevel3 11 }



pm1004mAlmClient2InitFail OBJECT-TYPE
	  SYNTAX EkiOnOff
	  MAX-ACCESS read-only
	  STATUS current
	  DESCRIPTION
        "
        Client2 Init Fail :This OID indicates 
        that Client 2 registers subset
         has not been correctly initialized 
         <Help>  This alarm indicates if 
        the client port 2 is correctly
         initialized <Condtype> CLIENT2_INIT_FAIL 
        <Probcause> softwareError (47)
         <Alarmtype> processingErrorAlarm 
        (4) <Polarity> (2) 
        "
	  ::= { pm1004mAlmmodInitFailLevel3 10 }



pm1004mAlmClient1InitFail OBJECT-TYPE
	  SYNTAX EkiOnOff
	  MAX-ACCESS read-only
	  STATUS current
	  DESCRIPTION
        "
        Client1 Init Fail :This OID indicates 
        that Client 1 registers subset
         has not been correctly initialized 
         <Help>  This alarm indicates if 
        the client port 1 is correctly
         initialized <Condtype> CLIENT1_INIT_FAIL 
        <Probcause> softwareError (47)
         <Alarmtype> processingErrorAlarm 
        (4) <Polarity> (2) 
        "
	  ::= { pm1004mAlmmodInitFailLevel3 9 }



pm1004mAlmLine2InitFail OBJECT-TYPE
	  SYNTAX EkiOnOff
	  MAX-ACCESS read-only
	  STATUS current
	  DESCRIPTION
        "
        Line2 Init Fail :This OID indicates 
        that the Line register subset has 
        not been correctly initialized
          <Help>  This alarm indicates
         if the line port 2 is correctly 
        initialized <Condtype> LINE2_INIT_FAIL 
        <Probcause> softwareError (47)
         <Alarmtype> processingErrorAlarm 
        (4) <Polarity> (2) 
        "
	  ::= { pm1004mAlmmodInitFailLevel3 8 }



pm1004mAlmLine1InitFail OBJECT-TYPE
	  SYNTAX EkiOnOff
	  MAX-ACCESS read-only
	  STATUS current
	  DESCRIPTION
        "
        Line1 Init Fail :This OID indicates 
        that the Line registersvsubset
         has not been correctly initialized 
         <Help>  This alarm indicates if 
        the line port 1 is correctly initialized 
        <Condtype> LINE1_INIT_FAIL <Probcause> 
        softwareError (47) <Alarmtype>
         processingErrorAlarm (4) <Polarity> 
        (2) 
        "
	  ::= { pm1004mAlmmodInitFailLevel3 7 }



pm1004mAlmXfp2InitFail OBJECT-TYPE
	  SYNTAX EkiOnOff
	  MAX-ACCESS read-only
	  STATUS current
	  DESCRIPTION
        "
        XFP2 Init Fail :This OID indicates 
        that the XFP has not been correctly 
        initialized  <Help>  This alarm 
        indicates if the line transceiver 
        2 is correctly initialized <Condtype> 
        XFP2_INIT_FAIL <Probcause> softwareError 
        (47) <Alarmtype> processingErrorAlarm 
        (4) <Polarity> (2) 
        "
	  ::= { pm1004mAlmmodInitFailLevel3 6 }



pm1004mAlmXfp1InitFail OBJECT-TYPE
	  SYNTAX EkiOnOff
	  MAX-ACCESS read-only
	  STATUS current
	  DESCRIPTION
        "
        XFP1 Init Fail :This OID indicates 
        that the XFP has not been correctly 
        initialized  <Help>  This alarm 
        indicates if the line transceiver 
        1 is correctly initialized <Condtype> 
        XFP1_INIT_FAIL <Probcause> softwareError 
        (47) <Alarmtype> processingErrorAlarm 
        (4) <Polarity> (2) 
        "
	  ::= { pm1004mAlmmodInitFailLevel3 5 }



pm1004mAlmInitModuleFail OBJECT-TYPE
	  SYNTAX EkiOnOff
	  MAX-ACCESS read-only
	  STATUS current
	  DESCRIPTION
        "
        Init Module Fail :This OID indicates 
        that the Module has not been correctly 
        initialized  <Help>  This alarm 
        indicates if the SW module is correctly 
        initialized <Condtype> INIT_MODULE_FAIL 
        <Probcause> softwareError (47)
         <Alarmtype> processingErrorAlarm 
        (4) <Polarity> (2) 
        "
	  ::= { pm1004mAlmmodInitFailLevel3 3 }



pm1004mAlmObmTypeReadFail OBJECT-TYPE
	  SYNTAX EkiOnOff
	  MAX-ACCESS read-only
	  STATUS current
	  DESCRIPTION
        "
        OBM Type Read Fail :This OID indicates 
        that OBM type has not been recognized 
         <Help>  This alarm indicates if 
        the OBM board has been correctly 
        identified <Condtype> OBM_TYPE_READ_FAIL 
        <Probcause> softwareError (47)
         <Alarmtype> processingErrorAlarm 
        (4) <Polarity> (2) 
        "
	  ::= { pm1004mAlmmodInitFailLevel3 2 }



pm1004mAlmGwIdentFail OBJECT-TYPE
	  SYNTAX EkiOnOff
	  MAX-ACCESS read-only
	  STATUS current
	  DESCRIPTION
        "
        GW Ident Fail :This OID indicates 
        that GW identification has not
         been read  <Help>  This alarm
         indicates if the GW has been correctly 
        identified <Condtype> GW_IDENT_FAIL 
        <Probcause> softwareError (47)
         <Alarmtype> processingErrorAlarm 
        (4) <Polarity> (2) 
        "
	  ::= { pm1004mAlmmodInitFailLevel3 1 }



--- *********************************************************
---     TABLE for the pm1004mAlmlineXfp1Alarm articles
--- *********************************************************

pm1004mAlmlineXfp1AlarmTable OBJECT-TYPE
	SYNTAX  SEQUENCE OF Pm1004mAlmlineXfp1AlarmEntry
	MAX-ACCESS not-accessible
	STATUS current
	DESCRIPTION
        "
        List of pm1004mAlmlineXfp1Alarm 
        Article
        "
	::= { pm1004mAlmLineUrg 208 }


pm1004mAlmlineXfp1AlarmEntry OBJECT-TYPE
	SYNTAX Pm1004mAlmlineXfp1AlarmEntry
	MAX-ACCESS not-accessible
	STATUS current
	DESCRIPTION
        "
        Row definition for the pm1004mAlmlineXfp1Alarm 
        table
        "
	INDEX   { pm1004mAlmlineXfp1AlarmIndex }
	::= { pm1004mAlmlineXfp1AlarmTable 1 }


Pm1004mAlmlineXfp1AlarmEntry ::=
	SEQUENCE {
	pm1004mAlmlineXfp1AlarmIndex
		INTEGER,
	pm1004mAlmRxPowerHighAlarmPortn
		EkiOnOff,
	pm1004mAlmRxPowerLowAlarmPortn
		EkiOnOff,
	pm1004mAlmTempHighAlarmPortn
		EkiOnOff,
	pm1004mAlmTempLowAlarmPortn
		EkiOnOff,
	pm1004mAlmTxBiasHighAlarmPortn
		EkiOnOff,
	pm1004mAlmTxBiasLowAlarmPortn
		EkiOnOff,
	pm1004mAlmTxPowerHighAlarmPortn
		EkiOnOff,
	pm1004mAlmTxPowerLowAlarmPortn
		EkiOnOff
	}


pm1004mAlmlineXfp1AlarmIndex OBJECT-TYPE
	SYNTAX  INTEGER(0..128)
	MAX-ACCESS  read-only
	STATUS current
	DESCRIPTION
        "
        Index definition for the pm1004mAlmlineXfp1Alarm 
        table
        "
	::= { pm1004mAlmlineXfp1AlarmEntry 1 }


pm1004mAlmRxPowerHighAlarmPortn OBJECT-TYPE
	SYNTAX  EkiOnOff
	MAX-ACCESS read-only
	STATUS current
	DESCRIPTION
        "
        Line Optical Rx Power High :Alarm 
        indicating that the XFP received 
        optical power is higher than the 
        threshold value written in the
         XFP EEPROM <Condtype> RX_POWER_HIGH_ALARM_1 
        <Probcause> receiveFailure (41) 
        <Alarmtype> equipmentAlarm (5)
         <Polarity> (2) 
        "
	::= { pm1004mAlmlineXfp1AlarmEntry 17 }


pm1004mAlmRxPowerLowAlarmPortn OBJECT-TYPE
	SYNTAX  EkiOnOff
	MAX-ACCESS read-only
	STATUS current
	DESCRIPTION
        "
        Line Optical Rx Power Low :Alarm 
        indicating that the XFP received 
        optical power is lower than the 
        threshold value written in the
         XFP EEPROM  <Condtype> RX_POWER_LOW_ALARM_1 
        <Probcause> receiveFailure (41) 
        <Alarmtype> equipmentAlarm (5)
         <Polarity> (2) 
        "
	::= { pm1004mAlmlineXfp1AlarmEntry 16 }


pm1004mAlmTempHighAlarmPortn OBJECT-TYPE
	SYNTAX  EkiOnOff
	MAX-ACCESS read-only
	STATUS current
	DESCRIPTION
        "
        Line Transceiver Temp High :Alarm 
        indicating that the XFP/OTX temperature 
        is higher than the threshold value 
        written in the XFP EEPROM <Condtype> 
        TEMP_HIGH_ALARM_1 <Probcause> temperatureUnacceptable 
        (51) <Alarmtype> equipmentAlarm 
        (5) <Polarity> (2) 
        "
	::= { pm1004mAlmlineXfp1AlarmEntry 9 }


pm1004mAlmTempLowAlarmPortn OBJECT-TYPE
	SYNTAX  EkiOnOff
	MAX-ACCESS read-only
	STATUS current
	DESCRIPTION
        "
        Line Transceiver Temp Low :Alarm 
        indicating that the XFP/OTX temperature 
        is lower than the threshold value 
        written in the XFP/OTX EEPROM <Condtype> 
        TEMP_LOW_ALARM_1 <Probcause> temperatureUnacceptable 
        (51) <Alarmtype> equipmentAlarm 
        (5) <Polarity> (2) 
        "
	::= { pm1004mAlmlineXfp1AlarmEntry 8 }


pm1004mAlmTxBiasHighAlarmPortn OBJECT-TYPE
	SYNTAX  EkiOnOff
	MAX-ACCESS read-only
	STATUS current
	DESCRIPTION
        "
        Line Transceiver Bias High :Alarm 
        indicating that the XFP/OTX transmitter 
        laser bias current is higher than 
        the threshold value written in
         the XFP EEPROM <Condtype> TX_BIAS_HIGH_ALARM_1 
        <Probcause> transmitterFailure
         (56) <Alarmtype> equipmentAlarm 
        (5) <Polarity> (2) 
        "
	::= { pm1004mAlmlineXfp1AlarmEntry 5 }


pm1004mAlmTxBiasLowAlarmPortn OBJECT-TYPE
	SYNTAX  EkiOnOff
	MAX-ACCESS read-only
	STATUS current
	DESCRIPTION
        "
        Line Transceiver Bias Low :Alarm 
        indicating that the XFP/OTX transmitter 
        laser bias current is lower than 
        the threshold value written in
         the XFP/OTX EEPROM <Condtype>
         TX_BIAS_LOW_ALARM_1 <Probcause> 
        transmitterFailure (56) <Alarmtype> 
        equipmentAlarm (5) <Polarity> (2) 
        "
	::= { pm1004mAlmlineXfp1AlarmEntry 4 }


pm1004mAlmTxPowerHighAlarmPortn OBJECT-TYPE
	SYNTAX  EkiOnOff
	MAX-ACCESS read-only
	STATUS current
	DESCRIPTION
        "
        Line Optical Tx Power High :Alarm 
        indicating that the XFP/OTX transmitter 
        transmitter output power is higher 
        than the threshold value written 
        in the XFP EEPROM <Condtype> TX_POWER_HIGH_ALARM_1 
        <Probcause> transmitterFailure
         (56) <Alarmtype> equipmentAlarm 
        (5) <Polarity> (2) 
        "
	::= { pm1004mAlmlineXfp1AlarmEntry 3 }


pm1004mAlmTxPowerLowAlarmPortn OBJECT-TYPE
	SYNTAX  EkiOnOff
	MAX-ACCESS read-only
	STATUS current
	DESCRIPTION
        "
        Line Optical Tx Power Low :Alarm 
        indicating that the XFP/OTX transmitter 
        transmitter output power is lower 
        than the threshold value written 
        in the XFP/OTX EEPROM <Condtype> 
        TX_POWER_LOW_ALARM_1 <Probcause> 
        transmitterFailure (56) <Alarmtype> 
        equipmentAlarm (5) <Polarity> (2) 
        "
	::= { pm1004mAlmlineXfp1AlarmEntry 2 }


--- *********************************************************
---     TABLE for the pm1004mAlmlineXfp1Warnings articles
--- *********************************************************

pm1004mAlmlineXfp1WarningsTable OBJECT-TYPE
	SYNTAX  SEQUENCE OF Pm1004mAlmlineXfp1WarningsEntry
	MAX-ACCESS not-accessible
	STATUS current
	DESCRIPTION
        "
        List of pm1004mAlmlineXfp1Warnings 
        Article
        "
	::= { pm1004mAlmLineNurg 209 }


pm1004mAlmlineXfp1WarningsEntry OBJECT-TYPE
	SYNTAX Pm1004mAlmlineXfp1WarningsEntry
	MAX-ACCESS not-accessible
	STATUS current
	DESCRIPTION
        "
        Row definition for the pm1004mAlmlineXfp1Warnings 
        table
        "
	INDEX   { pm1004mAlmlineXfp1WarningsIndex }
	::= { pm1004mAlmlineXfp1WarningsTable 1 }


Pm1004mAlmlineXfp1WarningsEntry ::=
	SEQUENCE {
	pm1004mAlmlineXfp1WarningsIndex
		INTEGER,
	pm1004mAlmRxPowerHighWarningPortn
		EkiOnOff,
	pm1004mAlmRxPowerLowWarningPortn
		EkiOnOff,
	pm1004mAlmTempHighWarningPortn
		EkiOnOff,
	pm1004mAlmTempLowWarningPortn
		EkiOnOff,
	pm1004mAlmTxBiasHighWarningPortn
		EkiOnOff,
	pm1004mAlmTxBiasLowWarningPortn
		EkiOnOff,
	pm1004mAlmTxPowerHighWarningPortn
		EkiOnOff,
	pm1004mAlmTxPowerLowWarningPortn
		EkiOnOff
	}


pm1004mAlmlineXfp1WarningsIndex OBJECT-TYPE
	SYNTAX  INTEGER(0..128)
	MAX-ACCESS  read-only
	STATUS current
	DESCRIPTION
        "
        Index definition for the pm1004mAlmlineXfp1Warnings 
        table
        "
	::= { pm1004mAlmlineXfp1WarningsEntry 1 }


pm1004mAlmRxPowerHighWarningPortn OBJECT-TYPE
	SYNTAX  EkiOnOff
	MAX-ACCESS read-only
	STATUS current
	DESCRIPTION
        "
        Line Optical Rx Power High Warning 
        :Warning indicating that the XFP 
        received optical power is higher 
        than the threshold value written 
        in the XFP EEPROM <Condtype> RX_POWER_HIGH_WARNING_1 
        <Probcause> receiveFailure (41) 
        <Alarmtype> equipmentAlarm (5)
         <Polarity> (2) 
        "
	::= { pm1004mAlmlineXfp1WarningsEntry 17 }


pm1004mAlmRxPowerLowWarningPortn OBJECT-TYPE
	SYNTAX  EkiOnOff
	MAX-ACCESS read-only
	STATUS current
	DESCRIPTION
        "
        Line Optical Rx Power Low Warning 
        :Warning indicating that the XFP 
        received optical power is lower 
        than the threshold value written 
        in the XFP EEPROM  <Condtype> RX_POWER_LOW_WARNING_1 
        <Probcause> receiveFailure (41) 
        <Alarmtype> equipmentAlarm (5)
         <Polarity> (2) 
        "
	::= { pm1004mAlmlineXfp1WarningsEntry 16 }


pm1004mAlmTempHighWarningPortn OBJECT-TYPE
	SYNTAX  EkiOnOff
	MAX-ACCESS read-only
	STATUS current
	DESCRIPTION
        "
        Line Transceiver Temp High Warning 
        :Warning indicating that the XFP/OTX 
        temperature is higher than the
         threshold value written in the 
        XFP EEPROM <Condtype> TEMP_HIGH_WARNING_1 
        <Probcause> temperatureUnacceptable 
        (51) <Alarmtype> equipmentAlarm 
        (5) <Polarity> (2) 
        "
	::= { pm1004mAlmlineXfp1WarningsEntry 9 }


pm1004mAlmTempLowWarningPortn OBJECT-TYPE
	SYNTAX  EkiOnOff
	MAX-ACCESS read-only
	STATUS current
	DESCRIPTION
        "
        Line Transceiver Temp Low Warning 
        :Warning indicating that the XFP/OTX 
        temperature is lower than the threshold 
        value written in the XFP/OTX EEPROM 
        <Condtype> TEMP_LOW_WARNING_1 <Probcause> 
        temperatureUnacceptable (51) <Alarmtype> 
        equipmentAlarm (5) <Polarity> (2) 
        "
	::= { pm1004mAlmlineXfp1WarningsEntry 8 }


pm1004mAlmTxBiasHighWarningPortn OBJECT-TYPE
	SYNTAX  EkiOnOff
	MAX-ACCESS read-only
	STATUS current
	DESCRIPTION
        "
        Line Transceiver Bias High Warning 
        :Warning indicating that the XFP/OTX 
        transmitter laser bias current
         is higher than the threshold value 
        written in the XFP EEPROM <Condtype> 
        TX_BIAS_HIGH_WARNING_1 <Probcause> 
        transmitterFailure (56) <Alarmtype> 
        equipmentAlarm (5) <Polarity> (2) 
        "
	::= { pm1004mAlmlineXfp1WarningsEntry 5 }


pm1004mAlmTxBiasLowWarningPortn OBJECT-TYPE
	SYNTAX  EkiOnOff
	MAX-ACCESS read-only
	STATUS current
	DESCRIPTION
        "
        Line Transceiver Bias Low Warning 
        :Warning indicating that the XFP/OTX 
        transmitter laser bias current
         is lower than the threshold value 
        written in the XFP/OTX EEPROM <Condtype> 
        TX_BIAS_LOW_WARNING_1 <Probcause> 
        transmitterFailure (56) <Alarmtype> 
        equipmentAlarm (5) <Polarity> (2) 
        "
	::= { pm1004mAlmlineXfp1WarningsEntry 4 }


pm1004mAlmTxPowerHighWarningPortn OBJECT-TYPE
	SYNTAX  EkiOnOff
	MAX-ACCESS read-only
	STATUS current
	DESCRIPTION
        "
        Line Optical Tx Power High Warning 
        :Warning indicating that the XFP/OTX 
        transmitter transmitter output
         power is higher than the threshold 
        value written in the XFP EEPROM 
        <Condtype> TX_POWER_HIGH_WARNING_1 
        <Probcause> transmitterFailure
         (56) <Alarmtype> equipmentAlarm 
        (5) <Polarity> (2) 
        "
	::= { pm1004mAlmlineXfp1WarningsEntry 3 }


pm1004mAlmTxPowerLowWarningPortn OBJECT-TYPE
	SYNTAX  EkiOnOff
	MAX-ACCESS read-only
	STATUS current
	DESCRIPTION
        "
        Line Optical Tx Power Low Warning 
        :Warning indicating that the XFP/OTX 
        transmitter transmitter output
         power is lower than the threshold 
        value written in the XFP/OTX EEPROM 
        <Condtype> TX_POWER_LOW_WARNING_1 
        <Probcause> transmitterFailure
         (56) <Alarmtype> equipmentAlarm 
        (5) <Polarity> (2) 
        "
	::= { pm1004mAlmlineXfp1WarningsEntry 2 }


--- *********************************************************
---     TABLE for the pm1004mAlmlineXfp1Alarms articles
--- *********************************************************

pm1004mAlmlineXfp1AlarmsTable OBJECT-TYPE
	SYNTAX  SEQUENCE OF Pm1004mAlmlineXfp1AlarmsEntry
	MAX-ACCESS not-accessible
	STATUS current
	DESCRIPTION
        "
        List of pm1004mAlmlineXfp1Alarms 
        Article
        "
	::= { pm1004mAlmLineCrit 211 }


pm1004mAlmlineXfp1AlarmsEntry OBJECT-TYPE
	SYNTAX Pm1004mAlmlineXfp1AlarmsEntry
	MAX-ACCESS not-accessible
	STATUS current
	DESCRIPTION
        "
        Row definition for the pm1004mAlmlineXfp1Alarms 
        table
        "
	INDEX   { pm1004mAlmlineXfp1AlarmsIndex }
	::= { pm1004mAlmlineXfp1AlarmsTable 1 }


Pm1004mAlmlineXfp1AlarmsEntry ::=
	SEQUENCE {
	pm1004mAlmlineXfp1AlarmsIndex
		INTEGER,
	pm1004mAlmApdSupplyFaultPortn
		EkiOnOff,
	pm1004mAlmTecFaultPortn
		EkiOnOff,
	pm1004mAlmWavelengthUnlockedPortn
		EkiOnOff,
	pm1004mAlmTxNrPortn
		EkiOnOff,
	pm1004mAlmTxFaultPortn
		EkiOnOff,
	pm1004mAlmTxCdrNotLockedPortn
		EkiOnOff,
	pm1004mAlmRxNrPortn
		EkiOnOff,
	pm1004mAlmRxCdrNotLockedPortn
		EkiOnOff,
	pm1004mAlmModNrPortn
		EkiOnOff
	}


pm1004mAlmlineXfp1AlarmsIndex OBJECT-TYPE
	SYNTAX  INTEGER(0..128)
	MAX-ACCESS  read-only
	STATUS current
	DESCRIPTION
        "
        Index definition for the pm1004mAlmlineXfp1Alarms 
        table
        "
	::= { pm1004mAlmlineXfp1AlarmsEntry 1 }


pm1004mAlmApdSupplyFaultPortn OBJECT-TYPE
	SYNTAX  EkiOnOff
	MAX-ACCESS read-only
	STATUS current
	DESCRIPTION
        "
        Line Rx Photodiode Power Failed 
        :This OID indicates a failure on 
        the APD power supply  <Help>  This 
        alarm indicates if the APD power 
        supply is in fail condition <Condtype> 
        APD_SUPPLY_FAULT_1 <Probcause>
         receiverFailure (42) <Alarmtype> 
        equipmentAlarm (5) <Polarity> (2) 
        "
	::= { pm1004mAlmlineXfp1AlarmsEntry 17 }


pm1004mAlmTecFaultPortn OBJECT-TYPE
	SYNTAX  EkiOnOff
	MAX-ACCESS read-only
	STATUS current
	DESCRIPTION
        "
        Line Optical Tx Temp Regul Failed 
        :This OID indicates a failure on 
        the TEC module  <Help>  This alarm 
        indicates if the TEC of the line 
        transceiver is in fail condition 
        <Condtype> TEC_FAULT_1 <Probcause> 
        transmitterFailure (56) <Alarmtype> 
        equipmentAlarm (5) <Polarity> (2) 
        "
	::= { pm1004mAlmlineXfp1AlarmsEntry 16 }


pm1004mAlmWavelengthUnlockedPortn OBJECT-TYPE
	SYNTAX  EkiOnOff
	MAX-ACCESS read-only
	STATUS current
	DESCRIPTION
        "
        Line Optical Tx Wavelength Unlocked 
        :This OID indicates that the wavelength 
        error is exceeding the manufacturer 
        tolerance  <Help>  This alarm indicates 
        if the wavelenght of the line transceiver 
        is locked <Condtype> WAVELENGTH_UNLOCKED_1 
        <Probcause> transmitterFailure
         (56) <Alarmtype> equipmentAlarm 
        (5) <Polarity> (2) 
        "
	::= { pm1004mAlmlineXfp1AlarmsEntry 15 }


pm1004mAlmTxNrPortn OBJECT-TYPE
	SYNTAX  EkiOnOff
	MAX-ACCESS read-only
	STATUS current
	DESCRIPTION
        "
        Line Optical Tx Not Ready :This 
        OID indicates a condition has arisen 
        leading to invalid data on the
         transmitting side  <Help>  This 
        alarm indicates if the Tx part
         of the line transceiver is ready 
        <Condtype> TX_NR_1 <Probcause>
         transmitterFailure (56) <Alarmtype> 
        equipmentAlarm (5) <Polarity> (2) 
        "
	::= { pm1004mAlmlineXfp1AlarmsEntry 9 }


pm1004mAlmTxFaultPortn OBJECT-TYPE
	SYNTAX  EkiOnOff
	MAX-ACCESS read-only
	STATUS current
	DESCRIPTION
        "
        Line Optical Tx Failure :This
         OID indicates a fault condition 
        on the laser detected by the safety 
        syste  <Help>  This alarm indicates 
        if the laser of the line transceiver 
        is in fail condition <Condtype> 
        TX_FAULT_1 <Probcause> transmitterFailure 
        (56) <Alarmtype> equipmentAlarm 
        (5) <Polarity> (2) 
        "
	::= { pm1004mAlmlineXfp1AlarmsEntry 8 }


pm1004mAlmTxCdrNotLockedPortn OBJECT-TYPE
	SYNTAX  EkiOnOff
	MAX-ACCESS read-only
	STATUS current
	DESCRIPTION
        "
        Line Optical Tx CDR Unlocked :This 
        OID indicates a loss of lock on 
        the transmitting side CDR has been 
        detected.  <Help>  This alarm indicates 
        if the Tx CDR is locked in the
         line transceiver <Condtype> TX_CDR_NOT_LOCKED1_1 
        <Probcause> transmitterFailure
         (56) <Alarmtype> equipmentAlarm 
        (5) <Polarity> (2) 
        "
	::= { pm1004mAlmlineXfp1AlarmsEntry 7 }


pm1004mAlmRxNrPortn OBJECT-TYPE
	SYNTAX  EkiOnOff
	MAX-ACCESS read-only
	STATUS current
	DESCRIPTION
        "
        Line Optical Rx Not Ready :This 
        OID indicates that a condition
         has arisen leading to invalid
         data on the receiving side.  <Help> 
         This alarm indicates if the Rx 
        part of the line transceiver is 
        ready <Condtype> RX_NR_1 <Probcause> 
        receiveFailure (41) <Alarmtype> 
        equipmentAlarm (5) <Polarity> (2) 
        "
	::= { pm1004mAlmlineXfp1AlarmsEntry 6 }


pm1004mAlmRxCdrNotLockedPortn OBJECT-TYPE
	SYNTAX  EkiOnOff
	MAX-ACCESS read-only
	STATUS current
	DESCRIPTION
        "
        Line Optical Rx CDR Unlocked :This 
        OID indicates that a loss of lock 
        on the receiving side CDR has been 
        detected  <Help>  This alarm indicates 
        if the Rx CDR is locked in the
         line transceiver <Condtype> RX_CDR_NOT_LOCKED1_1 
        <Probcause> receiveFailure (41) 
        <Alarmtype> equipmentAlarm (5)
         <Polarity> (2) 
        "
	::= { pm1004mAlmlineXfp1AlarmsEntry 4 }


pm1004mAlmModNrPortn OBJECT-TYPE
	SYNTAX  EkiOnOff
	MAX-ACCESS read-only
	STATUS current
	DESCRIPTION
        "
        Line Optical Module Not Ready
         :This OID indicates that the module 
        is unable to determine correct
         data.  <Help>  This alarm indicates 
        if the line transceiver is ready 
        <Condtype> MOD_NR_1 <Probcause> 
        receiveFailure (41) <Alarmtype> 
        equipmentAlarm (5) <Polarity> (2) 
        "
	::= { pm1004mAlmlineXfp1AlarmsEntry 3 }


--- *********************************************************
---     TABLE for the pm1004mAlmlineXfp1SupplyAlarm articles
--- *********************************************************

pm1004mAlmlineXfp1SupplyAlarmTable OBJECT-TYPE
	SYNTAX  SEQUENCE OF Pm1004mAlmlineXfp1SupplyAlarmEntry
	MAX-ACCESS not-accessible
	STATUS current
	DESCRIPTION
        "
        List of pm1004mAlmlineXfp1SupplyAlarm 
        Article
        "
	::= { pm1004mAlmLineUrg 212 }


pm1004mAlmlineXfp1SupplyAlarmEntry OBJECT-TYPE
	SYNTAX Pm1004mAlmlineXfp1SupplyAlarmEntry
	MAX-ACCESS not-accessible
	STATUS current
	DESCRIPTION
        "
        Row definition for the pm1004mAlmlineXfp1SupplyAlarm 
        table
        "
	INDEX   { pm1004mAlmlineXfp1SupplyAlarmIndex }
	::= { pm1004mAlmlineXfp1SupplyAlarmTable 1 }


Pm1004mAlmlineXfp1SupplyAlarmEntry ::=
	SEQUENCE {
	pm1004mAlmlineXfp1SupplyAlarmIndex
		INTEGER,
	pm1004mAlmVcc5HighWarningPortn
		EkiOnOff,
	pm1004mAlmVcc5LowWarningPortn
		EkiOnOff,
	pm1004mAlmVcc3HighWarningPortn
		EkiOnOff,
	pm1004mAlmVcc3LowWarningPortn
		EkiOnOff,
	pm1004mAlmVcc2HighWarningPortn
		EkiOnOff,
	pm1004mAlmVcc2LowWarningPortn
		EkiOnOff,
	pm1004mAlmVee5HighWarningPortn
		EkiOnOff,
	pm1004mAlmVee5LowWarningPortn
		EkiOnOff,
	pm1004mAlmVcc5HighAlarmPortn
		EkiOnOff,
	pm1004mAlmVcc5LowAlarmPortn
		EkiOnOff,
	pm1004mAlmVcc3HighAlarmPortn
		EkiOnOff,
	pm1004mAlmVcc3LowAlarmPortn
		EkiOnOff,
	pm1004mAlmVcc2HighAlarmPortn
		EkiOnOff,
	pm1004mAlmVcc2LowAlarmPortn
		EkiOnOff,
	pm1004mAlmVee5HighAlarmPortn
		EkiOnOff,
	pm1004mAlmVee5LowAlarmPortn
		EkiOnOff
	}


pm1004mAlmlineXfp1SupplyAlarmIndex OBJECT-TYPE
	SYNTAX  INTEGER(0..128)
	MAX-ACCESS  read-only
	STATUS current
	DESCRIPTION
        "
        Index definition for the pm1004mAlmlineXfp1SupplyAlarm 
        table
        "
	::= { pm1004mAlmlineXfp1SupplyAlarmEntry 1 }


pm1004mAlmVcc5HighWarningPortn OBJECT-TYPE
	SYNTAX  EkiOnOff
	MAX-ACCESS read-only
	STATUS current
	DESCRIPTION
        "
        VCC5 Power Supply High Warning 
        :Warning indicating the XFP/OTX 
        VCC5 power supply is higher than 
        the threshold written in the EEPROM 
        <Condtype> VCC5_HIGH_WARNING_1
         <Probcause> powerProblem (36)
         <Alarmtype> equipmentAlarm (5) 
        <Polarity> (2) 
        "
	::= { pm1004mAlmlineXfp1SupplyAlarmEntry 17 }


pm1004mAlmVcc5LowWarningPortn OBJECT-TYPE
	SYNTAX  EkiOnOff
	MAX-ACCESS read-only
	STATUS current
	DESCRIPTION
        "
        VCC5 Power Supply Low Warning
         :Warning indicating the XFP/OTX 
        VCC5 power supply is lower than 
        the threshold written in the EEPROM 
        <Condtype> VCC5_LOW_WARNING_1 <Probcause> 
        powerProblem (36) <Alarmtype> equipmentAlarm 
        (5) <Polarity> (2) 
        "
	::= { pm1004mAlmlineXfp1SupplyAlarmEntry 16 }


pm1004mAlmVcc3HighWarningPortn OBJECT-TYPE
	SYNTAX  EkiOnOff
	MAX-ACCESS read-only
	STATUS current
	DESCRIPTION
        "
        VCC3 Power Supply High Warning 
        :Warning indicating the XFP/OTX 
        VCC3 power supply is higher than 
        the threshold written in the EEPROM 
        <Condtype> VCC3_HIGH_WARNING_1
         <Probcause> powerProblem (36)
         <Alarmtype> equipmentAlarm (5) 
        <Polarity> (2) 
        "
	::= { pm1004mAlmlineXfp1SupplyAlarmEntry 15 }


pm1004mAlmVcc3LowWarningPortn OBJECT-TYPE
	SYNTAX  EkiOnOff
	MAX-ACCESS read-only
	STATUS current
	DESCRIPTION
        "
        VCC3 Power Supply Low Warning
         :Warning indicating the XFP/OTX 
        VCC3 power supply is lower than 
        the threshold written in the EEPROM 
        <Condtype> VCC3_LOW_WARNING_1 <Probcause> 
        powerProblem (36) <Alarmtype> equipmentAlarm 
        (5) <Polarity> (2) 
        "
	::= { pm1004mAlmlineXfp1SupplyAlarmEntry 14 }


pm1004mAlmVcc2HighWarningPortn OBJECT-TYPE
	SYNTAX  EkiOnOff
	MAX-ACCESS read-only
	STATUS current
	DESCRIPTION
        "
        VCC2 Power Supply High Warning 
        :Warning indicating the XFP/OTX 
        VCC2 power supply is higher than 
        the threshold written in the EEPROM 
        <Condtype> VCC2_HIGH_WARNING_1
         <Probcause> powerProblem (36)
         <Alarmtype> equipmentAlarm (5) 
        <Polarity> (2) 
        "
	::= { pm1004mAlmlineXfp1SupplyAlarmEntry 13 }


pm1004mAlmVcc2LowWarningPortn OBJECT-TYPE
	SYNTAX  EkiOnOff
	MAX-ACCESS read-only
	STATUS current
	DESCRIPTION
        "
        VCC2 Power Supply Low Warning
         :Warning indicating the XFP/OTX 
        VCC2 power supply is lower than 
        the threshold written in the EEPROM 
        <Condtype> VCC2_LOW_WARNING_1 <Probcause> 
        powerProblem (36) <Alarmtype> equipmentAlarm 
        (5) <Polarity> (2) 
        "
	::= { pm1004mAlmlineXfp1SupplyAlarmEntry 12 }


pm1004mAlmVee5HighWarningPortn OBJECT-TYPE
	SYNTAX  EkiOnOff
	MAX-ACCESS read-only
	STATUS current
	DESCRIPTION
        "
        VEE5 Power Supply High Warning 
        :Warning indicating the XFP/OTX 
        VEE5 power supply is higher than 
        the threshold written in the EEPROM 
        <Condtype> VEE5_HIGH_WARNING_1
         <Probcause> powerProblem (36)
         <Alarmtype> equipmentAlarm (5) 
        <Polarity> (2) 
        "
	::= { pm1004mAlmlineXfp1SupplyAlarmEntry 11 }


pm1004mAlmVee5LowWarningPortn OBJECT-TYPE
	SYNTAX  EkiOnOff
	MAX-ACCESS read-only
	STATUS current
	DESCRIPTION
        "
        VEE5 Power Supply Low Warning
         :Warning indicating the XFP/OTX 
        VEE5 power supply is lower than 
        the threshold written in the EEPROM 
        <Condtype> VEE5_LOW_WARNING_1 <Probcause> 
        powerProblem (36) <Alarmtype> equipmentAlarm 
        (5) <Polarity> (2) 
        "
	::= { pm1004mAlmlineXfp1SupplyAlarmEntry 10 }


pm1004mAlmVcc5HighAlarmPortn OBJECT-TYPE
	SYNTAX  EkiOnOff
	MAX-ACCESS read-only
	STATUS current
	DESCRIPTION
        "
        VCC5 Power Supply High :Alarm
         indicating the XFP/OTX VCC5 power 
        supply is higher than the threshold 
        written in the EEPROM <Condtype> 
        VCC5_HIGH_ALARM_1 <Probcause> powerProblem 
        (36) <Alarmtype> equipmentAlarm 
        (5) <Polarity> (2) 
        "
	::= { pm1004mAlmlineXfp1SupplyAlarmEntry 9 }


pm1004mAlmVcc5LowAlarmPortn OBJECT-TYPE
	SYNTAX  EkiOnOff
	MAX-ACCESS read-only
	STATUS current
	DESCRIPTION
        "
        VCC5 Power Supply Low :Alarm indicating 
        the XFP/OTX VCC5 power supply is 
        lower than the threshold written 
        in the EEPROM <Condtype> VCC5_LOW_ALARM_1 
        <Probcause> powerProblem (36) <Alarmtype> 
        equipmentAlarm (5) <Polarity> (2) 
        "
	::= { pm1004mAlmlineXfp1SupplyAlarmEntry 8 }


pm1004mAlmVcc3HighAlarmPortn OBJECT-TYPE
	SYNTAX  EkiOnOff
	MAX-ACCESS read-only
	STATUS current
	DESCRIPTION
        "
        VCC3 Power Supply High :Alarm
         indicating the XFP/OTX VCC3 power 
        supply is higher than the threshold 
        written in the EEPROM <Condtype> 
        VCC3_HIGH_ALARM_1 <Probcause> powerProblem 
        (36) <Alarmtype> equipmentAlarm 
        (5) <Polarity> (2) 
        "
	::= { pm1004mAlmlineXfp1SupplyAlarmEntry 7 }


pm1004mAlmVcc3LowAlarmPortn OBJECT-TYPE
	SYNTAX  EkiOnOff
	MAX-ACCESS read-only
	STATUS current
	DESCRIPTION
        "
        VCC3 Power Supply Low :Alarm indicating 
        the XFP/OTX VCC3 power supply is 
        lower than the threshold written 
        in the EEPROM <Condtype> VCC3_LOW_ALARM_1 
        <Probcause> powerProblem (36) <Alarmtype> 
        equipmentAlarm (5) <Polarity> (2) 
        "
	::= { pm1004mAlmlineXfp1SupplyAlarmEntry 6 }


pm1004mAlmVcc2HighAlarmPortn OBJECT-TYPE
	SYNTAX  EkiOnOff
	MAX-ACCESS read-only
	STATUS current
	DESCRIPTION
        "
        VCC2 Power Supply High :Alarm
         indicating the XFP/OTX VCC2 power 
        supply is higher than the threshold 
        written in the EEPROM <Condtype> 
        VCC2_HIGH_ALARM_1 <Probcause> powerProblem 
        (36) <Alarmtype> equipmentAlarm 
        (5) <Polarity> (2) 
        "
	::= { pm1004mAlmlineXfp1SupplyAlarmEntry 5 }


pm1004mAlmVcc2LowAlarmPortn OBJECT-TYPE
	SYNTAX  EkiOnOff
	MAX-ACCESS read-only
	STATUS current
	DESCRIPTION
        "
        VCC2 Power Supply Low :Alarm indicating 
        the XFP/OTX VCC2 power supply is 
        lower than the threshold written 
        in the EEPROM <Condtype> VCC2_LOW_ALARM_1 
        <Probcause> powerProblem (36) <Alarmtype> 
        equipmentAlarm (5) <Polarity> (2) 
        "
	::= { pm1004mAlmlineXfp1SupplyAlarmEntry 4 }


pm1004mAlmVee5HighAlarmPortn OBJECT-TYPE
	SYNTAX  EkiOnOff
	MAX-ACCESS read-only
	STATUS current
	DESCRIPTION
        "
        VEE5 Power Supply High :Alarm
         indicating the XFP/OTX VEE5 power 
        supply is higher than the threshold 
        written in the EEPROM <Condtype> 
        VEE5_HIGH_ALARM_1 <Probcause> powerProblem 
        (36) <Alarmtype> equipmentAlarm 
        (5) <Polarity> (2) 
        "
	::= { pm1004mAlmlineXfp1SupplyAlarmEntry 3 }


pm1004mAlmVee5LowAlarmPortn OBJECT-TYPE
	SYNTAX  EkiOnOff
	MAX-ACCESS read-only
	STATUS current
	DESCRIPTION
        "
        VEE5 Power Supply Low :Alarm indicating 
        the XFP/OTX VEE5 power supply is 
        lower than the threshold written 
        in the EEPROM <Condtype> VEE5_LOW_ALARM_1 
        <Probcause> powerProblem (36) <Alarmtype> 
        equipmentAlarm (5) <Polarity> (2) 
        "
	::= { pm1004mAlmlineXfp1SupplyAlarmEntry 2 }


--- *********************************************************
---     TABLE for the pm1004mAlmlineOtx1TlhAlarms articles
--- *********************************************************

pm1004mAlmlineOtx1TlhAlarmsTable OBJECT-TYPE
	SYNTAX  SEQUENCE OF Pm1004mAlmlineOtx1TlhAlarmsEntry
	MAX-ACCESS not-accessible
	STATUS current
	DESCRIPTION
        "
        List of pm1004mAlmlineOtx1TlhAlarms 
        Article
        "
	::= { pm1004mAlmLineUrg 224 }


pm1004mAlmlineOtx1TlhAlarmsEntry OBJECT-TYPE
	SYNTAX Pm1004mAlmlineOtx1TlhAlarmsEntry
	MAX-ACCESS not-accessible
	STATUS current
	DESCRIPTION
        "
        Row definition for the pm1004mAlmlineOtx1TlhAlarms 
        table
        "
	INDEX   { pm1004mAlmlineOtx1TlhAlarmsIndex }
	::= { pm1004mAlmlineOtx1TlhAlarmsTable 1 }


Pm1004mAlmlineOtx1TlhAlarmsEntry ::=
	SEQUENCE {
	pm1004mAlmlineOtx1TlhAlarmsIndex
		INTEGER,
	pm1004mAlmLineLaserTempHighAlaPortn
		EkiOnOff,
	pm1004mAlmLineFreqDevHighAlaPortn
		EkiOnOff,
	pm1004mAlmLineAgingHighAlaPortn
		EkiOnOff,
	pm1004mAlmLineModulatorAgingHighAlaPortn
		EkiOnOff
	}


pm1004mAlmlineOtx1TlhAlarmsIndex OBJECT-TYPE
	SYNTAX  INTEGER(0..128)
	MAX-ACCESS  read-only
	STATUS current
	DESCRIPTION
        "
        Index definition for the pm1004mAlmlineOtx1TlhAlarms 
        table
        "
	::= { pm1004mAlmlineOtx1TlhAlarmsEntry 1 }


pm1004mAlmLineLaserTempHighAlaPortn OBJECT-TYPE
	SYNTAX  EkiOnOff
	MAX-ACCESS read-only
	STATUS current
	DESCRIPTION
        "
        Line Laser Temp. High Alarm :Alarm 
        indicating the Line OTX TLH laser 
        temperature is higher than the
         threshold written in the EEPROM 
        <Condtype> LINE_LASER_TEMP_HIGH_ALA_1 
        <Probcause> temperatureUnacceptable 
        (51) <Alarmtype> equipmentAlarm 
        (5) <Polarity> (2) 
        "
	::= { pm1004mAlmlineOtx1TlhAlarmsEntry 15 }


pm1004mAlmLineFreqDevHighAlaPortn OBJECT-TYPE
	SYNTAX  EkiOnOff
	MAX-ACCESS read-only
	STATUS current
	DESCRIPTION
        "
        Line Freq. Deviation High Alarm 
        :Alarm indicating the Line OTX
         TLH frequency deviation is higher 
        than the threshold written in the 
        EEPROM <Condtype> LINE_FREQ_DEV_HIGH_ALA_1 
        <Probcause> transmitterFailure
         (56) <Alarmtype> equipmentAlarm 
        (5) <Polarity> (2) 
        "
	::= { pm1004mAlmlineOtx1TlhAlarmsEntry 13 }


pm1004mAlmLineAgingHighAlaPortn OBJECT-TYPE
	SYNTAX  EkiOnOff
	MAX-ACCESS read-only
	STATUS current
	DESCRIPTION
        "
        Line OTX TLH Aging High Alarm
         :Alarm indicating the Line OTX 
        TLH aging is higher than the threshold 
        written in the EEPROM <Condtype> 
        LINE_AGING_HIGH_ALA_1 <Probcause> 
        transmitterFailure (56) <Alarmtype> 
        equipmentAlarm (5) <Polarity> (2) 
        "
	::= { pm1004mAlmlineOtx1TlhAlarmsEntry 7 }


pm1004mAlmLineModulatorAgingHighAlaPortn OBJECT-TYPE
	SYNTAX  EkiOnOff
	MAX-ACCESS read-only
	STATUS current
	DESCRIPTION
        "
        Line Modulator Aging High Alarm 
        :Alarm indicating the Line OTX
         TLH modulator aging is higher
         than the threshold written in
         the EEPROM <Condtype> LINE_MODULATOR_AGING_HIGH_ALA_1 
        <Probcause> transmitterFailure
         (56) <Alarmtype> equipmentAlarm 
        (5) <Polarity> (2) 
        "
	::= { pm1004mAlmlineOtx1TlhAlarmsEntry 6 }


--- *********************************************************
---     TABLE for the pm1004mAlmlineOtx1TlhWarnings articles
--- *********************************************************

pm1004mAlmlineOtx1TlhWarningsTable OBJECT-TYPE
	SYNTAX  SEQUENCE OF Pm1004mAlmlineOtx1TlhWarningsEntry
	MAX-ACCESS not-accessible
	STATUS current
	DESCRIPTION
        "
        List of pm1004mAlmlineOtx1TlhWarnings 
        Article
        "
	::= { pm1004mAlmLineNurg 225 }


pm1004mAlmlineOtx1TlhWarningsEntry OBJECT-TYPE
	SYNTAX Pm1004mAlmlineOtx1TlhWarningsEntry
	MAX-ACCESS not-accessible
	STATUS current
	DESCRIPTION
        "
        Row definition for the pm1004mAlmlineOtx1TlhWarnings 
        table
        "
	INDEX   { pm1004mAlmlineOtx1TlhWarningsIndex }
	::= { pm1004mAlmlineOtx1TlhWarningsTable 1 }


Pm1004mAlmlineOtx1TlhWarningsEntry ::=
	SEQUENCE {
	pm1004mAlmlineOtx1TlhWarningsIndex
		INTEGER,
	pm1004mAlmLineLaserTempHighWarningPortn
		EkiOnOff,
	pm1004mAlmLineFreqDevHighWarningPortn
		EkiOnOff,
	pm1004mAlmLineAgingHighWarningPortn
		EkiOnOff,
	pm1004mAlmLineModulatorAgingHighWarningPortn
		EkiOnOff
	}


pm1004mAlmlineOtx1TlhWarningsIndex OBJECT-TYPE
	SYNTAX  INTEGER(0..128)
	MAX-ACCESS  read-only
	STATUS current
	DESCRIPTION
        "
        Index definition for the pm1004mAlmlineOtx1TlhWarnings 
        table
        "
	::= { pm1004mAlmlineOtx1TlhWarningsEntry 1 }


pm1004mAlmLineLaserTempHighWarningPortn OBJECT-TYPE
	SYNTAX  EkiOnOff
	MAX-ACCESS read-only
	STATUS current
	DESCRIPTION
        "
        Line Laser Temp. High Warning
         :Warning indicating the Line OTX 
        TLH laser temperature is higher 
        than the threshold written in the 
        EEPROM <Condtype> LINE_LASER_TEMP_HIGH_WARNING_1 
        <Probcause> temperatureUnacceptable 
        (51) <Alarmtype> equipmentAlarm 
        (5) <Polarity> (2) 
        "
	::= { pm1004mAlmlineOtx1TlhWarningsEntry 15 }


pm1004mAlmLineFreqDevHighWarningPortn OBJECT-TYPE
	SYNTAX  EkiOnOff
	MAX-ACCESS read-only
	STATUS current
	DESCRIPTION
        "
        Line Freq. Deviation High Warning 
        :Warning indicating the Line OTX 
        TLH frequency deviation is higher 
        than the threshold written in the 
        EEPROM <Condtype> LINE_FREQ_DEV_HIGH_WARNING_1 
        <Probcause> transmitterFailure
         (56) <Alarmtype> equipmentAlarm 
        (5) <Polarity> (2) 
        "
	::= { pm1004mAlmlineOtx1TlhWarningsEntry 13 }


pm1004mAlmLineAgingHighWarningPortn OBJECT-TYPE
	SYNTAX  EkiOnOff
	MAX-ACCESS read-only
	STATUS current
	DESCRIPTION
        "
        Line OTX TLH Aging High Warning 
        :Warning indicating the Line OTX 
        TLH aging is higher than the threshold 
        written in the EEPROM <Condtype> 
        LINE_AGING_HIGH_WARNING_1 <Probcause> 
        transmitterFailure (56) <Alarmtype> 
        equipmentAlarm (5) <Polarity> (2) 
        "
	::= { pm1004mAlmlineOtx1TlhWarningsEntry 7 }


pm1004mAlmLineModulatorAgingHighWarningPortn OBJECT-TYPE
	SYNTAX  EkiOnOff
	MAX-ACCESS read-only
	STATUS current
	DESCRIPTION
        "
        Line Modulator Aging High Warning 
        :Warning indicating the Line OTX 
        TLH modulator aging is higher than 
        the threshold written in the EEPROM 
        <Condtype> LINE_MODULATOR_AGING_HIGH_WARNING_1 
        <Probcause> transmitterFailure
         (56) <Alarmtype> equipmentAlarm 
        (5) <Polarity> (2) 
        "
	::= { pm1004mAlmlineOtx1TlhWarningsEntry 6 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm1004mCtrlconfMgnt1 OBJECT IDENTIFIER ::= { pm1004mCtrlOther 1 }




pm1004mCtrlConf2Clear1 OBJECT-TYPE
	  SYNTAX EkiOnOff
	  MAX-ACCESS read-write
	  STATUS current
	  DESCRIPTION
        "
        Clear Configuration Tables :This 
        OID clears the configuration tables 
        from configuration2 in the flash. 
         <Help>  This control restores
         the default configuration of the 
        module
        "
	  ::= { pm1004mCtrlconfMgnt1 14 }



pm1004mCtrlConf2Flash1 OBJECT-TYPE
	  SYNTAX EkiOnOff
	  MAX-ACCESS read-write
	  STATUS current
	  DESCRIPTION
        "
        Write Configuration Tables :This 
        OID saves the current configuration 
        of the PM as configuration2 in
         the flash.  <Help>  This control 
        saves the customer configuration 
        on the module
        "
	  ::= { pm1004mCtrlconfMgnt1 10 }



pm1004mCtrlConf2Load1 OBJECT-TYPE
	  SYNTAX EkiOnOff
	  MAX-ACCESS read-write
	  STATUS current
	  DESCRIPTION
        "
        Load Configuration Tables Set
         Nb 2 :When set this OID enables 
        loading from flash configuration2 
        into the PM.
        "
	  ::= { pm1004mCtrlconfMgnt1 2 }



pm1004mCtrlConf1Load1 OBJECT-TYPE
	  SYNTAX EkiOnOff
	  MAX-ACCESS read-write
	  STATUS current
	  DESCRIPTION
        "
        Load Configuration Tables Set
         Nb 1 :When set this OID enables 
        loading from flash configuration1 
        into the PM.
        "
	  ::= { pm1004mCtrlconfMgnt1 1 }



--- *****************************************************
---     LEAF for the synth4 article
--- *****************************************************
pm1004mCtrlsynth4 OBJECT IDENTIFIER ::= { pm1004mCtrlOther 4 }




pm1004mCtrlCorrelatOff OBJECT-TYPE
	  SYNTAX EkiOnOff
	  MAX-ACCESS read-write
	  STATUS current
	  DESCRIPTION
        "
        Disable Alarm Correlation :This 
        OID disables the alarm correlation 
        in the PM.
        "
	  ::= { pm1004mCtrlsynth4 2 }



pm1004mCtrlCorrelatOn OBJECT-TYPE
	  SYNTAX EkiOnOff
	  MAX-ACCESS read-write
	  STATUS current
	  DESCRIPTION
        "
        Enable Alarm Correlation :This 
        OID enables the alarm correlation 
        in the PM.
        "
	  ::= { pm1004mCtrlsynth4 1 }



--- *****************************************************
---     LEAF for the swMgnt article
--- *****************************************************
pm1004mCtrlswMgnt OBJECT IDENTIFIER ::= { pm1004mCtrlOther 5 }




pm1004mCtrlLoadSwBank2 OBJECT-TYPE
	  SYNTAX EkiOnOff
	  MAX-ACCESS read-write
	  STATUS current
	  DESCRIPTION
        "
        Set Software Nb 2 As Active :This 
        OID, when set, loads the SW from 
        bank2 into the PM. It must be followed 
        by a reset.  <Help>  This controls 
        selects the second SW bank as the 
        active bank for the next module 
        reset
        "
	  ::= { pm1004mCtrlswMgnt 6 }



pm1004mCtrlLoadSwBank1 OBJECT-TYPE
	  SYNTAX EkiOnOff
	  MAX-ACCESS read-write
	  STATUS current
	  DESCRIPTION
        "
        Set Software Nb 1 As Active :This 
        OID, when set, loads the SW from 
        bank1 into the PM. It must be followed 
        by a reset.  <Help>  This controls 
        selects the first SW bank as the 
        active bank for the next module 
        reset
        "
	  ::= { pm1004mCtrlswMgnt 5 }



pm1004mCtrlWarmReset OBJECT-TYPE
	  SYNTAX EkiOnOff
	  MAX-ACCESS read-write
	  STATUS current
	  DESCRIPTION
        "
        PM Warm Reset :This OID, when
         set, causes a warm reset of the 
        PM. This reset is not traffic affecting, 
        and the configuration of PM remains 
        unchanged.  <Help>  This control 
        initiates a warm reset of the module. 
        "
	  ::= { pm1004mCtrlswMgnt 3 }



pm1004mCtrlColdReset OBJECT-TYPE
	  SYNTAX EkiOnOff
	  MAX-ACCESS read-write
	  STATUS current
	  DESCRIPTION
        "
        PM Cold Reset :This OID, when
         set, causes a cold reset of the 
        PM. This reset is traffic affecting, 
        and the configuration of PM is
         reloaded on start-up.  <Help>
          This control initiates a cold 
        reset of the module. 
        "
	  ::= { pm1004mCtrlswMgnt 2 }



--- *****************************************************
---     LEAF for the gwMgnt article
--- *****************************************************
pm1004mCtrlgwMgnt OBJECT IDENTIFIER ::= { pm1004mCtrlOther 6 }




pm1004mCtrlLoadGwBank4 OBJECT-TYPE
	  SYNTAX EkiOnOff
	  MAX-ACCESS read-write
	  STATUS current
	  DESCRIPTION
        "
        Set Gateware Nb 4 As Active :This 
        OID, when set, loads the GW from 
        bank4 (Flash) into the PM. It is 
        followed by an automatic gateware 
        cold reset.
        "
	  ::= { pm1004mCtrlgwMgnt 8 }



pm1004mCtrlLoadGwBank3 OBJECT-TYPE
	  SYNTAX EkiOnOff
	  MAX-ACCESS read-write
	  STATUS current
	  DESCRIPTION
        "
        Set Gateware Nb 3 As Active :This 
        OID, when set, loads the GW from 
        bank3 (Flash) into the PM. It is 
        followed by an automatic gateware 
        cold reset.  <Help>  This controls 
        initiates a cold reset of the module 
        and select the third GW bank as 
        the active bank
        "
	  ::= { pm1004mCtrlgwMgnt 7 }



pm1004mCtrlLoadGwBank2 OBJECT-TYPE
	  SYNTAX EkiOnOff
	  MAX-ACCESS read-write
	  STATUS current
	  DESCRIPTION
        "
        Set Gateware Nb 2 As Active :This 
        OID, when set, loads the GW from 
        bank2 (Flash) into the PM. It is 
        followed by an automatic gateware 
        cold reset.
        "
	  ::= { pm1004mCtrlgwMgnt 6 }



pm1004mCtrlLoadGwBank1 OBJECT-TYPE
	  SYNTAX EkiOnOff
	  MAX-ACCESS read-write
	  STATUS current
	  DESCRIPTION
        "
        Set Gateware Nb 1 As Active :This 
        OID, when set, loads the GW from 
        bank1 (Flash) into the PM. It is 
        followed by an automatic gateware 
        cold reset.  <Help>  This controls 
        initiates a cold reset of the module 
        and select the first GW bank as 
        the active bank
        "
	  ::= { pm1004mCtrlgwMgnt 5 }



pm1004mCtrlCurrentGwReset OBJECT-TYPE
	  SYNTAX EkiOnOff
	  MAX-ACCESS read-write
	  STATUS current
	  DESCRIPTION
        "
        Active Gateware Reset :This OID, 
        when set, resets the active gateware. 
        It is traffic affecting.
        "
	  ::= { pm1004mCtrlgwMgnt 1 }



--- *********************************************************
---     TABLE for the pm1004mCtrlaccessLoop articles
--- *********************************************************

pm1004mCtrlaccessLoopTable OBJECT-TYPE
	SYNTAX  SEQUENCE OF Pm1004mCtrlaccessLoopEntry
	MAX-ACCESS not-accessible
	STATUS current
	DESCRIPTION
        "
        List of pm1004mCtrlaccessLoop
         Article
        "
	::= { pm1004mCtrlClient 16 }


pm1004mCtrlaccessLoopEntry OBJECT-TYPE
	SYNTAX Pm1004mCtrlaccessLoopEntry
	MAX-ACCESS not-accessible
	STATUS current
	DESCRIPTION
        "
        Row definition for the pm1004mCtrlaccessLoop 
        table
        "
	INDEX   { pm1004mCtrlaccessLoopIndex }
	::= { pm1004mCtrlaccessLoopTable 1 }


Pm1004mCtrlaccessLoopEntry ::=
	SEQUENCE {
	pm1004mCtrlaccessLoopIndex
		INTEGER,
	pm1004mCtrlaccessLoopPortn
		EkiState
	}


pm1004mCtrlaccessLoopIndex OBJECT-TYPE
	SYNTAX  INTEGER(0..128)
	MAX-ACCESS  read-only
	STATUS current
	DESCRIPTION
        "
        Index definition for the pm1004mCtrlaccessLoop 
        table
        "
	::= { pm1004mCtrlaccessLoopEntry 1 }


pm1004mCtrlaccessLoopPortn OBJECT-TYPE
	SYNTAX  EkiState
	MAX-ACCESS read-write
	STATUS current
	DESCRIPTION
        "
        Client Facility Loopback :This 
        OID operates a Client Facility
         Loopback, looping client input 
        signal on the client output port. 
        The loop is located on the client 
        transceiver  <Help> This maintenance 
        parameter operates a Client Facility 
        Loopback, looping client input
         signal on the client output port. 
        The loop is located on the client 
        transceiver
        "
	::= { pm1004mCtrlaccessLoopEntry 2 }


--- *********************************************************
---     TABLE for the pm1004mCtrlportOosMode articles
--- *********************************************************

pm1004mCtrlportOosModeTable OBJECT-TYPE
	SYNTAX  SEQUENCE OF Pm1004mCtrlportOosModeEntry
	MAX-ACCESS not-accessible
	STATUS current
	DESCRIPTION
        "
        List of pm1004mCtrlportOosMode 
        Article
        "
	::= { pm1004mCtrlClient 18 }


pm1004mCtrlportOosModeEntry OBJECT-TYPE
	SYNTAX Pm1004mCtrlportOosModeEntry
	MAX-ACCESS not-accessible
	STATUS current
	DESCRIPTION
        "
        Row definition for the pm1004mCtrlportOosMode 
        table
        "
	INDEX   { pm1004mCtrlportOosModeIndex }
	::= { pm1004mCtrlportOosModeTable 1 }


Pm1004mCtrlportOosModeEntry ::=
	SEQUENCE {
	pm1004mCtrlportOosModeIndex
		INTEGER,
	pm1004mCtrlportOosModePortn
		EkiState
	}


pm1004mCtrlportOosModeIndex OBJECT-TYPE
	SYNTAX  INTEGER(0..128)
	MAX-ACCESS  read-only
	STATUS current
	DESCRIPTION
        "
        Index definition for the pm1004mCtrlportOosMode 
        table
        "
	::= { pm1004mCtrlportOosModeEntry 1 }


pm1004mCtrlportOosModePortn OBJECT-TYPE
	SYNTAX  EkiState
	MAX-ACCESS read-write
	STATUS current
	DESCRIPTION
        "
        Client Port Out Of Service :This 
        OID sets the client port Out Of 
        Service  <Help>  This controls
         defines the service state of the 
        client port
        "
	::= { pm1004mCtrlportOosModeEntry 2 }


--- *********************************************************
---     TABLE for the pm1004mCtrlsfpOnCtrl articles
--- *********************************************************

pm1004mCtrlsfpOnCtrlTable OBJECT-TYPE
	SYNTAX  SEQUENCE OF Pm1004mCtrlsfpOnCtrlEntry
	MAX-ACCESS not-accessible
	STATUS current
	DESCRIPTION
        "
        List of pm1004mCtrlsfpOnCtrl Article
        "
	::= { pm1004mCtrlClient 19 }


pm1004mCtrlsfpOnCtrlEntry OBJECT-TYPE
	SYNTAX Pm1004mCtrlsfpOnCtrlEntry
	MAX-ACCESS not-accessible
	STATUS current
	DESCRIPTION
        "
        Row definition for the pm1004mCtrlsfpOnCtrl 
        table
        "
	INDEX   { pm1004mCtrlsfpOnCtrlIndex }
	::= { pm1004mCtrlsfpOnCtrlTable 1 }


Pm1004mCtrlsfpOnCtrlEntry ::=
	SEQUENCE {
	pm1004mCtrlsfpOnCtrlIndex
		INTEGER,
	pm1004mCtrlsfpOnCtrlPortn
		EkiState
	}


pm1004mCtrlsfpOnCtrlIndex OBJECT-TYPE
	SYNTAX  INTEGER(0..128)
	MAX-ACCESS  read-only
	STATUS current
	DESCRIPTION
        "
        Index definition for the pm1004mCtrlsfpOnCtrl 
        table
        "
	::= { pm1004mCtrlsfpOnCtrlEntry 1 }


pm1004mCtrlsfpOnCtrlPortn OBJECT-TYPE
	SYNTAX  EkiState
	MAX-ACCESS read-write
	STATUS current
	DESCRIPTION
        "
        Client SFP Optical Laser ON :This 
        OID switches on the SFP.
        "
	::= { pm1004mCtrlsfpOnCtrlEntry 2 }


--- *********************************************************
---     TABLE for the pm1004mCtrlsfpOffCtrl articles
--- *********************************************************

pm1004mCtrlsfpOffCtrlTable OBJECT-TYPE
	SYNTAX  SEQUENCE OF Pm1004mCtrlsfpOffCtrlEntry
	MAX-ACCESS not-accessible
	STATUS current
	DESCRIPTION
        "
        List of pm1004mCtrlsfpOffCtrl
         Article
        "
	::= { pm1004mCtrlClient 20 }


pm1004mCtrlsfpOffCtrlEntry OBJECT-TYPE
	SYNTAX Pm1004mCtrlsfpOffCtrlEntry
	MAX-ACCESS not-accessible
	STATUS current
	DESCRIPTION
        "
        Row definition for the pm1004mCtrlsfpOffCtrl 
        table
        "
	INDEX   { pm1004mCtrlsfpOffCtrlIndex }
	::= { pm1004mCtrlsfpOffCtrlTable 1 }


Pm1004mCtrlsfpOffCtrlEntry ::=
	SEQUENCE {
	pm1004mCtrlsfpOffCtrlIndex
		INTEGER,
	pm1004mCtrlsfpOffCtrlPortn
		EkiState
	}


pm1004mCtrlsfpOffCtrlIndex OBJECT-TYPE
	SYNTAX  INTEGER(0..128)
	MAX-ACCESS  read-only
	STATUS current
	DESCRIPTION
        "
        Index definition for the pm1004mCtrlsfpOffCtrl 
        table
        "
	::= { pm1004mCtrlsfpOffCtrlEntry 1 }


pm1004mCtrlsfpOffCtrlPortn OBJECT-TYPE
	SYNTAX  EkiState
	MAX-ACCESS read-write
	STATUS current
	DESCRIPTION
        "
        Client SFP Laser Shutdown :This 
        OID switches off the SFP.  <Help> 
         This control defines the laser 
        state of the client transceiver
        "
	::= { pm1004mCtrlsfpOffCtrlEntry 2 }


--- *********************************************************
---     TABLE for the pm1004mCtrlcsfUpIns articles
--- *********************************************************

pm1004mCtrlcsfUpInsTable OBJECT-TYPE
	SYNTAX  SEQUENCE OF Pm1004mCtrlcsfUpInsEntry
	MAX-ACCESS not-accessible
	STATUS current
	DESCRIPTION
        "
        List of pm1004mCtrlcsfUpIns Article
        "
	::= { pm1004mCtrlClient 21 }


pm1004mCtrlcsfUpInsEntry OBJECT-TYPE
	SYNTAX Pm1004mCtrlcsfUpInsEntry
	MAX-ACCESS not-accessible
	STATUS current
	DESCRIPTION
        "
        Row definition for the pm1004mCtrlcsfUpIns 
        table
        "
	INDEX   { pm1004mCtrlcsfUpInsIndex }
	::= { pm1004mCtrlcsfUpInsTable 1 }


Pm1004mCtrlcsfUpInsEntry ::=
	SEQUENCE {
	pm1004mCtrlcsfUpInsIndex
		INTEGER,
	pm1004mCtrlcsfUpInsPortn
		EkiState
	}


pm1004mCtrlcsfUpInsIndex OBJECT-TYPE
	SYNTAX  INTEGER(0..128)
	MAX-ACCESS  read-only
	STATUS current
	DESCRIPTION
        "
        Index definition for the pm1004mCtrlcsfUpIns 
        table
        "
	::= { pm1004mCtrlcsfUpInsEntry 1 }


pm1004mCtrlcsfUpInsPortn OBJECT-TYPE
	SYNTAX  EkiState
	MAX-ACCESS read-write
	STATUS current
	DESCRIPTION
        "
        Client Signal Fail Insertion :This 
        OID, when set, inserts  a client 
        signal fail in the upstream client 
        Port.  <Help>  This control inserts 
        a Client Signal Fail for the client 
        port
        "
	::= { pm1004mCtrlcsfUpInsEntry 2 }


--- *********************************************************
---     TABLE for the pm1004mCtrlcaisDwIns articles
--- *********************************************************

pm1004mCtrlcaisDwInsTable OBJECT-TYPE
	SYNTAX  SEQUENCE OF Pm1004mCtrlcaisDwInsEntry
	MAX-ACCESS not-accessible
	STATUS current
	DESCRIPTION
        "
        List of pm1004mCtrlcaisDwIns Article
        "
	::= { pm1004mCtrlClient 22 }


pm1004mCtrlcaisDwInsEntry OBJECT-TYPE
	SYNTAX Pm1004mCtrlcaisDwInsEntry
	MAX-ACCESS not-accessible
	STATUS current
	DESCRIPTION
        "
        Row definition for the pm1004mCtrlcaisDwIns 
        table
        "
	INDEX   { pm1004mCtrlcaisDwInsIndex }
	::= { pm1004mCtrlcaisDwInsTable 1 }


Pm1004mCtrlcaisDwInsEntry ::=
	SEQUENCE {
	pm1004mCtrlcaisDwInsIndex
		INTEGER,
	pm1004mCtrlcaisDwInsPortn
		EkiState
	}


pm1004mCtrlcaisDwInsIndex OBJECT-TYPE
	SYNTAX  INTEGER(0..128)
	MAX-ACCESS  read-only
	STATUS current
	DESCRIPTION
        "
        Index definition for the pm1004mCtrlcaisDwIns 
        table
        "
	::= { pm1004mCtrlcaisDwInsEntry 1 }


pm1004mCtrlcaisDwInsPortn OBJECT-TYPE
	SYNTAX  EkiState
	MAX-ACCESS read-write
	STATUS current
	DESCRIPTION
        "
        Client AIS Insertion :This OID, 
        when set, inserts a client AIS
         on the downstream client Port. 
         <Help>  This control inserts a 
        Client AIS for the client port
        "
	::= { pm1004mCtrlcaisDwInsEntry 2 }


--- *********************************************************
---     TABLE for the pm1004mCtrlclientAccessTermLoop articles
--- *********************************************************

pm1004mCtrlclientAccessTermLoopTable OBJECT-TYPE
	SYNTAX  SEQUENCE OF Pm1004mCtrlclientAccessTermLoopEntry
	MAX-ACCESS not-accessible
	STATUS current
	DESCRIPTION
        "
        List of pm1004mCtrlclientAccessTermLoop 
        Article
        "
	::= { pm1004mCtrlClient 26 }


pm1004mCtrlclientAccessTermLoopEntry OBJECT-TYPE
	SYNTAX Pm1004mCtrlclientAccessTermLoopEntry
	MAX-ACCESS not-accessible
	STATUS current
	DESCRIPTION
        "
        Row definition for the pm1004mCtrlclientAccessTermLoop 
        table
        "
	INDEX   { pm1004mCtrlclientAccessTermLoopIndex }
	::= { pm1004mCtrlclientAccessTermLoopTable 1 }


Pm1004mCtrlclientAccessTermLoopEntry ::=
	SEQUENCE {
	pm1004mCtrlclientAccessTermLoopIndex
		INTEGER,
	pm1004mCtrlclientAccessTermLoopPortn
		EkiState
	}


pm1004mCtrlclientAccessTermLoopIndex OBJECT-TYPE
	SYNTAX  INTEGER(0..128)
	MAX-ACCESS  read-only
	STATUS current
	DESCRIPTION
        "
        Index definition for the pm1004mCtrlclientAccessTermLoop 
        table
        "
	::= { pm1004mCtrlclientAccessTermLoopEntry 1 }


pm1004mCtrlclientAccessTermLoopPortn OBJECT-TYPE
	SYNTAX  EkiState
	MAX-ACCESS read-write
	STATUS current
	DESCRIPTION
        "
        Client Terminal Loopback :This 
        OID operates a Client Terminal
         Loopback, looping client input 
        signal on the client output port. 
        The loop is located on the line 
        transceiver  <Help> This maintenance 
        parameter operates a Client Terminal 
        Loopback, looping client input
         signal on the client output port. 
        The loop is located on the line 
        transceiver
        "
	::= { pm1004mCtrlclientAccessTermLoopEntry 2 }


--- *********************************************************
---     TABLE for the pm1004mCtrlresetCount15Port articles
--- *********************************************************

pm1004mCtrlresetCount15PortTable OBJECT-TYPE
	SYNTAX  SEQUENCE OF Pm1004mCtrlresetCount15PortEntry
	MAX-ACCESS not-accessible
	STATUS current
	DESCRIPTION
        "
        List of pm1004mCtrlresetCount15Port 
        Article
        "
	::= { pm1004mCtrlClient 35 }


pm1004mCtrlresetCount15PortEntry OBJECT-TYPE
	SYNTAX Pm1004mCtrlresetCount15PortEntry
	MAX-ACCESS not-accessible
	STATUS current
	DESCRIPTION
        "
        Row definition for the pm1004mCtrlresetCount15Port 
        table
        "
	INDEX   { pm1004mCtrlresetCount15PortIndex }
	::= { pm1004mCtrlresetCount15PortTable 1 }


Pm1004mCtrlresetCount15PortEntry ::=
	SEQUENCE {
	pm1004mCtrlresetCount15PortIndex
		INTEGER,
	pm1004mCtrlclientResetAllPerfCount15Portn
		EkiState
	}


pm1004mCtrlresetCount15PortIndex OBJECT-TYPE
	SYNTAX  INTEGER(0..128)
	MAX-ACCESS  read-only
	STATUS current
	DESCRIPTION
        "
        Index definition for the pm1004mCtrlresetCount15Port 
        table
        "
	::= { pm1004mCtrlresetCount15PortEntry 1 }


pm1004mCtrlclientResetAllPerfCount15Portn OBJECT-TYPE
	SYNTAX  EkiState
	MAX-ACCESS read-write
	STATUS current
	DESCRIPTION
        "
        Client 15-min Counters Reset :This 
        OID resets all the current 15-min 
        Counters on the client port
        "
	::= { pm1004mCtrlresetCount15PortEntry 2 }


--- *********************************************************
---     TABLE for the pm1004mCtrlresetCount24Port articles
--- *********************************************************

pm1004mCtrlresetCount24PortTable OBJECT-TYPE
	SYNTAX  SEQUENCE OF Pm1004mCtrlresetCount24PortEntry
	MAX-ACCESS not-accessible
	STATUS current
	DESCRIPTION
        "
        List of pm1004mCtrlresetCount24Port 
        Article
        "
	::= { pm1004mCtrlClient 36 }


pm1004mCtrlresetCount24PortEntry OBJECT-TYPE
	SYNTAX Pm1004mCtrlresetCount24PortEntry
	MAX-ACCESS not-accessible
	STATUS current
	DESCRIPTION
        "
        Row definition for the pm1004mCtrlresetCount24Port 
        table
        "
	INDEX   { pm1004mCtrlresetCount24PortIndex }
	::= { pm1004mCtrlresetCount24PortTable 1 }


Pm1004mCtrlresetCount24PortEntry ::=
	SEQUENCE {
	pm1004mCtrlresetCount24PortIndex
		INTEGER,
	pm1004mCtrlclientResetAllPerfCount24Portn
		EkiState
	}


pm1004mCtrlresetCount24PortIndex OBJECT-TYPE
	SYNTAX  INTEGER(0..128)
	MAX-ACCESS  read-only
	STATUS current
	DESCRIPTION
        "
        Index definition for the pm1004mCtrlresetCount24Port 
        table
        "
	::= { pm1004mCtrlresetCount24PortEntry 1 }


pm1004mCtrlclientResetAllPerfCount24Portn OBJECT-TYPE
	SYNTAX  EkiState
	MAX-ACCESS read-write
	STATUS current
	DESCRIPTION
        "
        Client 24-hours Counters Reset 
        :This OID resets all the current 
        24-hours Counters on the client 
        port
        "
	::= { pm1004mCtrlresetCount24PortEntry 2 }


--- *****************************************************
---     LEAF for the commAccessLoop article
--- *****************************************************
pm1004mCtrlcommAccessLoop OBJECT IDENTIFIER ::= { pm1004mCtrlLine 64 }




pm1004mCtrlCommAccessloop OBJECT-TYPE
	  SYNTAX EkiOnOff
	  MAX-ACCESS read-write
	  STATUS deprecated
	  DESCRIPTION
        "
        PM Full Access Loop Mode :This 
        OID, when set, puts the module
         in common access loop back, looping 
        the 10 Gb/s output signal on the 
        10 Gb/s input.
        "
	  ::= { pm1004mCtrlcommAccessLoop 1 }



--- *****************************************************
---     LEAF for the lineLoop article
--- *****************************************************
pm1004mCtrllineLoop OBJECT IDENTIFIER ::= { pm1004mCtrlLine 66 }




pm1004mCtrlLineLoop OBJECT-TYPE
	  SYNTAX EkiOnOff
	  MAX-ACCESS read-write
	  STATUS deprecated
	  DESCRIPTION
        "
        PM Line Loop Mode :This OID, when 
        set at '1' puts the module in line 
        loopback mode, looping the received 
        10 Gb/s signal on the transmit
         10 Gb/s output. The Upstream part 
        of the module is timed on the 10 
        Gb/s recovered clock in that case.
        "
	  ::= { pm1004mCtrllineLoop 1 }



--- *****************************************************
---     LEAF for the msAis article
--- *****************************************************
pm1004mCtrlmsAis OBJECT IDENTIFIER ::= { pm1004mCtrlLine 67 }




pm1004mCtrlMsAis OBJECT-TYPE
	  SYNTAX EkiOnOff
	  MAX-ACCESS read-write
	  STATUS current
	  DESCRIPTION
        "
        Insert MS-AIS/L-AIS On Line Output 
        :This OID, when set, inserts an 
        MS-AIS/L-AIS in the outgoing STM-64/OC-192 
        signal.
        "
	  ::= { pm1004mCtrlmsAis 1 }



--- *****************************************************
---     LEAF for the protMgnt article
--- *****************************************************
pm1004mCtrlProtMgnt OBJECT IDENTIFIER ::= { pm1004mCtrlLine 73 }




pm1004mCtrlLineNumber OBJECT-TYPE
	  SYNTAX Unsigned32 (0..3)
	  MAX-ACCESS read-write
	  STATUS current
	  DESCRIPTION
        "
        Active Line Number : This OID
         sets the active line number
        "
	  ::= { pm1004mCtrlProtMgnt 1 }



pm1004mCtrlProtMode OBJECT-TYPE
	  SYNTAX EkiMode
	  MAX-ACCESS read-write
	  STATUS current
	  DESCRIPTION
        "
        Line Switch Mode (Auto Or Manual) 
        :This bit selects the manual (1) 
        or automatic (0) switch method
          <Help>  This control defines
         the protection switch mode on
         the line interface
        "
	  ::= { pm1004mCtrlProtMgnt 2 }



--- *********************************************************
---     TABLE for the pm1004mCtrllineOosMode articles
--- *********************************************************

pm1004mCtrllineOosModeTable OBJECT-TYPE
	SYNTAX  SEQUENCE OF Pm1004mCtrllineOosModeEntry
	MAX-ACCESS not-accessible
	STATUS current
	DESCRIPTION
        "
        List of pm1004mCtrllineOosMode 
        Article
        "
	::= { pm1004mCtrlLine 74 }


pm1004mCtrllineOosModeEntry OBJECT-TYPE
	SYNTAX Pm1004mCtrllineOosModeEntry
	MAX-ACCESS not-accessible
	STATUS current
	DESCRIPTION
        "
        Row definition for the pm1004mCtrllineOosMode 
        table
        "
	INDEX   { pm1004mCtrllineOosModeIndex }
	::= { pm1004mCtrllineOosModeTable 1 }


Pm1004mCtrllineOosModeEntry ::=
	SEQUENCE {
	pm1004mCtrllineOosModeIndex
		INTEGER,
	pm1004mCtrllineOosModePortn
		EkiState
	}


pm1004mCtrllineOosModeIndex OBJECT-TYPE
	SYNTAX  INTEGER(0..128)
	MAX-ACCESS  read-only
	STATUS current
	DESCRIPTION
        "
        Index definition for the pm1004mCtrllineOosMode 
        table
        "
	::= { pm1004mCtrllineOosModeEntry 1 }


pm1004mCtrllineOosModePortn OBJECT-TYPE
	SYNTAX  EkiState
	MAX-ACCESS read-write
	STATUS current
	DESCRIPTION
        "
        Line Port Out Of Service :This 
        OID sets the line port Out Of Service 
         <Help>  This control defines the 
        service state of the line port
        "
	::= { pm1004mCtrllineOosModeEntry 2 }


--- *********************************************************
---     TABLE for the pm1004mCtrllineResetCount15Line articles
--- *********************************************************

pm1004mCtrllineResetCount15LineTable OBJECT-TYPE
	SYNTAX  SEQUENCE OF Pm1004mCtrllineResetCount15LineEntry
	MAX-ACCESS not-accessible
	STATUS current
	DESCRIPTION
        "
        List of pm1004mCtrllineResetCount15Line 
        Article
        "
	::= { pm1004mCtrlLine 86 }


pm1004mCtrllineResetCount15LineEntry OBJECT-TYPE
	SYNTAX Pm1004mCtrllineResetCount15LineEntry
	MAX-ACCESS not-accessible
	STATUS current
	DESCRIPTION
        "
        Row definition for the pm1004mCtrllineResetCount15Line 
        table
        "
	INDEX   { pm1004mCtrllineResetCount15LineIndex }
	::= { pm1004mCtrllineResetCount15LineTable 1 }


Pm1004mCtrllineResetCount15LineEntry ::=
	SEQUENCE {
	pm1004mCtrllineResetCount15LineIndex
		INTEGER,
	pm1004mCtrlresetAllPerfCount15Portn
		EkiState
	}


pm1004mCtrllineResetCount15LineIndex OBJECT-TYPE
	SYNTAX  INTEGER(0..128)
	MAX-ACCESS  read-only
	STATUS current
	DESCRIPTION
        "
        Index definition for the pm1004mCtrllineResetCount15Line 
        table
        "
	::= { pm1004mCtrllineResetCount15LineEntry 1 }


pm1004mCtrlresetAllPerfCount15Portn OBJECT-TYPE
	SYNTAX  EkiState
	MAX-ACCESS read-write
	STATUS current
	DESCRIPTION
        "
        Line 15-min Counters Reset :This 
        OID resets all the current 15-min 
        Counters on the client port
        "
	::= { pm1004mCtrllineResetCount15LineEntry 2 }


--- *********************************************************
---     TABLE for the pm1004mCtrllineResetCount24Line articles
--- *********************************************************

pm1004mCtrllineResetCount24LineTable OBJECT-TYPE
	SYNTAX  SEQUENCE OF Pm1004mCtrllineResetCount24LineEntry
	MAX-ACCESS not-accessible
	STATUS current
	DESCRIPTION
        "
        List of pm1004mCtrllineResetCount24Line 
        Article
        "
	::= { pm1004mCtrlLine 87 }


pm1004mCtrllineResetCount24LineEntry OBJECT-TYPE
	SYNTAX Pm1004mCtrllineResetCount24LineEntry
	MAX-ACCESS not-accessible
	STATUS current
	DESCRIPTION
        "
        Row definition for the pm1004mCtrllineResetCount24Line 
        table
        "
	INDEX   { pm1004mCtrllineResetCount24LineIndex }
	::= { pm1004mCtrllineResetCount24LineTable 1 }


Pm1004mCtrllineResetCount24LineEntry ::=
	SEQUENCE {
	pm1004mCtrllineResetCount24LineIndex
		INTEGER,
	pm1004mCtrlresetAllPerfCount24Portn
		EkiState
	}


pm1004mCtrllineResetCount24LineIndex OBJECT-TYPE
	SYNTAX  INTEGER(0..128)
	MAX-ACCESS  read-only
	STATUS current
	DESCRIPTION
        "
        Index definition for the pm1004mCtrllineResetCount24Line 
        table
        "
	::= { pm1004mCtrllineResetCount24LineEntry 1 }


pm1004mCtrlresetAllPerfCount24Portn OBJECT-TYPE
	SYNTAX  EkiState
	MAX-ACCESS read-write
	STATUS current
	DESCRIPTION
        "
        Line 24-hours Counters Reset :This 
        OID resets all the current 24-hours 
        Counters on the client port
        "
	::= { pm1004mCtrllineResetCount24LineEntry 2 }


--- *****************************************************
---     LEAF for the ledTest article
--- *****************************************************
pm1004mCtrlledTest OBJECT IDENTIFIER ::= { pm1004mCtrlOther 192 }




pm1004mCtrlLedOff OBJECT-TYPE
	  SYNTAX EkiOnOff
	  MAX-ACCESS read-write
	  STATUS current
	  DESCRIPTION
        "
        Leds Off :This OID switches off 
        all the Leds as a test feature. 
         <Help>  This control initiates 
        a test leds turning all the LEDs 
        to OFF
        "
	  ::= { pm1004mCtrlledTest 3 }



pm1004mCtrlRedLed OBJECT-TYPE
	  SYNTAX EkiOnOff
	  MAX-ACCESS read-write
	  STATUS current
	  DESCRIPTION
        "
        Red Leds Test :This OID switches 
        on all the red Leds as a test feature. 
         <Help>  This control initiates 
        a test leds turning all the LEDs 
        to red
        "
	  ::= { pm1004mCtrlledTest 2 }



pm1004mCtrlGreenLed OBJECT-TYPE
	  SYNTAX EkiOnOff
	  MAX-ACCESS read-write
	  STATUS current
	  DESCRIPTION
        "
        Green Leds Test :This OID switches 
        on all the green Leds as a test 
        feature.  <Help>  This control
         initiates a test leds turning
         all the LEDs to green
        "
	  ::= { pm1004mCtrlledTest 1 }



--- *****************************************************
---     LEAF for the moduleOosMode article
--- *****************************************************
pm1004mCtrlmoduleOosMode OBJECT IDENTIFIER ::= { pm1004mCtrlOther 193 }




pm1004mCtrlModuleOosMode OBJECT-TYPE
	  SYNTAX EkiOnOff
	  MAX-ACCESS read-write
	  STATUS current
	  DESCRIPTION
        "
        PM Out Of Service :This OID sets 
        the PM Out Of Service  <Help> 
         This control defines the service 
        state of the complete module
        "
	  ::= { pm1004mCtrlmoduleOosMode 1 }



--- *****************************************************
---     LEAF for the maintenanceMode article
--- *****************************************************
pm1004mCtrlmaintenanceMode OBJECT IDENTIFIER ::= { pm1004mCtrlOther 197 }




pm1004mCtrlMaintenanceMode OBJECT-TYPE
	  SYNTAX EkiOnOff
	  MAX-ACCESS read-write
	  STATUS current
	  DESCRIPTION
        "
        Module Maintenance Mode :This
         OID enables the maintenance mode 
        on the PM.  <Help>   This control 
        enables the maintenance mode on 
        the PM.
        "
	  ::= { pm1004mCtrlmaintenanceMode 1 }



--- *****************************************************
---     LEAF for the dccEnable article
--- *****************************************************
pm1004mCtrldccEnable OBJECT IDENTIFIER ::= { pm1004mCtrlOther 198 }




pm1004mCtrlDccEnable OBJECT-TYPE
	  SYNTAX EkiOnOff
	  MAX-ACCESS read-write
	  STATUS current
	  DESCRIPTION
        "
        DCC Enable :This OID enables the 
        DCC mode on the PM   <Help>   This 
        control enables the DCC mode on 
        the PM
        "
	  ::= { pm1004mCtrldccEnable 1 }



--- *********************************************************
---     TABLE for the pm1004mCtrlxfpOnoff articles
--- *********************************************************

pm1004mCtrlxfpOnoffTable OBJECT-TYPE
	SYNTAX  SEQUENCE OF Pm1004mCtrlxfpOnoffEntry
	MAX-ACCESS not-accessible
	STATUS current
	DESCRIPTION
        "
        List of pm1004mCtrlxfpOnoff Article
        "
	::= { pm1004mCtrlLine 208 }


pm1004mCtrlxfpOnoffEntry OBJECT-TYPE
	SYNTAX Pm1004mCtrlxfpOnoffEntry
	MAX-ACCESS not-accessible
	STATUS current
	DESCRIPTION
        "
        Row definition for the pm1004mCtrlxfpOnoff 
        table
        "
	INDEX   { pm1004mCtrlxfpOnoffIndex }
	::= { pm1004mCtrlxfpOnoffTable 1 }


Pm1004mCtrlxfpOnoffEntry ::=
	SEQUENCE {
	pm1004mCtrlxfpOnoffIndex
		INTEGER,
	pm1004mCtrlxfpOnoffPortn
		EkiState
	}


pm1004mCtrlxfpOnoffIndex OBJECT-TYPE
	SYNTAX  INTEGER(0..128)
	MAX-ACCESS  read-only
	STATUS current
	DESCRIPTION
        "
        Index definition for the pm1004mCtrlxfpOnoff 
        table
        "
	::= { pm1004mCtrlxfpOnoffEntry 1 }


pm1004mCtrlxfpOnoffPortn OBJECT-TYPE
	SYNTAX  EkiState
	MAX-ACCESS read-write
	STATUS current
	DESCRIPTION
        "
        Line Optical Laser Shutdown :This 
        OID switches off the XFP or the 
        OTX  <Help>  This control defines 
        the laser state of the line transceiver
        "
	::= { pm1004mCtrlxfpOnoffEntry 2 }


--- *********************************************************
---     TABLE for the pm1004mCtrlxfpLineLoop articles
--- *********************************************************

pm1004mCtrlxfpLineLoopTable OBJECT-TYPE
	SYNTAX  SEQUENCE OF Pm1004mCtrlxfpLineLoopEntry
	MAX-ACCESS not-accessible
	STATUS current
	DESCRIPTION
        "
        List of pm1004mCtrlxfpLineLoop 
        Article
        "
	::= { pm1004mCtrlLine 209 }


pm1004mCtrlxfpLineLoopEntry OBJECT-TYPE
	SYNTAX Pm1004mCtrlxfpLineLoopEntry
	MAX-ACCESS not-accessible
	STATUS current
	DESCRIPTION
        "
        Row definition for the pm1004mCtrlxfpLineLoop 
        table
        "
	INDEX   { pm1004mCtrlxfpLineLoopIndex }
	::= { pm1004mCtrlxfpLineLoopTable 1 }


Pm1004mCtrlxfpLineLoopEntry ::=
	SEQUENCE {
	pm1004mCtrlxfpLineLoopIndex
		INTEGER,
	pm1004mCtrlxfpLineLoopPortn
		EkiState
	}


pm1004mCtrlxfpLineLoopIndex OBJECT-TYPE
	SYNTAX  INTEGER(0..128)
	MAX-ACCESS  read-only
	STATUS current
	DESCRIPTION
        "
        Index definition for the pm1004mCtrlxfpLineLoop 
        table
        "
	::= { pm1004mCtrlxfpLineLoopEntry 1 }


pm1004mCtrlxfpLineLoopPortn OBJECT-TYPE
	SYNTAX  EkiState
	MAX-ACCESS read-write
	STATUS current
	DESCRIPTION
        "
        Line Facility Loopback :This OID 
        operates a Line Facility Loopback, 
        looping line input signal on the 
        line output port. The loop is located 
        on the line transceiver. If the 
        Line signal carries DCC, the management 
        network is impacted  <Help> This 
        maintenance parameter operates
         a Line Facility Loopback, looping 
        line input signal on the line output 
        port. The loop is located on the 
        line transceiver. If the Line signal 
        carries DCC, the management network 
        is impacted
        "
	::= { pm1004mCtrlxfpLineLoopEntry 2 }


--- *********************************************************
---     TABLE for the pm1004mCtrlxfpXfiLoop articles
--- *********************************************************

pm1004mCtrlxfpXfiLoopTable OBJECT-TYPE
	SYNTAX  SEQUENCE OF Pm1004mCtrlxfpXfiLoopEntry
	MAX-ACCESS not-accessible
	STATUS current
	DESCRIPTION
        "
        List of pm1004mCtrlxfpXfiLoop
         Article
        "
	::= { pm1004mCtrlLine 210 }


pm1004mCtrlxfpXfiLoopEntry OBJECT-TYPE
	SYNTAX Pm1004mCtrlxfpXfiLoopEntry
	MAX-ACCESS not-accessible
	STATUS current
	DESCRIPTION
        "
        Row definition for the pm1004mCtrlxfpXfiLoop 
        table
        "
	INDEX   { pm1004mCtrlxfpXfiLoopIndex }
	::= { pm1004mCtrlxfpXfiLoopTable 1 }


Pm1004mCtrlxfpXfiLoopEntry ::=
	SEQUENCE {
	pm1004mCtrlxfpXfiLoopIndex
		INTEGER,
	pm1004mCtrlxfpXfiLoopPortn
		EkiState
	}


pm1004mCtrlxfpXfiLoopIndex OBJECT-TYPE
	SYNTAX  INTEGER(0..128)
	MAX-ACCESS  read-only
	STATUS current
	DESCRIPTION
        "
        Index definition for the pm1004mCtrlxfpXfiLoop 
        table
        "
	::= { pm1004mCtrlxfpXfiLoopEntry 1 }


pm1004mCtrlxfpXfiLoopPortn OBJECT-TYPE
	SYNTAX  EkiState
	MAX-ACCESS read-write
	STATUS current
	DESCRIPTION
        "
        Line Terminal Loopback :This OID 
        operates a Line Terminal Loopback, 
        looping line input signal on the 
        line output port. The loop is located 
        on all client transceivers  <Help> 
        This maintenance parameter operates 
        a Line Terminal Loopback, looping 
        line input signal on the line output 
        port. The loop is located on all 
        client transceivers.
        "
	::= { pm1004mCtrlxfpXfiLoopEntry 2 }


--- *********************************************************
---     TABLE for the pm1004mCtrllineTunableChannel articles
--- *********************************************************

pm1004mCtrllineTunableChannelTable OBJECT-TYPE
	SYNTAX  SEQUENCE OF Pm1004mCtrllineTunableChannelEntry
	MAX-ACCESS not-accessible
	STATUS current
	DESCRIPTION
        "
        List of pm1004mCtrllineTunableChannel 
        Article
        "
	::= { pm1004mCtrlLine 212 }


pm1004mCtrllineTunableChannelEntry OBJECT-TYPE
	SYNTAX Pm1004mCtrllineTunableChannelEntry
	MAX-ACCESS not-accessible
	STATUS current
	DESCRIPTION
        "
        Row definition for the pm1004mCtrllineTunableChannel 
        table
        "
	INDEX   { pm1004mCtrllineTunableChannelIndex }
	::= { pm1004mCtrllineTunableChannelTable 1 }


Pm1004mCtrllineTunableChannelEntry ::=
	SEQUENCE {
	pm1004mCtrllineTunableChannelIndex
		INTEGER,
	pm1004mCtrllineTunableChannelPortn
		Pm1004mOtxChannel
	}


pm1004mCtrllineTunableChannelIndex OBJECT-TYPE
	SYNTAX  INTEGER(0..128)
	MAX-ACCESS  read-only
	STATUS current
	DESCRIPTION
        "
        Index definition for the pm1004mCtrllineTunableChannel 
        table
        "
	::= { pm1004mCtrllineTunableChannelEntry 1 }


pm1004mCtrllineTunableChannelPortn OBJECT-TYPE
	SYNTAX  Pm1004mOtxChannel
	MAX-ACCESS read-write
	STATUS current
	DESCRIPTION
        "
        ITU Channel :This OID selects
         the ITU channel of the Line OTX 
        TLH Laser  <Help>   This control 
        defines the ITU channel of the
         Line OTX TLH Laser
        "
	::= { pm1004mCtrllineTunableChannelEntry 2 }


--- *********************************************************
---     TABLE for the pm1004mCtrllinePhotodiodeMode articles
--- *********************************************************

pm1004mCtrllinePhotodiodeModeTable OBJECT-TYPE
	SYNTAX  SEQUENCE OF Pm1004mCtrllinePhotodiodeModeEntry
	MAX-ACCESS not-accessible
	STATUS current
	DESCRIPTION
        "
        List of pm1004mCtrllinePhotodiodeMode 
        Article
        "
	::= { pm1004mCtrlLine 213 }


pm1004mCtrllinePhotodiodeModeEntry OBJECT-TYPE
	SYNTAX Pm1004mCtrllinePhotodiodeModeEntry
	MAX-ACCESS not-accessible
	STATUS current
	DESCRIPTION
        "
        Row definition for the pm1004mCtrllinePhotodiodeMode 
        table
        "
	INDEX   { pm1004mCtrllinePhotodiodeModeIndex }
	::= { pm1004mCtrllinePhotodiodeModeTable 1 }


Pm1004mCtrllinePhotodiodeModeEntry ::=
	SEQUENCE {
	pm1004mCtrllinePhotodiodeModeIndex
		INTEGER,
	pm1004mCtrllinePhotodiodeModePortn
		Pm1004mOtxMode
	}


pm1004mCtrllinePhotodiodeModeIndex OBJECT-TYPE
	SYNTAX  INTEGER(0..128)
	MAX-ACCESS  read-only
	STATUS current
	DESCRIPTION
        "
        Index definition for the pm1004mCtrllinePhotodiodeMode 
        table
        "
	::= { pm1004mCtrllinePhotodiodeModeEntry 1 }


pm1004mCtrllinePhotodiodeModePortn OBJECT-TYPE
	SYNTAX  Pm1004mOtxMode
	MAX-ACCESS read-write
	STATUS current
	DESCRIPTION
        "
        OTX TLH Rx Sens. Mode :This OID 
        defines the Rx sensiblity mode
         of the Line OTX TLH  <Help>  
         This control defines the receiver 
        sensibility mode of the Line OTX 
        TLH Laser (OTX60, OTX80 or Custom)
        "
	::= { pm1004mCtrllinePhotodiodeModeEntry 2 }


--- *********************************************************
---     TABLE for the pm1004mCtrllinePhotodiodeValue articles
--- *********************************************************

pm1004mCtrllinePhotodiodeValueTable OBJECT-TYPE
	SYNTAX  SEQUENCE OF Pm1004mCtrllinePhotodiodeValueEntry
	MAX-ACCESS not-accessible
	STATUS current
	DESCRIPTION
        "
        List of pm1004mCtrllinePhotodiodeValue 
        Article
        "
	::= { pm1004mCtrlLine 214 }


pm1004mCtrllinePhotodiodeValueEntry OBJECT-TYPE
	SYNTAX Pm1004mCtrllinePhotodiodeValueEntry
	MAX-ACCESS not-accessible
	STATUS current
	DESCRIPTION
        "
        Row definition for the pm1004mCtrllinePhotodiodeValue 
        table
        "
	INDEX   { pm1004mCtrllinePhotodiodeValueIndex }
	::= { pm1004mCtrllinePhotodiodeValueTable 1 }


Pm1004mCtrllinePhotodiodeValueEntry ::=
	SEQUENCE {
	pm1004mCtrllinePhotodiodeValueIndex
		INTEGER,
	pm1004mCtrllinePhotodiodeValuePortn
		Pm1004mAdjustValue
	}


pm1004mCtrllinePhotodiodeValueIndex OBJECT-TYPE
	SYNTAX  INTEGER(0..128)
	MAX-ACCESS  read-only
	STATUS current
	DESCRIPTION
        "
        Index definition for the pm1004mCtrllinePhotodiodeValue 
        table
        "
	::= { pm1004mCtrllinePhotodiodeValueEntry 1 }


pm1004mCtrllinePhotodiodeValuePortn OBJECT-TYPE
	SYNTAX  Pm1004mAdjustValue
	MAX-ACCESS read-write
	STATUS current
	DESCRIPTION
        "
        OTX TLH Rx Sensibility :This OID 
        sets the Rx sensibility of the
         Line OTX TLH (custom mode only) 
         <Help>   This control defines
         the receiver sensibility value 
        (only in Custom mode) of the Line 
        OTX TLH Laser
        "
	::= { pm1004mCtrllinePhotodiodeValueEntry 2 }


--- *********************************************************
---     TABLE for the pm1004mCtrllinePowerLaser articles
--- *********************************************************

pm1004mCtrllinePowerLaserTable OBJECT-TYPE
	SYNTAX  SEQUENCE OF Pm1004mCtrllinePowerLaserEntry
	MAX-ACCESS not-accessible
	STATUS current
	DESCRIPTION
        "
        List of pm1004mCtrllinePowerLaser 
        Article
        "
	::= { pm1004mCtrlLine 215 }


pm1004mCtrllinePowerLaserEntry OBJECT-TYPE
	SYNTAX Pm1004mCtrllinePowerLaserEntry
	MAX-ACCESS not-accessible
	STATUS current
	DESCRIPTION
        "
        Row definition for the pm1004mCtrllinePowerLaser 
        table
        "
	INDEX   { pm1004mCtrllinePowerLaserIndex }
	::= { pm1004mCtrllinePowerLaserTable 1 }


Pm1004mCtrllinePowerLaserEntry ::=
	SEQUENCE {
	pm1004mCtrllinePowerLaserIndex
		INTEGER,
	pm1004mCtrllinePowerLaserPortn
		INTEGER 
	}


pm1004mCtrllinePowerLaserIndex OBJECT-TYPE
	SYNTAX  INTEGER(0..128)
	MAX-ACCESS  read-only
	STATUS current
	DESCRIPTION
        "
        Index definition for the pm1004mCtrllinePowerLaser 
        table
        "
	::= { pm1004mCtrllinePowerLaserEntry 1 }


pm1004mCtrllinePowerLaserPortn OBJECT-TYPE
	SYNTAX  INTEGER (0..255)
	MAX-ACCESS read-write
	STATUS current
	DESCRIPTION
        "
        Line Laser Output Power [3-5]
         :This OID sets the output power 
        value on the laser of the Line
         OTX TLH (AV=Power*10+158) (Unit 
        = dBm)  <Help>   This control defines 
        the start-up output power of the 
        Line OTX TLH
        "
	::= { pm1004mCtrllinePowerLaserEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm1004mCntupRaRemCnt articles
--- *********************************************************

pm1004mCntupRaRemCntTable OBJECT-TYPE
	SYNTAX  SEQUENCE OF Pm1004mCntupRaRemCntEntry
	MAX-ACCESS not-accessible
	STATUS current
	DESCRIPTION
        "
        List of pm1004mCntupRaRemCnt Article
        "
	::= { pm1004mCntClient 16 }


pm1004mCntupRaRemCntEntry OBJECT-TYPE
	SYNTAX Pm1004mCntupRaRemCntEntry
	MAX-ACCESS not-accessible
	STATUS current
	DESCRIPTION
        "
        Row definition for the pm1004mCntupRaRemCnt 
        table
        "
	INDEX   { pm1004mCntupRaRemCntIndex }
	::= { pm1004mCntupRaRemCntTable 1 }


Pm1004mCntupRaRemCntEntry ::=
	SEQUENCE {
	pm1004mCntupRaRemCntIndex
		INTEGER,
	pm1004mCntupRaRemCntValuePortn
		Counter32,
	pm1004mCntupRaRemCntErrorPortn
		EkiOnOff,
	pm1004mCntupRaRemCntOverloadPortn
		EkiOnOff
	}


pm1004mCntupRaRemCntIndex OBJECT-TYPE
	SYNTAX  INTEGER(0..128)
	MAX-ACCESS  read-only
	STATUS current
	DESCRIPTION
        "
        Index definition for the pm1004mCntupRaRemCnt 
        table
        "
	::= { pm1004mCntupRaRemCntEntry 1 }


pm1004mCntupRaRemCntValuePortn OBJECT-TYPE
	SYNTAX  Counter32
	MAX-ACCESS read-only
	STATUS current
	DESCRIPTION
        "
        Client Rate Adapt. Words Removal 
        :This counter is incremented each 
        time a rate adaptation 10B word 
        is removed from the Client input 
        stream
        "
	::= { pm1004mCntupRaRemCntEntry 2 }


pm1004mCntupRaRemCntErrorPortn OBJECT-TYPE
	SYNTAX  EkiOnOff
	MAX-ACCESS read-only
	STATUS current
	DESCRIPTION
        "
        Client Counter Error :This OID 
        when set indicates the rate adaptation 
        removal counter value is invalid 
        on Port
        "
	::= { pm1004mCntupRaRemCntEntry 3 }


pm1004mCntupRaRemCntOverloadPortn OBJECT-TYPE
	SYNTAX  EkiOnOff
	MAX-ACCESS read-only
	STATUS current
	DESCRIPTION
        "
        Client Counter Overload :This
         OID when set indicates a rate
         adaptation removal counter overload 
        on Port
        "
	::= { pm1004mCntupRaRemCntEntry 4 }


--- *********************************************************
---     TABLE for the pm1004mCntupRaInsCnt articles
--- *********************************************************

pm1004mCntupRaInsCntTable OBJECT-TYPE
	SYNTAX  SEQUENCE OF Pm1004mCntupRaInsCntEntry
	MAX-ACCESS not-accessible
	STATUS current
	DESCRIPTION
        "
        List of pm1004mCntupRaInsCnt Article
        "
	::= { pm1004mCntClient 24 }


pm1004mCntupRaInsCntEntry OBJECT-TYPE
	SYNTAX Pm1004mCntupRaInsCntEntry
	MAX-ACCESS not-accessible
	STATUS current
	DESCRIPTION
        "
        Row definition for the pm1004mCntupRaInsCnt 
        table
        "
	INDEX   { pm1004mCntupRaInsCntIndex }
	::= { pm1004mCntupRaInsCntTable 1 }


Pm1004mCntupRaInsCntEntry ::=
	SEQUENCE {
	pm1004mCntupRaInsCntIndex
		INTEGER,
	pm1004mCntupRaInsCntValuePortn
		Counter32,
	pm1004mCntupRaInsCntErrorPortn
		EkiOnOff,
	pm1004mCntupRaInsCntOverloadPortn
		EkiOnOff
	}


pm1004mCntupRaInsCntIndex OBJECT-TYPE
	SYNTAX  INTEGER(0..128)
	MAX-ACCESS  read-only
	STATUS current
	DESCRIPTION
        "
        Index definition for the pm1004mCntupRaInsCnt 
        table
        "
	::= { pm1004mCntupRaInsCntEntry 1 }


pm1004mCntupRaInsCntValuePortn OBJECT-TYPE
	SYNTAX  Counter32
	MAX-ACCESS read-only
	STATUS current
	DESCRIPTION
        "
        Client Rate Adapt. Words Insertion 
        :This counter is incremented each 
        time a rate adaptation 10B word 
        is inserted in the Client input 
        stream
        "
	::= { pm1004mCntupRaInsCntEntry 2 }


pm1004mCntupRaInsCntErrorPortn OBJECT-TYPE
	SYNTAX  EkiOnOff
	MAX-ACCESS read-only
	STATUS current
	DESCRIPTION
        "
        Client Counter Error :This OID 
        when set indicates the rate adaptation 
        insertion counter value is invalid 
        on Port
        "
	::= { pm1004mCntupRaInsCntEntry 3 }


pm1004mCntupRaInsCntOverloadPortn OBJECT-TYPE
	SYNTAX  EkiOnOff
	MAX-ACCESS read-only
	STATUS current
	DESCRIPTION
        "
        Client Counter Overload :This
         OID when set indicates a rate
         adaptation insertion counter overload 
        on Port
        "
	::= { pm1004mCntupRaInsCntEntry 4 }


--- *********************************************************
---     TABLE for the pm1004mCntupRdErrCnt articles
--- *********************************************************

pm1004mCntupRdErrCntTable OBJECT-TYPE
	SYNTAX  SEQUENCE OF Pm1004mCntupRdErrCntEntry
	MAX-ACCESS not-accessible
	STATUS current
	DESCRIPTION
        "
        List of pm1004mCntupRdErrCnt Article
        "
	::= { pm1004mCntClient 32 }


pm1004mCntupRdErrCntEntry OBJECT-TYPE
	SYNTAX Pm1004mCntupRdErrCntEntry
	MAX-ACCESS not-accessible
	STATUS current
	DESCRIPTION
        "
        Row definition for the pm1004mCntupRdErrCnt 
        table
        "
	INDEX   { pm1004mCntupRdErrCntIndex }
	::= { pm1004mCntupRdErrCntTable 1 }


Pm1004mCntupRdErrCntEntry ::=
	SEQUENCE {
	pm1004mCntupRdErrCntIndex
		INTEGER,
	pm1004mCntupRdErrCntValuePortn
		Counter32,
	pm1004mCntupRdErrCntErrorPortn
		EkiOnOff,
	pm1004mCntupRdErrCntOverloadPortn
		EkiOnOff
	}


pm1004mCntupRdErrCntIndex OBJECT-TYPE
	SYNTAX  INTEGER(0..128)
	MAX-ACCESS  read-only
	STATUS current
	DESCRIPTION
        "
        Index definition for the pm1004mCntupRdErrCnt 
        table
        "
	::= { pm1004mCntupRdErrCntEntry 1 }


pm1004mCntupRdErrCntValuePortn OBJECT-TYPE
	SYNTAX  Counter32
	MAX-ACCESS read-only
	STATUS current
	DESCRIPTION
        "
        Client Input Errors :This counter 
        is increased each time a 10b/8b 
        running disparity error is detected 
        on the Client input stream  <Help> 
         This counter gives the number
         of B1 errors on the client input 
        port
        "
	::= { pm1004mCntupRdErrCntEntry 2 }


pm1004mCntupRdErrCntErrorPortn OBJECT-TYPE
	SYNTAX  EkiOnOff
	MAX-ACCESS read-only
	STATUS current
	DESCRIPTION
        "
        Client Counter Error :This OID 
        when set indicates the client error 
        counter value is invalid on Port
        "
	::= { pm1004mCntupRdErrCntEntry 3 }


pm1004mCntupRdErrCntOverloadPortn OBJECT-TYPE
	SYNTAX  EkiOnOff
	MAX-ACCESS read-only
	STATUS current
	DESCRIPTION
        "
        Client Counter Overload :This
         OID when set indicates a client 
        input error counter overload on 
        Port
        "
	::= { pm1004mCntupRdErrCntEntry 4 }


--- *********************************************************
---     TABLE for the pm1004mCntupTimCnt articles
--- *********************************************************

pm1004mCntupTimCntTable OBJECT-TYPE
	SYNTAX  SEQUENCE OF Pm1004mCntupTimCntEntry
	MAX-ACCESS not-accessible
	STATUS current
	DESCRIPTION
        "
        List of pm1004mCntupTimCnt Article
        "
	::= { pm1004mCntClient 40 }


pm1004mCntupTimCntEntry OBJECT-TYPE
	SYNTAX Pm1004mCntupTimCntEntry
	MAX-ACCESS not-accessible
	STATUS current
	DESCRIPTION
        "
        Row definition for the pm1004mCntupTimCnt 
        table
        "
	INDEX   { pm1004mCntupTimCntIndex }
	::= { pm1004mCntupTimCntTable 1 }


Pm1004mCntupTimCntEntry ::=
	SEQUENCE {
	pm1004mCntupTimCntIndex
		INTEGER,
	pm1004mCntupTimCntValuePortn
		Counter32,
	pm1004mCntupTimCntErrorPortn
		EkiOnOff,
	pm1004mCntupTimCntOverloadPortn
		EkiOnOff
	}


pm1004mCntupTimCntIndex OBJECT-TYPE
	SYNTAX  INTEGER(0..128)
	MAX-ACCESS  read-only
	STATUS current
	DESCRIPTION
        "
        Index definition for the pm1004mCntupTimCnt 
        table
        "
	::= { pm1004mCntupTimCntEntry 1 }


pm1004mCntupTimCntValuePortn OBJECT-TYPE
	SYNTAX  Counter32
	MAX-ACCESS read-only
	STATUS current
	DESCRIPTION
        "
        Client Upstream Timer Counter
         :This is the timing counter dedicated 
        to the upstream access counters. 
        It is incremented every 125 us.
        "
	::= { pm1004mCntupTimCntEntry 2 }


pm1004mCntupTimCntErrorPortn OBJECT-TYPE
	SYNTAX  EkiOnOff
	MAX-ACCESS read-only
	STATUS current
	DESCRIPTION
        "
        Client Counter Error :This OID 
        when set indicates the upstream 
        timing counter value is invalid 
        on Port
        "
	::= { pm1004mCntupTimCntEntry 3 }


pm1004mCntupTimCntOverloadPortn OBJECT-TYPE
	SYNTAX  EkiOnOff
	MAX-ACCESS read-only
	STATUS current
	DESCRIPTION
        "
        Client Counter Overload :This
         OID when set indicates a upstream 
        timing counter overload on Port
        "
	::= { pm1004mCntupTimCntEntry 4 }


--- *********************************************************
---     TABLE for the pm1004mCntupCvErrCnt articles
--- *********************************************************

pm1004mCntupCvErrCntTable OBJECT-TYPE
	SYNTAX  SEQUENCE OF Pm1004mCntupCvErrCntEntry
	MAX-ACCESS not-accessible
	STATUS current
	DESCRIPTION
        "
        List of pm1004mCntupCvErrCnt Article
        "
	::= { pm1004mCntClient 48 }


pm1004mCntupCvErrCntEntry OBJECT-TYPE
	SYNTAX Pm1004mCntupCvErrCntEntry
	MAX-ACCESS not-accessible
	STATUS current
	DESCRIPTION
        "
        Row definition for the pm1004mCntupCvErrCnt 
        table
        "
	INDEX   { pm1004mCntupCvErrCntIndex }
	::= { pm1004mCntupCvErrCntTable 1 }


Pm1004mCntupCvErrCntEntry ::=
	SEQUENCE {
	pm1004mCntupCvErrCntIndex
		INTEGER,
	pm1004mCntupCvErrCntValuePortn
		Counter32,
	pm1004mCntupCvErrCntErrorPortn
		EkiOnOff,
	pm1004mCntupCvErrCntOverloadPortn
		EkiOnOff
	}


pm1004mCntupCvErrCntIndex OBJECT-TYPE
	SYNTAX  INTEGER(0..128)
	MAX-ACCESS  read-only
	STATUS current
	DESCRIPTION
        "
        Index definition for the pm1004mCntupCvErrCnt 
        table
        "
	::= { pm1004mCntupCvErrCntEntry 1 }


pm1004mCntupCvErrCntValuePortn OBJECT-TYPE
	SYNTAX  Counter32
	MAX-ACCESS read-only
	STATUS current
	DESCRIPTION
        "
        Client Coding Violation Counter 
        :This counter is increased each 
        time a 10b/8b coding violation
         is detected on the Client input 
        stream
        "
	::= { pm1004mCntupCvErrCntEntry 2 }


pm1004mCntupCvErrCntErrorPortn OBJECT-TYPE
	SYNTAX  EkiOnOff
	MAX-ACCESS read-only
	STATUS current
	DESCRIPTION
        "
        Client Counter Error :This OID 
        when set indicates the coding violation 
        counter value is invalid on Port
        "
	::= { pm1004mCntupCvErrCntEntry 3 }


pm1004mCntupCvErrCntOverloadPortn OBJECT-TYPE
	SYNTAX  EkiOnOff
	MAX-ACCESS read-only
	STATUS current
	DESCRIPTION
        "
        Client Counter Overload :This
         OID when set indicates a coding 
        violation counter overload on Port
        "
	::= { pm1004mCntupCvErrCntEntry 4 }


--- *********************************************************
---     TABLE for the pm1004mCntdwTimCnt articles
--- *********************************************************

pm1004mCntdwTimCntTable OBJECT-TYPE
	SYNTAX  SEQUENCE OF Pm1004mCntdwTimCntEntry
	MAX-ACCESS not-accessible
	STATUS current
	DESCRIPTION
        "
        List of pm1004mCntdwTimCnt Article
        "
	::= { pm1004mCntClient 72 }


pm1004mCntdwTimCntEntry OBJECT-TYPE
	SYNTAX Pm1004mCntdwTimCntEntry
	MAX-ACCESS not-accessible
	STATUS current
	DESCRIPTION
        "
        Row definition for the pm1004mCntdwTimCnt 
        table
        "
	INDEX   { pm1004mCntdwTimCntIndex }
	::= { pm1004mCntdwTimCntTable 1 }


Pm1004mCntdwTimCntEntry ::=
	SEQUENCE {
	pm1004mCntdwTimCntIndex
		INTEGER,
	pm1004mCntdwTimCntValuePortn
		Counter32,
	pm1004mCntdwTimCntErrorPortn
		EkiOnOff,
	pm1004mCntdwTimCntOverloadPortn
		EkiOnOff
	}


pm1004mCntdwTimCntIndex OBJECT-TYPE
	SYNTAX  INTEGER(0..128)
	MAX-ACCESS  read-only
	STATUS current
	DESCRIPTION
        "
        Index definition for the pm1004mCntdwTimCnt 
        table
        "
	::= { pm1004mCntdwTimCntEntry 1 }


pm1004mCntdwTimCntValuePortn OBJECT-TYPE
	SYNTAX  Counter32
	MAX-ACCESS read-only
	STATUS current
	DESCRIPTION
        "
        Client Downstream Timer Counter 
        :This is the timing counter dedicated 
        to the downstream access counters. 
        It is incremented every 125 us.
        "
	::= { pm1004mCntdwTimCntEntry 2 }


pm1004mCntdwTimCntErrorPortn OBJECT-TYPE
	SYNTAX  EkiOnOff
	MAX-ACCESS read-only
	STATUS current
	DESCRIPTION
        "
        Client Counter Error :This OID 
        when set indicates the downstream 
        timer counter value is invalid
         on Port
        "
	::= { pm1004mCntdwTimCntEntry 3 }


pm1004mCntdwTimCntOverloadPortn OBJECT-TYPE
	SYNTAX  EkiOnOff
	MAX-ACCESS read-only
	STATUS current
	DESCRIPTION
        "
        Client Counter Overload :This
         OID when set indicates a downstream 
        timer counter overload on Port
        "
	::= { pm1004mCntdwTimCntEntry 4 }


--- *********************************************************
---     TABLE for the pm1004mCntdfrmB1ErrCnt articles
--- *********************************************************

pm1004mCntdfrmB1ErrCntTable OBJECT-TYPE
	SYNTAX  SEQUENCE OF Pm1004mCntdfrmB1ErrCntEntry
	MAX-ACCESS not-accessible
	STATUS current
	DESCRIPTION
        "
        List of pm1004mCntdfrmB1ErrCnt 
        Article
        "
	::= { pm1004mCntLine 152 }


pm1004mCntdfrmB1ErrCntEntry OBJECT-TYPE
	SYNTAX Pm1004mCntdfrmB1ErrCntEntry
	MAX-ACCESS not-accessible
	STATUS current
	DESCRIPTION
        "
        Row definition for the pm1004mCntdfrmB1ErrCnt 
        table
        "
	INDEX   { pm1004mCntdfrmB1ErrCntIndex }
	::= { pm1004mCntdfrmB1ErrCntTable 1 }


Pm1004mCntdfrmB1ErrCntEntry ::=
	SEQUENCE {
	pm1004mCntdfrmB1ErrCntIndex
		INTEGER,
	pm1004mCntdfrmB1ErrCntValuePortn
		Counter32,
	pm1004mCntdfrmB1ErrCntErrorPortn
		EkiOnOff,
	pm1004mCntdfrmB1ErrCntOverloadPortn
		EkiOnOff
	}


pm1004mCntdfrmB1ErrCntIndex OBJECT-TYPE
	SYNTAX  INTEGER(0..128)
	MAX-ACCESS  read-only
	STATUS current
	DESCRIPTION
        "
        Index definition for the pm1004mCntdfrmB1ErrCnt 
        table
        "
	::= { pm1004mCntdfrmB1ErrCntEntry 1 }


pm1004mCntdfrmB1ErrCntValuePortn OBJECT-TYPE
	SYNTAX  Counter32
	MAX-ACCESS read-only
	STATUS current
	DESCRIPTION
        "
        Line Input B1 Errors :This counter 
        is incremented each time a SM BIP 
        error is detected on the Deframer 
        input stream.  <Help>  This counter 
        gives the number of BIP8 errors 
        on the line port
        "
	::= { pm1004mCntdfrmB1ErrCntEntry 2 }


pm1004mCntdfrmB1ErrCntErrorPortn OBJECT-TYPE
	SYNTAX  EkiOnOff
	MAX-ACCESS read-only
	STATUS current
	DESCRIPTION
        "
        Line Counter Error :This OID when 
        set indicates the SM BIP error
         counter value is invalid on Port
        "
	::= { pm1004mCntdfrmB1ErrCntEntry 3 }


pm1004mCntdfrmB1ErrCntOverloadPortn OBJECT-TYPE
	SYNTAX  EkiOnOff
	MAX-ACCESS read-only
	STATUS current
	DESCRIPTION
        "
        Line Counter Overload :This OID 
        when set indicates a SM BIP error 
        counter overload on Port
        "
	::= { pm1004mCntdfrmB1ErrCntEntry 4 }


--- *********************************************************
---     TABLE for the pm1004mCntdfrmTimCnt articles
--- *********************************************************

pm1004mCntdfrmTimCntTable OBJECT-TYPE
	SYNTAX  SEQUENCE OF Pm1004mCntdfrmTimCntEntry
	MAX-ACCESS not-accessible
	STATUS current
	DESCRIPTION
        "
        List of pm1004mCntdfrmTimCnt Article
        "
	::= { pm1004mCntLine 153 }


pm1004mCntdfrmTimCntEntry OBJECT-TYPE
	SYNTAX Pm1004mCntdfrmTimCntEntry
	MAX-ACCESS not-accessible
	STATUS current
	DESCRIPTION
        "
        Row definition for the pm1004mCntdfrmTimCnt 
        table
        "
	INDEX   { pm1004mCntdfrmTimCntIndex }
	::= { pm1004mCntdfrmTimCntTable 1 }


Pm1004mCntdfrmTimCntEntry ::=
	SEQUENCE {
	pm1004mCntdfrmTimCntIndex
		INTEGER,
	pm1004mCntdfrmTimCntValuePortn
		Counter32,
	pm1004mCntdfrmTimCntErrorPortn
		EkiOnOff,
	pm1004mCntdfrmTimCntOverloadPortn
		EkiOnOff
	}


pm1004mCntdfrmTimCntIndex OBJECT-TYPE
	SYNTAX  INTEGER(0..128)
	MAX-ACCESS  read-only
	STATUS current
	DESCRIPTION
        "
        Index definition for the pm1004mCntdfrmTimCnt 
        table
        "
	::= { pm1004mCntdfrmTimCntEntry 1 }


pm1004mCntdfrmTimCntValuePortn OBJECT-TYPE
	SYNTAX  Counter32
	MAX-ACCESS read-only
	STATUS current
	DESCRIPTION
        "
        Line Timer Counter :This is the 
        timing counter dedicated to the 
        downstream deframer counters. It 
        is incremented every 125 us.
        "
	::= { pm1004mCntdfrmTimCntEntry 2 }


pm1004mCntdfrmTimCntErrorPortn OBJECT-TYPE
	SYNTAX  EkiOnOff
	MAX-ACCESS read-only
	STATUS current
	DESCRIPTION
        "
        Line Counter Error :This OID when 
        set indicates the deframer timer 
        counter value is invalid on Port
        "
	::= { pm1004mCntdfrmTimCntEntry 3 }


pm1004mCntdfrmTimCntOverloadPortn OBJECT-TYPE
	SYNTAX  EkiOnOff
	MAX-ACCESS read-only
	STATUS current
	DESCRIPTION
        "
        Line Counter Overload :This OID 
        when set indicates a deframer timer 
        counter overload on Port
        "
	::= { pm1004mCntdfrmTimCntEntry 4 }


pm1004mCntCountersReset  OBJECT-TYPE
	SYNTAX EkiOnOff
	MAX-ACCESS read-write
	STATUS current
	DESCRIPTION
	"Counters Reset:This OID resets and restarts all the counters"
	::= { pm1004mcounters  259 }

pm1004mCntCountersStop  OBJECT-TYPE
	SYNTAX EkiOnOff
	MAX-ACCESS read-write
	STATUS current
	DESCRIPTION
	"Counters stop:This OID stops all the counters"
	::= { pm1004mcounters 260 }






--- *****************************************************
--- $$$$$$$$$$$$$$$$$$$$$$$$$$$$$$$$$$$$$$$$$$$$$$$$$$$$$
---     J0
--- $$$$$$$$$$$$$$$$$$$$$$$$$$$$$$$$$$$$$$$$$$$$$$$$$$$$$
--- *****************************************************








--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm1004mMesrsynth0 OBJECT-TYPE
	  SYNTAX EkiMeasureType
	  MAX-ACCESS read-only
	  STATUS deprecated
	  DESCRIPTION
        "
        Not Used :This OID gives the unit 
        used on AUX1 measurement of XFP#1 
         (Unit = )
        "
	  ::= { pm1004mMesrOther 0 }



pm1004mMesrsynth1 OBJECT-TYPE
	  SYNTAX EkiMeasureType
	  MAX-ACCESS read-only
	  STATUS deprecated
	  DESCRIPTION
        "
        Not Used :This OID gives the unit 
        used on AUX2 measurement of XFP#1 
         (Unit = )
        "
	  ::= { pm1004mMesrOther 1 }



--- *********************************************************
---     TABLE for the pm1004mMesrtempMeas articles
--- *********************************************************

pm1004mMesrtempMeasTable OBJECT-TYPE
	SYNTAX  SEQUENCE OF Pm1004mMesrtempMeasEntry
	MAX-ACCESS not-accessible
	STATUS current
	DESCRIPTION
        "
        List of pm1004mMesrtempMeas Article
        "
	::= { pm1004mMesrClient 16 }


pm1004mMesrtempMeasEntry OBJECT-TYPE
	SYNTAX Pm1004mMesrtempMeasEntry
	MAX-ACCESS not-accessible
	STATUS current
	DESCRIPTION
        "
        Row definition for the pm1004mMesrtempMeas 
        table
        "
	INDEX   { pm1004mMesrtempMeasIndex }
	::= { pm1004mMesrtempMeasTable 1 }


Pm1004mMesrtempMeasEntry ::=
	SEQUENCE {
	pm1004mMesrtempMeasIndex
		INTEGER,
	pm1004mMesrtempMeasPortn
		INTEGER 
	}


pm1004mMesrtempMeasIndex OBJECT-TYPE
	SYNTAX  INTEGER(0..128)
	MAX-ACCESS  read-only
	STATUS current
	DESCRIPTION
        "
        Index definition for the pm1004mMesrtempMeas 
        table
        "
	::= { pm1004mMesrtempMeasEntry 1 }


pm1004mMesrtempMeasPortn OBJECT-TYPE
	SYNTAX  INTEGER (0..65535)
	MAX-ACCESS read-only
	STATUS current
	DESCRIPTION
        "
        Client SFP Temperature :This OID 
        gives the temperature value of
         the SFP plugged in port, read
         from the DDM (Digital Diagnostic 
        Monitoring)  (Temperature = AV/256) 
        (Unit = C)  <Help>  This measure 
        gives the temperature of the client 
        transceiver
        "
	::= { pm1004mMesrtempMeasEntry 2 }


--- *********************************************************
---     TABLE for the pm1004mMesrvoltMeas articles
--- *********************************************************

pm1004mMesrvoltMeasTable OBJECT-TYPE
	SYNTAX  SEQUENCE OF Pm1004mMesrvoltMeasEntry
	MAX-ACCESS not-accessible
	STATUS current
	DESCRIPTION
        "
        List of pm1004mMesrvoltMeas Article
        "
	::= { pm1004mMesrClient 24 }


pm1004mMesrvoltMeasEntry OBJECT-TYPE
	SYNTAX Pm1004mMesrvoltMeasEntry
	MAX-ACCESS not-accessible
	STATUS current
	DESCRIPTION
        "
        Row definition for the pm1004mMesrvoltMeas 
        table
        "
	INDEX   { pm1004mMesrvoltMeasIndex }
	::= { pm1004mMesrvoltMeasTable 1 }


Pm1004mMesrvoltMeasEntry ::=
	SEQUENCE {
	pm1004mMesrvoltMeasIndex
		INTEGER,
	pm1004mMesrvoltMeasPortn
		INTEGER 
	}


pm1004mMesrvoltMeasIndex OBJECT-TYPE
	SYNTAX  INTEGER(0..128)
	MAX-ACCESS  read-only
	STATUS current
	DESCRIPTION
        "
        Index definition for the pm1004mMesrvoltMeas 
        table
        "
	::= { pm1004mMesrvoltMeasEntry 1 }


pm1004mMesrvoltMeasPortn OBJECT-TYPE
	SYNTAX  INTEGER (0..65535)
	MAX-ACCESS read-only
	STATUS current
	DESCRIPTION
        "
        Client SFP Power Supply :This
         OID gives the 3V3 voltage value 
        of the SFP plugged into port, read 
        from the DDM (Digital Diagnostic 
        Monitoring)  (Voltage = AV/10000) 
        (Unit = V)  <Help>  This measure 
        gives the 3V3 voltage of the client 
        transceiver
        "
	::= { pm1004mMesrvoltMeasEntry 2 }


--- *********************************************************
---     TABLE for the pm1004mMesrbiasMeas articles
--- *********************************************************

pm1004mMesrbiasMeasTable OBJECT-TYPE
	SYNTAX  SEQUENCE OF Pm1004mMesrbiasMeasEntry
	MAX-ACCESS not-accessible
	STATUS current
	DESCRIPTION
        "
        List of pm1004mMesrbiasMeas Article
        "
	::= { pm1004mMesrClient 32 }


pm1004mMesrbiasMeasEntry OBJECT-TYPE
	SYNTAX Pm1004mMesrbiasMeasEntry
	MAX-ACCESS not-accessible
	STATUS current
	DESCRIPTION
        "
        Row definition for the pm1004mMesrbiasMeas 
        table
        "
	INDEX   { pm1004mMesrbiasMeasIndex }
	::= { pm1004mMesrbiasMeasTable 1 }


Pm1004mMesrbiasMeasEntry ::=
	SEQUENCE {
	pm1004mMesrbiasMeasIndex
		INTEGER,
	pm1004mMesrbiasMeasPortn
		INTEGER 
	}


pm1004mMesrbiasMeasIndex OBJECT-TYPE
	SYNTAX  INTEGER(0..128)
	MAX-ACCESS  read-only
	STATUS current
	DESCRIPTION
        "
        Index definition for the pm1004mMesrbiasMeas 
        table
        "
	::= { pm1004mMesrbiasMeasEntry 1 }


pm1004mMesrbiasMeasPortn OBJECT-TYPE
	SYNTAX  INTEGER (0..65535)
	MAX-ACCESS read-only
	STATUS current
	DESCRIPTION
        "
        Client SFP Laser Bias :This OID 
        gives the bias value of the SFP 
        plugged into port, read from the 
        DDM (Digital Diagnostic Monitoring) 
         (Bias = AV/500) (Unit = mA)  <Help> 
         This measure gives the bias of 
        the client transceiver
        "
	::= { pm1004mMesrbiasMeasEntry 2 }


--- *********************************************************
---     TABLE for the pm1004mMesrtxpwrMeas articles
--- *********************************************************

pm1004mMesrtxpwrMeasTable OBJECT-TYPE
	SYNTAX  SEQUENCE OF Pm1004mMesrtxpwrMeasEntry
	MAX-ACCESS not-accessible
	STATUS current
	DESCRIPTION
        "
        List of pm1004mMesrtxpwrMeas Article
        "
	::= { pm1004mMesrClient 40 }


pm1004mMesrtxpwrMeasEntry OBJECT-TYPE
	SYNTAX Pm1004mMesrtxpwrMeasEntry
	MAX-ACCESS not-accessible
	STATUS current
	DESCRIPTION
        "
        Row definition for the pm1004mMesrtxpwrMeas 
        table
        "
	INDEX   { pm1004mMesrtxpwrMeasIndex }
	::= { pm1004mMesrtxpwrMeasTable 1 }


Pm1004mMesrtxpwrMeasEntry ::=
	SEQUENCE {
	pm1004mMesrtxpwrMeasIndex
		INTEGER,
	pm1004mMesrtxpwrMeasPortn
		INTEGER 
	}


pm1004mMesrtxpwrMeasIndex OBJECT-TYPE
	SYNTAX  INTEGER(0..128)
	MAX-ACCESS  read-only
	STATUS current
	DESCRIPTION
        "
        Index definition for the pm1004mMesrtxpwrMeas 
        table
        "
	::= { pm1004mMesrtxpwrMeasEntry 1 }


pm1004mMesrtxpwrMeasPortn OBJECT-TYPE
	SYNTAX  INTEGER (0..65535)
	MAX-ACCESS read-only
	STATUS current
	DESCRIPTION
        "
        Client SFP Tx Power :This OID
         gives the transmit power value 
        of the SFP plugged into port, read 
        from the DDM (Digital Diagnostic 
        Monitoring) (Power = 10*log(AV)-40) 
        (Unit = dBm)  <Help>  This measure 
        gives the Tx optical power of the 
        client transceiver
        "
	::= { pm1004mMesrtxpwrMeasEntry 2 }


--- *********************************************************
---     TABLE for the pm1004mMesrrxpwrMeas articles
--- *********************************************************

pm1004mMesrrxpwrMeasTable OBJECT-TYPE
	SYNTAX  SEQUENCE OF Pm1004mMesrrxpwrMeasEntry
	MAX-ACCESS not-accessible
	STATUS current
	DESCRIPTION
        "
        List of pm1004mMesrrxpwrMeas Article
        "
	::= { pm1004mMesrClient 48 }


pm1004mMesrrxpwrMeasEntry OBJECT-TYPE
	SYNTAX Pm1004mMesrrxpwrMeasEntry
	MAX-ACCESS not-accessible
	STATUS current
	DESCRIPTION
        "
        Row definition for the pm1004mMesrrxpwrMeas 
        table
        "
	INDEX   { pm1004mMesrrxpwrMeasIndex }
	::= { pm1004mMesrrxpwrMeasTable 1 }


Pm1004mMesrrxpwrMeasEntry ::=
	SEQUENCE {
	pm1004mMesrrxpwrMeasIndex
		INTEGER,
	pm1004mMesrrxpwrMeasPortn
		INTEGER 
	}


pm1004mMesrrxpwrMeasIndex OBJECT-TYPE
	SYNTAX  INTEGER(0..128)
	MAX-ACCESS  read-only
	STATUS current
	DESCRIPTION
        "
        Index definition for the pm1004mMesrrxpwrMeas 
        table
        "
	::= { pm1004mMesrrxpwrMeasEntry 1 }


pm1004mMesrrxpwrMeasPortn OBJECT-TYPE
	SYNTAX  INTEGER (0..65535)
	MAX-ACCESS read-only
	STATUS current
	DESCRIPTION
        "
        Client SFP Rx Power :This OID
         gives the receive power value
         of the SFP plugged into port,
         read in the DDM (Digital Diagnostic 
        Monitoring) (Power = 10*log(AV)-40) 
        (Unit = dBm)  <Help>  This measure 
        gives the Rx optical power of the 
        client transceiver
        "
	::= { pm1004mMesrrxpwrMeasEntry 2 }


--- *********************************************************
---     TABLE for the pm1004mMesrxfp1LxModTempMeas articles
--- *********************************************************

pm1004mMesrxfp1LxModTempMeasTable OBJECT-TYPE
	SYNTAX  SEQUENCE OF Pm1004mMesrxfp1LxModTempMeasEntry
	MAX-ACCESS not-accessible
	STATUS current
	DESCRIPTION
        "
        List of pm1004mMesrxfp1LxModTempMeas 
        Article
        "
	::= { pm1004mMesrLine 208 }


pm1004mMesrxfp1LxModTempMeasEntry OBJECT-TYPE
	SYNTAX Pm1004mMesrxfp1LxModTempMeasEntry
	MAX-ACCESS not-accessible
	STATUS current
	DESCRIPTION
        "
        Row definition for the pm1004mMesrxfp1LxModTempMeas 
        table
        "
	INDEX   { pm1004mMesrxfp1LxModTempMeasIndex }
	::= { pm1004mMesrxfp1LxModTempMeasTable 1 }


Pm1004mMesrxfp1LxModTempMeasEntry ::=
	SEQUENCE {
	pm1004mMesrxfp1LxModTempMeasIndex
		INTEGER,
	pm1004mMesrxfp1LxModTempMeasPortn
		INTEGER 
	}


pm1004mMesrxfp1LxModTempMeasIndex OBJECT-TYPE
	SYNTAX  INTEGER(0..128)
	MAX-ACCESS  read-only
	STATUS current
	DESCRIPTION
        "
        Index definition for the pm1004mMesrxfp1LxModTempMeas 
        table
        "
	::= { pm1004mMesrxfp1LxModTempMeasEntry 1 }


pm1004mMesrxfp1LxModTempMeasPortn OBJECT-TYPE
	SYNTAX  INTEGER (0..65535)
	MAX-ACCESS read-only
	STATUS current
	DESCRIPTION
        "
        Line Optical Module Temperature 
        :This OID gives the temperature 
        of the XFP or OTX plugged in line, 
        read from the DDM (Digital Diagnostic 
        Monitoring) (Temperature = AV/256) 
        (Unit = C)  <Help>  This measure 
        gives the temperature of the line 
        transceiver
        "
	::= { pm1004mMesrxfp1LxModTempMeasEntry 2 }


--- *********************************************************
---     TABLE for the pm1004mMesrxfp1Reserved articles
--- *********************************************************

pm1004mMesrxfp1ReservedTable OBJECT-TYPE
	SYNTAX  SEQUENCE OF Pm1004mMesrxfp1ReservedEntry
	MAX-ACCESS not-accessible
	STATUS deprecated
	DESCRIPTION
        "
        List of pm1004mMesrxfp1Reserved 
        Article
        "
	::= { pm1004mMesrLine 209 }


pm1004mMesrxfp1ReservedEntry OBJECT-TYPE
	SYNTAX Pm1004mMesrxfp1ReservedEntry
	MAX-ACCESS not-accessible
	STATUS deprecated
	DESCRIPTION
        "
        Row definition for the pm1004mMesrxfp1Reserved 
        table
        "
	INDEX   { pm1004mMesrxfp1ReservedIndex }
	::= { pm1004mMesrxfp1ReservedTable 1 }


Pm1004mMesrxfp1ReservedEntry ::=
	SEQUENCE {
	pm1004mMesrxfp1ReservedIndex
		INTEGER,
	pm1004mMesrxfp1ReservedPortn
		INTEGER 
	}


pm1004mMesrxfp1ReservedIndex OBJECT-TYPE
	SYNTAX  INTEGER(0..128)
	MAX-ACCESS  read-only
	STATUS deprecated
	DESCRIPTION
        "
        Index definition for the pm1004mMesrxfp1Reserved 
        table
        "
	::= { pm1004mMesrxfp1ReservedEntry 1 }


pm1004mMesrxfp1ReservedPortn OBJECT-TYPE
	SYNTAX  INTEGER (0..65535)
	MAX-ACCESS read-only
	STATUS deprecated
	DESCRIPTION
        "
        Not Used :Reserved
        "
	::= { pm1004mMesrxfp1ReservedEntry 2 }


--- *********************************************************
---     TABLE for the pm1004mMesrxfp1LoBiasCurrentMeas articles
--- *********************************************************

pm1004mMesrxfp1LoBiasCurrentMeasTable OBJECT-TYPE
	SYNTAX  SEQUENCE OF Pm1004mMesrxfp1LoBiasCurrentMeasEntry
	MAX-ACCESS not-accessible
	STATUS current
	DESCRIPTION
        "
        List of pm1004mMesrxfp1LoBiasCurrentMeas 
        Article
        "
	::= { pm1004mMesrLine 210 }


pm1004mMesrxfp1LoBiasCurrentMeasEntry OBJECT-TYPE
	SYNTAX Pm1004mMesrxfp1LoBiasCurrentMeasEntry
	MAX-ACCESS not-accessible
	STATUS current
	DESCRIPTION
        "
        Row definition for the pm1004mMesrxfp1LoBiasCurrentMeas 
        table
        "
	INDEX   { pm1004mMesrxfp1LoBiasCurrentMeasIndex }
	::= { pm1004mMesrxfp1LoBiasCurrentMeasTable 1 }


Pm1004mMesrxfp1LoBiasCurrentMeasEntry ::=
	SEQUENCE {
	pm1004mMesrxfp1LoBiasCurrentMeasIndex
		INTEGER,
	pm1004mMesrxfp1LoBiasCurrentMeasPortn
		INTEGER 
	}


pm1004mMesrxfp1LoBiasCurrentMeasIndex OBJECT-TYPE
	SYNTAX  INTEGER(0..128)
	MAX-ACCESS  read-only
	STATUS current
	DESCRIPTION
        "
        Index definition for the pm1004mMesrxfp1LoBiasCurrentMeas 
        table
        "
	::= { pm1004mMesrxfp1LoBiasCurrentMeasEntry 1 }


pm1004mMesrxfp1LoBiasCurrentMeasPortn OBJECT-TYPE
	SYNTAX  INTEGER (0..65535)
	MAX-ACCESS read-only
	STATUS current
	DESCRIPTION
        "
        Line Optical Module Laser Bias 
        :This OID gives the bias value
         of the XFP or OTX plugged in line 
        , read from the DDM (Digital Diagnostic 
        Monitoring) (Bias = AV/500) (Unit 
        = mA)  <Help>  This measure gives 
        the bias of the line transceiver
        "
	::= { pm1004mMesrxfp1LoBiasCurrentMeasEntry 2 }


--- *********************************************************
---     TABLE for the pm1004mMesrxfp1LoTxPowerMeas articles
--- *********************************************************

pm1004mMesrxfp1LoTxPowerMeasTable OBJECT-TYPE
	SYNTAX  SEQUENCE OF Pm1004mMesrxfp1LoTxPowerMeasEntry
	MAX-ACCESS not-accessible
	STATUS current
	DESCRIPTION
        "
        List of pm1004mMesrxfp1LoTxPowerMeas 
        Article
        "
	::= { pm1004mMesrLine 211 }


pm1004mMesrxfp1LoTxPowerMeasEntry OBJECT-TYPE
	SYNTAX Pm1004mMesrxfp1LoTxPowerMeasEntry
	MAX-ACCESS not-accessible
	STATUS current
	DESCRIPTION
        "
        Row definition for the pm1004mMesrxfp1LoTxPowerMeas 
        table
        "
	INDEX   { pm1004mMesrxfp1LoTxPowerMeasIndex }
	::= { pm1004mMesrxfp1LoTxPowerMeasTable 1 }


Pm1004mMesrxfp1LoTxPowerMeasEntry ::=
	SEQUENCE {
	pm1004mMesrxfp1LoTxPowerMeasIndex
		INTEGER,
	pm1004mMesrxfp1LoTxPowerMeasPortn
		INTEGER 
	}


pm1004mMesrxfp1LoTxPowerMeasIndex OBJECT-TYPE
	SYNTAX  INTEGER(0..128)
	MAX-ACCESS  read-only
	STATUS current
	DESCRIPTION
        "
        Index definition for the pm1004mMesrxfp1LoTxPowerMeas 
        table
        "
	::= { pm1004mMesrxfp1LoTxPowerMeasEntry 1 }


pm1004mMesrxfp1LoTxPowerMeasPortn OBJECT-TYPE
	SYNTAX  INTEGER (0..65535)
	MAX-ACCESS read-only
	STATUS current
	DESCRIPTION
        "
        Line Optical Module Tx Power :This 
        OID gives the transmit power value 
        of the XFP or OTX plugged in line 
        , read from the DDM (Digital  
         Diagnostic Monitoring) (Power
         = 10*log(AV)-40) (Unit = dBm)
          <Help>  This measure gives the 
        Tx optical power of the line transceiver
        "
	::= { pm1004mMesrxfp1LoTxPowerMeasEntry 2 }


--- *********************************************************
---     TABLE for the pm1004mMesrxfp1LiRxPowerMeas articles
--- *********************************************************

pm1004mMesrxfp1LiRxPowerMeasTable OBJECT-TYPE
	SYNTAX  SEQUENCE OF Pm1004mMesrxfp1LiRxPowerMeasEntry
	MAX-ACCESS not-accessible
	STATUS current
	DESCRIPTION
        "
        List of pm1004mMesrxfp1LiRxPowerMeas 
        Article
        "
	::= { pm1004mMesrLine 212 }


pm1004mMesrxfp1LiRxPowerMeasEntry OBJECT-TYPE
	SYNTAX Pm1004mMesrxfp1LiRxPowerMeasEntry
	MAX-ACCESS not-accessible
	STATUS current
	DESCRIPTION
        "
        Row definition for the pm1004mMesrxfp1LiRxPowerMeas 
        table
        "
	INDEX   { pm1004mMesrxfp1LiRxPowerMeasIndex }
	::= { pm1004mMesrxfp1LiRxPowerMeasTable 1 }


Pm1004mMesrxfp1LiRxPowerMeasEntry ::=
	SEQUENCE {
	pm1004mMesrxfp1LiRxPowerMeasIndex
		INTEGER,
	pm1004mMesrxfp1LiRxPowerMeasPortn
		INTEGER 
	}


pm1004mMesrxfp1LiRxPowerMeasIndex OBJECT-TYPE
	SYNTAX  INTEGER(0..128)
	MAX-ACCESS  read-only
	STATUS current
	DESCRIPTION
        "
        Index definition for the pm1004mMesrxfp1LiRxPowerMeas 
        table
        "
	::= { pm1004mMesrxfp1LiRxPowerMeasEntry 1 }


pm1004mMesrxfp1LiRxPowerMeasPortn OBJECT-TYPE
	SYNTAX  INTEGER (0..65535)
	MAX-ACCESS read-only
	STATUS current
	DESCRIPTION
        "
        Line Optical Module Rx Power :This 
        OID gives the receive power value 
        of the XFP or OTX plugged in line 
        , read from the DDM (Digital Diagnostic 
        Monitoring) (Power = 10*log(AV)-40) 
        (Unit = dBm)  <Help>  This measure 
        gives the Rx optical power of the 
        line transceiver
        "
	::= { pm1004mMesrxfp1LiRxPowerMeasEntry 2 }


--- *********************************************************
---     TABLE for the pm1004mMesrxfp1LxAux1Meas articles
--- *********************************************************

pm1004mMesrxfp1LxAux1MeasTable OBJECT-TYPE
	SYNTAX  SEQUENCE OF Pm1004mMesrxfp1LxAux1MeasEntry
	MAX-ACCESS not-accessible
	STATUS deprecated
	DESCRIPTION
        "
        List of pm1004mMesrxfp1LxAux1Meas 
        Article
        "
	::= { pm1004mMesrLine 213 }


pm1004mMesrxfp1LxAux1MeasEntry OBJECT-TYPE
	SYNTAX Pm1004mMesrxfp1LxAux1MeasEntry
	MAX-ACCESS not-accessible
	STATUS deprecated
	DESCRIPTION
        "
        Row definition for the pm1004mMesrxfp1LxAux1Meas 
        table
        "
	INDEX   { pm1004mMesrxfp1LxAux1MeasIndex }
	::= { pm1004mMesrxfp1LxAux1MeasTable 1 }


Pm1004mMesrxfp1LxAux1MeasEntry ::=
	SEQUENCE {
	pm1004mMesrxfp1LxAux1MeasIndex
		INTEGER,
	pm1004mMesrxfp1LxAux1MeasPortn
		INTEGER 
	}


pm1004mMesrxfp1LxAux1MeasIndex OBJECT-TYPE
	SYNTAX  INTEGER(0..128)
	MAX-ACCESS  read-only
	STATUS deprecated
	DESCRIPTION
        "
        Index definition for the pm1004mMesrxfp1LxAux1Meas 
        table
        "
	::= { pm1004mMesrxfp1LxAux1MeasEntry 1 }


pm1004mMesrxfp1LxAux1MeasPortn OBJECT-TYPE
	SYNTAX  INTEGER (0..65535)
	MAX-ACCESS read-only
	STATUS deprecated
	DESCRIPTION
        "
        Not Used :This OID gives the receive 
        power value read in the DDM (Digital 
        Diagnostic Monitoring) of the XFP 
        or OTX plugged in line  (Unit = 
        ?)
        "
	::= { pm1004mMesrxfp1LxAux1MeasEntry 2 }


--- *********************************************************
---     TABLE for the pm1004mMesrxfp1LxAux2Meas articles
--- *********************************************************

pm1004mMesrxfp1LxAux2MeasTable OBJECT-TYPE
	SYNTAX  SEQUENCE OF Pm1004mMesrxfp1LxAux2MeasEntry
	MAX-ACCESS not-accessible
	STATUS deprecated
	DESCRIPTION
        "
        List of pm1004mMesrxfp1LxAux2Meas 
        Article
        "
	::= { pm1004mMesrLine 214 }


pm1004mMesrxfp1LxAux2MeasEntry OBJECT-TYPE
	SYNTAX Pm1004mMesrxfp1LxAux2MeasEntry
	MAX-ACCESS not-accessible
	STATUS deprecated
	DESCRIPTION
        "
        Row definition for the pm1004mMesrxfp1LxAux2Meas 
        table
        "
	INDEX   { pm1004mMesrxfp1LxAux2MeasIndex }
	::= { pm1004mMesrxfp1LxAux2MeasTable 1 }


Pm1004mMesrxfp1LxAux2MeasEntry ::=
	SEQUENCE {
	pm1004mMesrxfp1LxAux2MeasIndex
		INTEGER,
	pm1004mMesrxfp1LxAux2MeasPortn
		INTEGER 
	}


pm1004mMesrxfp1LxAux2MeasIndex OBJECT-TYPE
	SYNTAX  INTEGER(0..128)
	MAX-ACCESS  read-only
	STATUS deprecated
	DESCRIPTION
        "
        Index definition for the pm1004mMesrxfp1LxAux2Meas 
        table
        "
	::= { pm1004mMesrxfp1LxAux2MeasEntry 1 }


pm1004mMesrxfp1LxAux2MeasPortn OBJECT-TYPE
	SYNTAX  INTEGER (0..65535)
	MAX-ACCESS read-only
	STATUS deprecated
	DESCRIPTION
        "
        Not Used :This OID gives the receive 
        power value read in the DDM (Digital 
        Diagnostic Monitoring) of the XFP 
        or OTX plugged in line  (Unit = 
        ?)
        "
	::= { pm1004mMesrxfp1LxAux2MeasEntry 2 }


--- *********************************************************
---     TABLE for the pm1004mMesrotx1Aging articles
--- *********************************************************

pm1004mMesrotx1AgingTable OBJECT-TYPE
	SYNTAX  SEQUENCE OF Pm1004mMesrotx1AgingEntry
	MAX-ACCESS not-accessible
	STATUS current
	DESCRIPTION
        "
        List of pm1004mMesrotx1Aging Article
        "
	::= { pm1004mMesrLine 224 }


pm1004mMesrotx1AgingEntry OBJECT-TYPE
	SYNTAX Pm1004mMesrotx1AgingEntry
	MAX-ACCESS not-accessible
	STATUS current
	DESCRIPTION
        "
        Row definition for the pm1004mMesrotx1Aging 
        table
        "
	INDEX   { pm1004mMesrotx1AgingIndex }
	::= { pm1004mMesrotx1AgingTable 1 }


Pm1004mMesrotx1AgingEntry ::=
	SEQUENCE {
	pm1004mMesrotx1AgingIndex
		INTEGER,
	pm1004mMesrotx1AgingPortn
		INTEGER 
	}


pm1004mMesrotx1AgingIndex OBJECT-TYPE
	SYNTAX  INTEGER(0..128)
	MAX-ACCESS  read-only
	STATUS current
	DESCRIPTION
        "
        Index definition for the pm1004mMesrotx1Aging 
        table
        "
	::= { pm1004mMesrotx1AgingEntry 1 }


pm1004mMesrotx1AgingPortn OBJECT-TYPE
	SYNTAX  INTEGER (0..65535)
	MAX-ACCESS read-only
	STATUS current
	DESCRIPTION
        "
        Line OTX TLH Aging :This OID gives 
        the aging of the Line OTX TLH,
         read from the DDM (Digital Diagnostic 
        Monitoring)  (Aging = AV) (Unit 
        = %)  <Help>  This measure gives 
        the aging of the Line OTX TLH
        "
	::= { pm1004mMesrotx1AgingEntry 2 }


--- *********************************************************
---     TABLE for the pm1004mMesrotx1LaserTemperature articles
--- *********************************************************

pm1004mMesrotx1LaserTemperatureTable OBJECT-TYPE
	SYNTAX  SEQUENCE OF Pm1004mMesrotx1LaserTemperatureEntry
	MAX-ACCESS not-accessible
	STATUS deprecated
	DESCRIPTION
        "
        List of pm1004mMesrotx1LaserTemperature 
        Article
        "
	::= { pm1004mMesrLine 225 }


pm1004mMesrotx1LaserTemperatureEntry OBJECT-TYPE
	SYNTAX Pm1004mMesrotx1LaserTemperatureEntry
	MAX-ACCESS not-accessible
	STATUS deprecated
	DESCRIPTION
        "
        Row definition for the pm1004mMesrotx1LaserTemperature 
        table
        "
	INDEX   { pm1004mMesrotx1LaserTemperatureIndex }
	::= { pm1004mMesrotx1LaserTemperatureTable 1 }


Pm1004mMesrotx1LaserTemperatureEntry ::=
	SEQUENCE {
	pm1004mMesrotx1LaserTemperatureIndex
		INTEGER,
	pm1004mMesrotx1LaserTemperaturePortn
		INTEGER 
	}


pm1004mMesrotx1LaserTemperatureIndex OBJECT-TYPE
	SYNTAX  INTEGER(0..128)
	MAX-ACCESS  read-only
	STATUS deprecated
	DESCRIPTION
        "
        Index definition for the pm1004mMesrotx1LaserTemperature 
        table
        "
	::= { pm1004mMesrotx1LaserTemperatureEntry 1 }


pm1004mMesrotx1LaserTemperaturePortn OBJECT-TYPE
	SYNTAX  INTEGER (0..65535)
	MAX-ACCESS read-only
	STATUS deprecated
	DESCRIPTION
        "
        Line OTX TLH Laser Temperature 
        :This OID gives the laser temperature 
        of the Line OTX TLH, read from
         the DDM (Digital Diagnostic Monitoring) 
         (Temperature = AV/256) (Unit = 
        C)  <Help>  This measure gives
         the laser temperature of the Line 
        OTX TLH
        "
	::= { pm1004mMesrotx1LaserTemperatureEntry 2 }


--- *********************************************************
---     TABLE for the pm1004mMesrotx1FreqDeviation articles
--- *********************************************************

pm1004mMesrotx1FreqDeviationTable OBJECT-TYPE
	SYNTAX  SEQUENCE OF Pm1004mMesrotx1FreqDeviationEntry
	MAX-ACCESS not-accessible
	STATUS current
	DESCRIPTION
        "
        List of pm1004mMesrotx1FreqDeviation 
        Article
        "
	::= { pm1004mMesrLine 226 }


pm1004mMesrotx1FreqDeviationEntry OBJECT-TYPE
	SYNTAX Pm1004mMesrotx1FreqDeviationEntry
	MAX-ACCESS not-accessible
	STATUS current
	DESCRIPTION
        "
        Row definition for the pm1004mMesrotx1FreqDeviation 
        table
        "
	INDEX   { pm1004mMesrotx1FreqDeviationIndex }
	::= { pm1004mMesrotx1FreqDeviationTable 1 }


Pm1004mMesrotx1FreqDeviationEntry ::=
	SEQUENCE {
	pm1004mMesrotx1FreqDeviationIndex
		INTEGER,
	pm1004mMesrotx1FreqDeviationPortn
		INTEGER 
	}


pm1004mMesrotx1FreqDeviationIndex OBJECT-TYPE
	SYNTAX  INTEGER(0..128)
	MAX-ACCESS  read-only
	STATUS current
	DESCRIPTION
        "
        Index definition for the pm1004mMesrotx1FreqDeviation 
        table
        "
	::= { pm1004mMesrotx1FreqDeviationEntry 1 }


pm1004mMesrotx1FreqDeviationPortn OBJECT-TYPE
	SYNTAX  INTEGER (0..65535)
	MAX-ACCESS read-only
	STATUS current
	DESCRIPTION
        "
        Line OTX TLH Frequency Deviation 
        :This OID gives the frequency deviation 
        of the Line OTX TLH, read from
         the DDM (Digital Diagnostic Monitoring) 
        (Deviation = (AV-32768)*100)  (Unit 
        = MHz)  <Help>  This measure gives 
        the frequency deviation of the
         Line OTX TLH
        "
	::= { pm1004mMesrotx1FreqDeviationEntry 2 }


--- *********************************************************
---     TABLE for the pm1004mMesrotx1LaserWvlength articles
--- *********************************************************

pm1004mMesrotx1LaserWvlengthTable OBJECT-TYPE
	SYNTAX  SEQUENCE OF Pm1004mMesrotx1LaserWvlengthEntry
	MAX-ACCESS not-accessible
	STATUS current
	DESCRIPTION
        "
        List of pm1004mMesrotx1LaserWvlength 
        Article
        "
	::= { pm1004mMesrLine 227 }


pm1004mMesrotx1LaserWvlengthEntry OBJECT-TYPE
	SYNTAX Pm1004mMesrotx1LaserWvlengthEntry
	MAX-ACCESS not-accessible
	STATUS current
	DESCRIPTION
        "
        Row definition for the pm1004mMesrotx1LaserWvlength 
        table
        "
	INDEX   { pm1004mMesrotx1LaserWvlengthIndex }
	::= { pm1004mMesrotx1LaserWvlengthTable 1 }


Pm1004mMesrotx1LaserWvlengthEntry ::=
	SEQUENCE {
	pm1004mMesrotx1LaserWvlengthIndex
		INTEGER,
	pm1004mMesrotx1LaserWvlengthPortn
		INTEGER 
	}


pm1004mMesrotx1LaserWvlengthIndex OBJECT-TYPE
	SYNTAX  INTEGER(0..128)
	MAX-ACCESS  read-only
	STATUS current
	DESCRIPTION
        "
        Index definition for the pm1004mMesrotx1LaserWvlength 
        table
        "
	::= { pm1004mMesrotx1LaserWvlengthEntry 1 }


pm1004mMesrotx1LaserWvlengthPortn OBJECT-TYPE
	SYNTAX  INTEGER (0..65535)
	MAX-ACCESS read-only
	STATUS current
	DESCRIPTION
        "
        Line Optical Module Wavelength 
        :This OID gives the laser wavelength 
        of the Line OTX TLH, read from
         the DDM (Digital Diagnostic Monitoring) 
         (Wavelength=299792458/((193,100+(AV-32768 
        )*12,5)*10 3)) (Unit = nm)  <Help> 
         This measure gives the laser wavelength 
        of the Line OTX TLH
        "
	::= { pm1004mMesrotx1LaserWvlengthEntry 2 }







--- *****************************************************
--- $$$$$$$$$$$$$$$$$$$$$$$$$$$$$$$$$$$$$$$$$$$$$$$$$$$$$
---     PERFORMANCE
--- $$$$$$$$$$$$$$$$$$$$$$$$$$$$$$$$$$$$$$$$$$$$$$$$$$$$$
--- *****************************************************



--- *********************************************************
---     TABLE for the pm1004mPerfUpCurrent15Cnt articles
--- *********************************************************

pm1004mPerfUpCurrent15CntTable OBJECT-TYPE
	SYNTAX  SEQUENCE OF Pm1004mPerfUpCurrent15CntEntry
	MAX-ACCESS not-accessible
	STATUS current
	DESCRIPTION
        "
        List of pm1004mPerfUpCurrent15Cnt 
        Article
        "
	::= { pm1004mMonClientPerformance 16 }


pm1004mPerfUpCurrent15CntEntry OBJECT-TYPE
	SYNTAX Pm1004mPerfUpCurrent15CntEntry
	MAX-ACCESS not-accessible
	STATUS current
	DESCRIPTION
        "
        Row definition for the pm1004mPerfUpCurrent15Cnt 
        table
        "
	INDEX   { pm1004mPerfUpCurrent15CntIndex }
	::= { pm1004mPerfUpCurrent15CntTable 1 }


Pm1004mPerfUpCurrent15CntEntry ::=
	SEQUENCE {
	pm1004mPerfUpCurrent15CntIndex
		INTEGER,
	pm1004mPerfUpCurrent15CntInvCvPortn
		EkiOnOff,
	pm1004mPerfUpCurrent15CntCvValuePortn
		Unsigned32,
	pm1004mPerfUpCurrent15CntInvEsPortn
		EkiOnOff,
	pm1004mPerfUpCurrent15CntEsValuePortn
		Unsigned32,
	pm1004mPerfUpCurrent15CntInvSesPortn
		EkiOnOff,
	pm1004mPerfUpCurrent15CntSesValuePortn
		Unsigned32,
	pm1004mPerfUpCurrent15CntInvSefsPortn
		EkiOnOff,
	pm1004mPerfUpCurrent15CntSefsValuePortn
		Unsigned32,
	pm1004mPerfUpCurrent15CntInvUasPortn
		EkiOnOff,
	pm1004mPerfUpCurrent15CntUasValuePortn
		Unsigned32
	}


pm1004mPerfUpCurrent15CntIndex OBJECT-TYPE
	SYNTAX  INTEGER(0..128)
	MAX-ACCESS  read-only
	STATUS current
	DESCRIPTION
        "
        Index definition for the pm1004mPerfUpCurrent15Cnt 
        table
        "
	::= { pm1004mPerfUpCurrent15CntEntry 1 }


pm1004mPerfUpCurrent15CntInvCvPortn OBJECT-TYPE
	SYNTAX  EkiOnOff
	MAX-ACCESS read-only
	STATUS current
	DESCRIPTION
        "
        Current 15-min CV counter inv. 
        :This OID indicates that the current 
        15-min Coding Violation counter 
        is invalid
        "
	::= { pm1004mPerfUpCurrent15CntEntry 2 }


pm1004mPerfUpCurrent15CntCvValuePortn OBJECT-TYPE
	SYNTAX  Unsigned32
	MAX-ACCESS read-only
	STATUS current
	DESCRIPTION
        "
        Current 15-min CV counter :This 
        OID gives the current 15-min Coding 
        Violation counter value
        "
	::= { pm1004mPerfUpCurrent15CntEntry 3 }


pm1004mPerfUpCurrent15CntInvEsPortn OBJECT-TYPE
	SYNTAX  EkiOnOff
	MAX-ACCESS read-only
	STATUS current
	DESCRIPTION
        "
        Current 15-min ES counter inv. 
        :This OID indicates that the current 
        15-min Errored Second counter is 
        invalid
        "
	::= { pm1004mPerfUpCurrent15CntEntry 4 }


pm1004mPerfUpCurrent15CntEsValuePortn OBJECT-TYPE
	SYNTAX  Unsigned32
	MAX-ACCESS read-only
	STATUS current
	DESCRIPTION
        "
        Current 15-min ES counter :This 
        OID gives the current 15-min Errored 
        Second counter value
        "
	::= { pm1004mPerfUpCurrent15CntEntry 5 }


pm1004mPerfUpCurrent15CntInvSesPortn OBJECT-TYPE
	SYNTAX  EkiOnOff
	MAX-ACCESS read-only
	STATUS current
	DESCRIPTION
        "
        Current 15-min SES counter inv. 
        :This OID indicates that the current 
        15-min severely Errored Second
         counter is invalid
        "
	::= { pm1004mPerfUpCurrent15CntEntry 6 }


pm1004mPerfUpCurrent15CntSesValuePortn OBJECT-TYPE
	SYNTAX  Unsigned32
	MAX-ACCESS read-only
	STATUS current
	DESCRIPTION
        "
        Current 15-min SES counter :This 
        OID gives the current 15-min severely 
        Errored Second counter value
        "
	::= { pm1004mPerfUpCurrent15CntEntry 7 }


pm1004mPerfUpCurrent15CntInvSefsPortn OBJECT-TYPE
	SYNTAX  EkiOnOff
	MAX-ACCESS read-only
	STATUS current
	DESCRIPTION
        "
        Current 15-min SEFS counter inv. 
        :This OID indicates that the current 
        15-min severely Errored Framing 
        Second counter is invalid
        "
	::= { pm1004mPerfUpCurrent15CntEntry 8 }


pm1004mPerfUpCurrent15CntSefsValuePortn OBJECT-TYPE
	SYNTAX  Unsigned32
	MAX-ACCESS read-only
	STATUS current
	DESCRIPTION
        "
        Current 15-min SEFS counter :This 
        OID gives the current 15-min severely 
        Errored Framing Second counter
         value
        "
	::= { pm1004mPerfUpCurrent15CntEntry 9 }


pm1004mPerfUpCurrent15CntInvUasPortn OBJECT-TYPE
	SYNTAX  EkiOnOff
	MAX-ACCESS read-only
	STATUS current
	DESCRIPTION
        "
        Current 15-min UAS counter inv. 
        :This OID indicates that the current 
        15-min UnAvailable Second counter 
        is invalid
        "
	::= { pm1004mPerfUpCurrent15CntEntry 10 }


pm1004mPerfUpCurrent15CntUasValuePortn OBJECT-TYPE
	SYNTAX  Unsigned32
	MAX-ACCESS read-only
	STATUS current
	DESCRIPTION
        "
        Current 15-min UAS counter :This 
        OID gives the current 15-min UnAvailable 
        Second counter value
        "
	::= { pm1004mPerfUpCurrent15CntEntry 11 }


--- *********************************************************
---     TABLE for the pm1004mPerfUpPast15Cnt articles
--- *********************************************************

pm1004mPerfUpPast15CntTable OBJECT-TYPE
	SYNTAX  SEQUENCE OF Pm1004mPerfUpPast15CntEntry
	MAX-ACCESS not-accessible
	STATUS current
	DESCRIPTION
        "
        List of pm1004mPerfUpPast15Cnt 
        Article
        "
	::= { pm1004mMonClientPerformance 24 }


pm1004mPerfUpPast15CntEntry OBJECT-TYPE
	SYNTAX Pm1004mPerfUpPast15CntEntry
	MAX-ACCESS not-accessible
	STATUS current
	DESCRIPTION
        "
        Row definition for the pm1004mPerfUpPast15Cnt 
        table
        "
	INDEX   { pm1004mPerfUpPast15CntIndex }
	::= { pm1004mPerfUpPast15CntTable 1 }


Pm1004mPerfUpPast15CntEntry ::=
	SEQUENCE {
	pm1004mPerfUpPast15CntIndex
		INTEGER,
	pm1004mPerfUpPast15CntInvCvPortn
		EkiOnOff,
	pm1004mPerfUpPast15CntCvValuePortn
		Unsigned32,
	pm1004mPerfUpPast15CntInvEsPortn
		EkiOnOff,
	pm1004mPerfUpPast15CntEsValuePortn
		Unsigned32,
	pm1004mPerfUpPast15CntInvSesPortn
		EkiOnOff,
	pm1004mPerfUpPast15CntSesValuePortn
		Unsigned32,
	pm1004mPerfUpPast15CntInvSefsPortn
		EkiOnOff,
	pm1004mPerfUpPast15CntSefsValuePortn
		Unsigned32,
	pm1004mPerfUpPast15CntInvUasPortn
		EkiOnOff,
	pm1004mPerfUpPast15CntUasValuePortn
		Unsigned32
	}


pm1004mPerfUpPast15CntIndex OBJECT-TYPE
	SYNTAX  INTEGER(0..128)
	MAX-ACCESS  read-only
	STATUS current
	DESCRIPTION
        "
        Index definition for the pm1004mPerfUpPast15Cnt 
        table
        "
	::= { pm1004mPerfUpPast15CntEntry 1 }


pm1004mPerfUpPast15CntInvCvPortn OBJECT-TYPE
	SYNTAX  EkiOnOff
	MAX-ACCESS read-only
	STATUS current
	DESCRIPTION
        "
        Previous 15-min CV counter inv. 
        :This OID indicates that the previous 
        15-min Coding Violation counter 
        is invalid
        "
	::= { pm1004mPerfUpPast15CntEntry 2 }


pm1004mPerfUpPast15CntCvValuePortn OBJECT-TYPE
	SYNTAX  Unsigned32
	MAX-ACCESS read-only
	STATUS current
	DESCRIPTION
        "
        Previous 15-min CV counter :This 
        OID gives the previous 15-min Coding 
        Violation counter value
        "
	::= { pm1004mPerfUpPast15CntEntry 3 }


pm1004mPerfUpPast15CntInvEsPortn OBJECT-TYPE
	SYNTAX  EkiOnOff
	MAX-ACCESS read-only
	STATUS current
	DESCRIPTION
        "
        Previous 15-min ES counter inv. 
        :This OID indicates that the previous 
        15-min Errored Second counter is 
        invalid
        "
	::= { pm1004mPerfUpPast15CntEntry 4 }


pm1004mPerfUpPast15CntEsValuePortn OBJECT-TYPE
	SYNTAX  Unsigned32
	MAX-ACCESS read-only
	STATUS current
	DESCRIPTION
        "
        Previous 15-min ES counter :This 
        OID gives the previous 15-min Errored 
        Second counter value
        "
	::= { pm1004mPerfUpPast15CntEntry 5 }


pm1004mPerfUpPast15CntInvSesPortn OBJECT-TYPE
	SYNTAX  EkiOnOff
	MAX-ACCESS read-only
	STATUS current
	DESCRIPTION
        "
        Previous 15-min SES counter inv. 
        :This OID indicates that the previous 
        15-min severely Errored Second
         counter is invalid
        "
	::= { pm1004mPerfUpPast15CntEntry 6 }


pm1004mPerfUpPast15CntSesValuePortn OBJECT-TYPE
	SYNTAX  Unsigned32
	MAX-ACCESS read-only
	STATUS current
	DESCRIPTION
        "
        Previous 15-min SES counter :This 
        OID gives the previous 15-min severely 
        Errored Second counter value
        "
	::= { pm1004mPerfUpPast15CntEntry 7 }


pm1004mPerfUpPast15CntInvSefsPortn OBJECT-TYPE
	SYNTAX  EkiOnOff
	MAX-ACCESS read-only
	STATUS current
	DESCRIPTION
        "
        Previous 15-min SEFS counter inv. 
        :This OID indicates that the previous 
        15-min severely Errored Framing 
        Second counter is invalid
        "
	::= { pm1004mPerfUpPast15CntEntry 8 }


pm1004mPerfUpPast15CntSefsValuePortn OBJECT-TYPE
	SYNTAX  Unsigned32
	MAX-ACCESS read-only
	STATUS current
	DESCRIPTION
        "
        Previous 15-min SEFS counter :This 
        OID gives the previous 15-min severely 
        Errored Framing Second counter
         value
        "
	::= { pm1004mPerfUpPast15CntEntry 9 }


pm1004mPerfUpPast15CntInvUasPortn OBJECT-TYPE
	SYNTAX  EkiOnOff
	MAX-ACCESS read-only
	STATUS current
	DESCRIPTION
        "
        Previous 15-min UAS counter inv. 
        :This OID indicates that the previous 
        15-min UnAvailable Second counter 
        is invalid
        "
	::= { pm1004mPerfUpPast15CntEntry 10 }


pm1004mPerfUpPast15CntUasValuePortn OBJECT-TYPE
	SYNTAX  Unsigned32
	MAX-ACCESS read-only
	STATUS current
	DESCRIPTION
        "
        Previous 15-min UAS counter :This 
        OID gives the previous 15-min UnAvailable 
        Second counter value
        "
	::= { pm1004mPerfUpPast15CntEntry 11 }


--- *********************************************************
---     TABLE for the pm1004mPerfUpCurrent24Cnt articles
--- *********************************************************

pm1004mPerfUpCurrent24CntTable OBJECT-TYPE
	SYNTAX  SEQUENCE OF Pm1004mPerfUpCurrent24CntEntry
	MAX-ACCESS not-accessible
	STATUS current
	DESCRIPTION
        "
        List of pm1004mPerfUpCurrent24Cnt 
        Article
        "
	::= { pm1004mMonClientPerformance 32 }


pm1004mPerfUpCurrent24CntEntry OBJECT-TYPE
	SYNTAX Pm1004mPerfUpCurrent24CntEntry
	MAX-ACCESS not-accessible
	STATUS current
	DESCRIPTION
        "
        Row definition for the pm1004mPerfUpCurrent24Cnt 
        table
        "
	INDEX   { pm1004mPerfUpCurrent24CntIndex }
	::= { pm1004mPerfUpCurrent24CntTable 1 }


Pm1004mPerfUpCurrent24CntEntry ::=
	SEQUENCE {
	pm1004mPerfUpCurrent24CntIndex
		INTEGER,
	pm1004mPerfUpCurrent24CntInvCvPortn
		EkiOnOff,
	pm1004mPerfUpCurrent24CntCvValuePortn
		Unsigned32,
	pm1004mPerfUpCurrent24CntInvEsPortn
		EkiOnOff,
	pm1004mPerfUpCurrent24CntEsValuePortn
		Unsigned32,
	pm1004mPerfUpCurrent24CntInvSesPortn
		EkiOnOff,
	pm1004mPerfUpCurrent24CntSesValuePortn
		Unsigned32,
	pm1004mPerfUpCurrent24CntInvSefsPortn
		EkiOnOff,
	pm1004mPerfUpCurrent24CntSefsValuePortn
		Unsigned32,
	pm1004mPerfUpCurrent24CntInvUasPortn
		EkiOnOff,
	pm1004mPerfUpCurrent24CntUasValuePortn
		Unsigned32
	}


pm1004mPerfUpCurrent24CntIndex OBJECT-TYPE
	SYNTAX  INTEGER(0..128)
	MAX-ACCESS  read-only
	STATUS current
	DESCRIPTION
        "
        Index definition for the pm1004mPerfUpCurrent24Cnt 
        table
        "
	::= { pm1004mPerfUpCurrent24CntEntry 1 }


pm1004mPerfUpCurrent24CntInvCvPortn OBJECT-TYPE
	SYNTAX  EkiOnOff
	MAX-ACCESS read-only
	STATUS current
	DESCRIPTION
        "
        Current 24-hours CV counter inv. 
        :This OID indicates that the current 
        24-hours Coding Violation counter 
        is invalid
        "
	::= { pm1004mPerfUpCurrent24CntEntry 2 }


pm1004mPerfUpCurrent24CntCvValuePortn OBJECT-TYPE
	SYNTAX  Unsigned32
	MAX-ACCESS read-only
	STATUS current
	DESCRIPTION
        "
        Current 24-hours CV counter :This 
        OID gives the current 24-hours
         Coding Violation counter value
        "
	::= { pm1004mPerfUpCurrent24CntEntry 3 }


pm1004mPerfUpCurrent24CntInvEsPortn OBJECT-TYPE
	SYNTAX  EkiOnOff
	MAX-ACCESS read-only
	STATUS current
	DESCRIPTION
        "
        Current 24-hours ES counter inv. 
        :This OID indicates that the current 
        24-hours Errored Second counter 
        is invalid
        "
	::= { pm1004mPerfUpCurrent24CntEntry 4 }


pm1004mPerfUpCurrent24CntEsValuePortn OBJECT-TYPE
	SYNTAX  Unsigned32
	MAX-ACCESS read-only
	STATUS current
	DESCRIPTION
        "
        Current 24-hours ES counter :This 
        OID gives the current 24-hours
         Errored Second counter value
        "
	::= { pm1004mPerfUpCurrent24CntEntry 5 }


pm1004mPerfUpCurrent24CntInvSesPortn OBJECT-TYPE
	SYNTAX  EkiOnOff
	MAX-ACCESS read-only
	STATUS current
	DESCRIPTION
        "
        Current 24-hours SES counter inv. 
        :This OID indicates that the current 
        24-hours severely Errored Second 
        counter is invalid
        "
	::= { pm1004mPerfUpCurrent24CntEntry 6 }


pm1004mPerfUpCurrent24CntSesValuePortn OBJECT-TYPE
	SYNTAX  Unsigned32
	MAX-ACCESS read-only
	STATUS current
	DESCRIPTION
        "
        Current 24-hours SES counter :This 
        OID gives the current 24-hours
         severely Errored Second counter 
        value
        "
	::= { pm1004mPerfUpCurrent24CntEntry 7 }


pm1004mPerfUpCurrent24CntInvSefsPortn OBJECT-TYPE
	SYNTAX  EkiOnOff
	MAX-ACCESS read-only
	STATUS current
	DESCRIPTION
        "
        Current 24-hours SEFS counter
         inv. :This OID indicates that
         the current 24-hours severely
         Errored Framing Second counter 
        is invalid
        "
	::= { pm1004mPerfUpCurrent24CntEntry 8 }


pm1004mPerfUpCurrent24CntSefsValuePortn OBJECT-TYPE
	SYNTAX  Unsigned32
	MAX-ACCESS read-only
	STATUS current
	DESCRIPTION
        "
        Current 24-hours SEFS counter
         :This OID gives the current 24-hours 
        severely Errored Framing Second 
        counter value
        "
	::= { pm1004mPerfUpCurrent24CntEntry 9 }


pm1004mPerfUpCurrent24CntInvUasPortn OBJECT-TYPE
	SYNTAX  EkiOnOff
	MAX-ACCESS read-only
	STATUS current
	DESCRIPTION
        "
        Current 24-hours UAS counter inv. 
        :This OID indicates that the current 
        24-hours UnAvailable Second counter 
        is invalid
        "
	::= { pm1004mPerfUpCurrent24CntEntry 10 }


pm1004mPerfUpCurrent24CntUasValuePortn OBJECT-TYPE
	SYNTAX  Unsigned32
	MAX-ACCESS read-only
	STATUS current
	DESCRIPTION
        "
        Current 24-hours UAS counter :This 
        OID gives the current 24-hours
         UnAvailable Second counter value
        "
	::= { pm1004mPerfUpCurrent24CntEntry 11 }


--- *********************************************************
---     TABLE for the pm1004mPerfUpPast24Cnt articles
--- *********************************************************

pm1004mPerfUpPast24CntTable OBJECT-TYPE
	SYNTAX  SEQUENCE OF Pm1004mPerfUpPast24CntEntry
	MAX-ACCESS not-accessible
	STATUS current
	DESCRIPTION
        "
        List of pm1004mPerfUpPast24Cnt 
        Article
        "
	::= { pm1004mMonClientPerformance 40 }


pm1004mPerfUpPast24CntEntry OBJECT-TYPE
	SYNTAX Pm1004mPerfUpPast24CntEntry
	MAX-ACCESS not-accessible
	STATUS current
	DESCRIPTION
        "
        Row definition for the pm1004mPerfUpPast24Cnt 
        table
        "
	INDEX   { pm1004mPerfUpPast24CntIndex }
	::= { pm1004mPerfUpPast24CntTable 1 }


Pm1004mPerfUpPast24CntEntry ::=
	SEQUENCE {
	pm1004mPerfUpPast24CntIndex
		INTEGER,
	pm1004mPerfUpPast24CntInvCvPortn
		EkiOnOff,
	pm1004mPerfUpPast24CntCvValuePortn
		Unsigned32,
	pm1004mPerfUpPast24CntInvEsPortn
		EkiOnOff,
	pm1004mPerfUpPast24CntEsValuePortn
		Unsigned32,
	pm1004mPerfUpPast24CntInvSesPortn
		EkiOnOff,
	pm1004mPerfUpPast24CntSesValuePortn
		Unsigned32,
	pm1004mPerfUpPast24CntInvSefsPortn
		EkiOnOff,
	pm1004mPerfUpPast24CntSefsValuePortn
		Unsigned32,
	pm1004mPerfUpPast24CntInvUasPortn
		EkiOnOff,
	pm1004mPerfUpPast24CntUasValuePortn
		Unsigned32
	}


pm1004mPerfUpPast24CntIndex OBJECT-TYPE
	SYNTAX  INTEGER(0..128)
	MAX-ACCESS  read-only
	STATUS current
	DESCRIPTION
        "
        Index definition for the pm1004mPerfUpPast24Cnt 
        table
        "
	::= { pm1004mPerfUpPast24CntEntry 1 }


pm1004mPerfUpPast24CntInvCvPortn OBJECT-TYPE
	SYNTAX  EkiOnOff
	MAX-ACCESS read-only
	STATUS current
	DESCRIPTION
        "
        Previous 24-hours CV counter inv. 
        :This OID indicates that the previous 
        24-hours Coding Violation counter 
        is invalid
        "
	::= { pm1004mPerfUpPast24CntEntry 2 }


pm1004mPerfUpPast24CntCvValuePortn OBJECT-TYPE
	SYNTAX  Unsigned32
	MAX-ACCESS read-only
	STATUS current
	DESCRIPTION
        "
        Previous 24-hours CV counter :This 
        OID gives the previous 24-hours 
        Coding Violation counter value
        "
	::= { pm1004mPerfUpPast24CntEntry 3 }


pm1004mPerfUpPast24CntInvEsPortn OBJECT-TYPE
	SYNTAX  EkiOnOff
	MAX-ACCESS read-only
	STATUS current
	DESCRIPTION
        "
        Previous 24-hours ES counter inv. 
        :This OID indicates that the previous 
        24-hours Errored Second counter 
        is invalid
        "
	::= { pm1004mPerfUpPast24CntEntry 4 }


pm1004mPerfUpPast24CntEsValuePortn OBJECT-TYPE
	SYNTAX  Unsigned32
	MAX-ACCESS read-only
	STATUS current
	DESCRIPTION
        "
        Previous 24-hours ES counter :This 
        OID gives the previous 24-hours 
        Errored Second counter value
        "
	::= { pm1004mPerfUpPast24CntEntry 5 }


pm1004mPerfUpPast24CntInvSesPortn OBJECT-TYPE
	SYNTAX  EkiOnOff
	MAX-ACCESS read-only
	STATUS current
	DESCRIPTION
        "
        Previous 24-hours SES counter
         inv. :This OID indicates that
         the previous 24-hours severely 
        Errored Second counter is invalid
        "
	::= { pm1004mPerfUpPast24CntEntry 6 }


pm1004mPerfUpPast24CntSesValuePortn OBJECT-TYPE
	SYNTAX  Unsigned32
	MAX-ACCESS read-only
	STATUS current
	DESCRIPTION
        "
        Previous 24-hours SES counter
         :This OID gives the previous 24-hours 
        severely Errored Second counter 
        value
        "
	::= { pm1004mPerfUpPast24CntEntry 7 }


pm1004mPerfUpPast24CntInvSefsPortn OBJECT-TYPE
	SYNTAX  EkiOnOff
	MAX-ACCESS read-only
	STATUS current
	DESCRIPTION
        "
        Previous 24-hours SEFS counter 
        inv. :This OID indicates that the 
        previous 24-hours severely Errored 
        Framing Second counter is invalid
        "
	::= { pm1004mPerfUpPast24CntEntry 8 }


pm1004mPerfUpPast24CntSefsValuePortn OBJECT-TYPE
	SYNTAX  Unsigned32
	MAX-ACCESS read-only
	STATUS current
	DESCRIPTION
        "
        Previous 24-hours SEFS counter 
        :This OID gives the previous 24-hours 
        severely Errored Framing Second 
        counter value
        "
	::= { pm1004mPerfUpPast24CntEntry 9 }


pm1004mPerfUpPast24CntInvUasPortn OBJECT-TYPE
	SYNTAX  EkiOnOff
	MAX-ACCESS read-only
	STATUS current
	DESCRIPTION
        "
        Previous 24-hours UAS counter
         inv. :This OID indicates that
         the previous 24-hours UnAvailable 
        Second counter is invalid
        "
	::= { pm1004mPerfUpPast24CntEntry 10 }


pm1004mPerfUpPast24CntUasValuePortn OBJECT-TYPE
	SYNTAX  Unsigned32
	MAX-ACCESS read-only
	STATUS current
	DESCRIPTION
        "
        Previous 24-hours UAS counter
         :This OID gives the previous 24-hours 
        UnAvailable Second counter value
        "
	::= { pm1004mPerfUpPast24CntEntry 11 }


--- *********************************************************
---     TABLE for the pm1004mPerfLineCurrent15Cnt articles
--- *********************************************************

pm1004mPerfLineCurrent15CntTable OBJECT-TYPE
	SYNTAX  SEQUENCE OF Pm1004mPerfLineCurrent15CntEntry
	MAX-ACCESS not-accessible
	STATUS current
	DESCRIPTION
        "
        List of pm1004mPerfLineCurrent15Cnt 
        Article
        "
	::= { pm1004mMonLinePerformance 128 }


pm1004mPerfLineCurrent15CntEntry OBJECT-TYPE
	SYNTAX Pm1004mPerfLineCurrent15CntEntry
	MAX-ACCESS not-accessible
	STATUS current
	DESCRIPTION
        "
        Row definition for the pm1004mPerfLineCurrent15Cnt 
        table
        "
	INDEX   { pm1004mPerfLineCurrent15CntIndex }
	::= { pm1004mPerfLineCurrent15CntTable 1 }


Pm1004mPerfLineCurrent15CntEntry ::=
	SEQUENCE {
	pm1004mPerfLineCurrent15CntIndex
		INTEGER,
	pm1004mPerfLineCurrent15CntInvCvPortn
		EkiOnOff,
	pm1004mPerfLineCurrent15CntCvValuePortn
		Unsigned32,
	pm1004mPerfLineCurrent15CntInvEsPortn
		EkiOnOff,
	pm1004mPerfLineCurrent15CntEsValuePortn
		Unsigned32,
	pm1004mPerfLineCurrent15CntInvSesPortn
		EkiOnOff,
	pm1004mPerfLineCurrent15CntSesValuePortn
		Unsigned32,
	pm1004mPerfLineCurrent15CntInvSefsPortn
		EkiOnOff,
	pm1004mPerfLineCurrent15CntSefsValuePortn
		Unsigned32,
	pm1004mPerfLineCurrent15CntInvUasPortn
		EkiOnOff,
	pm1004mPerfLineCurrent15CntUasValuePortn
		Unsigned32
	}


pm1004mPerfLineCurrent15CntIndex OBJECT-TYPE
	SYNTAX  INTEGER(0..128)
	MAX-ACCESS  read-only
	STATUS current
	DESCRIPTION
        "
        Index definition for the pm1004mPerfLineCurrent15Cnt 
        table
        "
	::= { pm1004mPerfLineCurrent15CntEntry 1 }


pm1004mPerfLineCurrent15CntInvCvPortn OBJECT-TYPE
	SYNTAX  EkiOnOff
	MAX-ACCESS read-only
	STATUS current
	DESCRIPTION
        "
        Current 15-min CV counter inv. 
        :This OID indicates that the current 
        15-min Coding Violation counter 
        is invalid
        "
	::= { pm1004mPerfLineCurrent15CntEntry 2 }


pm1004mPerfLineCurrent15CntCvValuePortn OBJECT-TYPE
	SYNTAX  Unsigned32
	MAX-ACCESS read-only
	STATUS current
	DESCRIPTION
        "
        Current 15-min CV counter :This 
        OID gives the current 15-min Coding 
        Violation counter value
        "
	::= { pm1004mPerfLineCurrent15CntEntry 3 }


pm1004mPerfLineCurrent15CntInvEsPortn OBJECT-TYPE
	SYNTAX  EkiOnOff
	MAX-ACCESS read-only
	STATUS current
	DESCRIPTION
        "
        Current 15-min ES counter inv. 
        :This OID indicates that the current 
        15-min Errored Second counter is 
        invalid
        "
	::= { pm1004mPerfLineCurrent15CntEntry 4 }


pm1004mPerfLineCurrent15CntEsValuePortn OBJECT-TYPE
	SYNTAX  Unsigned32
	MAX-ACCESS read-only
	STATUS current
	DESCRIPTION
        "
        Current 15-min ES counter :This 
        OID gives the current 15-min Errored 
        Second counter value
        "
	::= { pm1004mPerfLineCurrent15CntEntry 5 }


pm1004mPerfLineCurrent15CntInvSesPortn OBJECT-TYPE
	SYNTAX  EkiOnOff
	MAX-ACCESS read-only
	STATUS current
	DESCRIPTION
        "
        Current 15-min SES counter inv. 
        :This OID indicates that the current 
        15-min severely Errored Second
         counter is invalid
        "
	::= { pm1004mPerfLineCurrent15CntEntry 6 }


pm1004mPerfLineCurrent15CntSesValuePortn OBJECT-TYPE
	SYNTAX  Unsigned32
	MAX-ACCESS read-only
	STATUS current
	DESCRIPTION
        "
        Current 15-min SES counter :This 
        OID gives the current 15-min severely 
        Errored Second counter value
        "
	::= { pm1004mPerfLineCurrent15CntEntry 7 }


pm1004mPerfLineCurrent15CntInvSefsPortn OBJECT-TYPE
	SYNTAX  EkiOnOff
	MAX-ACCESS read-only
	STATUS current
	DESCRIPTION
        "
        Current 15-min SEFS counter inv. 
        :This OID indicates that the current 
        15-min severely Errored Framing 
        Second counter is invalid
        "
	::= { pm1004mPerfLineCurrent15CntEntry 8 }


pm1004mPerfLineCurrent15CntSefsValuePortn OBJECT-TYPE
	SYNTAX  Unsigned32
	MAX-ACCESS read-only
	STATUS current
	DESCRIPTION
        "
        Current 15-min SEFS counter :This 
        OID gives the current 15-min severely 
        Errored Framing Second counter
         value
        "
	::= { pm1004mPerfLineCurrent15CntEntry 9 }


pm1004mPerfLineCurrent15CntInvUasPortn OBJECT-TYPE
	SYNTAX  EkiOnOff
	MAX-ACCESS read-only
	STATUS current
	DESCRIPTION
        "
        Current 15-min UAS counter inv. 
        :This OID indicates that the current 
        15-min UnAvailable Second counter 
        is invalid
        "
	::= { pm1004mPerfLineCurrent15CntEntry 10 }


pm1004mPerfLineCurrent15CntUasValuePortn OBJECT-TYPE
	SYNTAX  Unsigned32
	MAX-ACCESS read-only
	STATUS current
	DESCRIPTION
        "
        Current 15-min UAS counter :This 
        OID gives the current 15-min UnAvailable 
        Second counter value
        "
	::= { pm1004mPerfLineCurrent15CntEntry 11 }


--- *********************************************************
---     TABLE for the pm1004mPerfLinePast15Cnt articles
--- *********************************************************

pm1004mPerfLinePast15CntTable OBJECT-TYPE
	SYNTAX  SEQUENCE OF Pm1004mPerfLinePast15CntEntry
	MAX-ACCESS not-accessible
	STATUS current
	DESCRIPTION
        "
        List of pm1004mPerfLinePast15Cnt 
        Article
        "
	::= { pm1004mMonLinePerformance 129 }


pm1004mPerfLinePast15CntEntry OBJECT-TYPE
	SYNTAX Pm1004mPerfLinePast15CntEntry
	MAX-ACCESS not-accessible
	STATUS current
	DESCRIPTION
        "
        Row definition for the pm1004mPerfLinePast15Cnt 
        table
        "
	INDEX   { pm1004mPerfLinePast15CntIndex }
	::= { pm1004mPerfLinePast15CntTable 1 }


Pm1004mPerfLinePast15CntEntry ::=
	SEQUENCE {
	pm1004mPerfLinePast15CntIndex
		INTEGER,
	pm1004mPerfLinePast15CntInvCvPortn
		EkiOnOff,
	pm1004mPerfLinePast15CntCvValuePortn
		Unsigned32,
	pm1004mPerfLinePast15CntInvEsPortn
		EkiOnOff,
	pm1004mPerfLinePast15CntEsValuePortn
		Unsigned32,
	pm1004mPerfLinePast15CntInvSesPortn
		EkiOnOff,
	pm1004mPerfLinePast15CntSesValuePortn
		Unsigned32,
	pm1004mPerfLinePast15CntInvSefsPortn
		EkiOnOff,
	pm1004mPerfLinePast15CntSefsValuePortn
		Unsigned32,
	pm1004mPerfLinePast15CntInvUasPortn
		EkiOnOff,
	pm1004mPerfLinePast15CntUasValuePortn
		Unsigned32
	}


pm1004mPerfLinePast15CntIndex OBJECT-TYPE
	SYNTAX  INTEGER(0..128)
	MAX-ACCESS  read-only
	STATUS current
	DESCRIPTION
        "
        Index definition for the pm1004mPerfLinePast15Cnt 
        table
        "
	::= { pm1004mPerfLinePast15CntEntry 1 }


pm1004mPerfLinePast15CntInvCvPortn OBJECT-TYPE
	SYNTAX  EkiOnOff
	MAX-ACCESS read-only
	STATUS current
	DESCRIPTION
        "
        Previous 15-min CV counter inv. 
        :This OID indicates that the previous 
        15-min Coding Violation counter 
        is invalid
        "
	::= { pm1004mPerfLinePast15CntEntry 2 }


pm1004mPerfLinePast15CntCvValuePortn OBJECT-TYPE
	SYNTAX  Unsigned32
	MAX-ACCESS read-only
	STATUS current
	DESCRIPTION
        "
        Previous 15-min CV counter :This 
        OID gives the previous 15-min Coding 
        Violation counter value
        "
	::= { pm1004mPerfLinePast15CntEntry 3 }


pm1004mPerfLinePast15CntInvEsPortn OBJECT-TYPE
	SYNTAX  EkiOnOff
	MAX-ACCESS read-only
	STATUS current
	DESCRIPTION
        "
        Previous 15-min ES counter inv. 
        :This OID indicates that the previous 
        15-min Errored Second counter is 
        invalid
        "
	::= { pm1004mPerfLinePast15CntEntry 4 }


pm1004mPerfLinePast15CntEsValuePortn OBJECT-TYPE
	SYNTAX  Unsigned32
	MAX-ACCESS read-only
	STATUS current
	DESCRIPTION
        "
        Previous 15-min ES counter :This 
        OID gives the previous 15-min Errored 
        Second counter value
        "
	::= { pm1004mPerfLinePast15CntEntry 5 }


pm1004mPerfLinePast15CntInvSesPortn OBJECT-TYPE
	SYNTAX  EkiOnOff
	MAX-ACCESS read-only
	STATUS current
	DESCRIPTION
        "
        Previous 15-min SES counter inv. 
        :This OID indicates that the previous 
        15-min severely Errored Second
         counter is invalid
        "
	::= { pm1004mPerfLinePast15CntEntry 6 }


pm1004mPerfLinePast15CntSesValuePortn OBJECT-TYPE
	SYNTAX  Unsigned32
	MAX-ACCESS read-only
	STATUS current
	DESCRIPTION
        "
        Previous 15-min SES counter :This 
        OID gives the previous 15-min severely 
        Errored Second counter value
        "
	::= { pm1004mPerfLinePast15CntEntry 7 }


pm1004mPerfLinePast15CntInvSefsPortn OBJECT-TYPE
	SYNTAX  EkiOnOff
	MAX-ACCESS read-only
	STATUS current
	DESCRIPTION
        "
        Previous 15-min SEFS counter inv. 
        :This OID indicates that the previous 
        15-min severely Errored Framing 
        Second counter is invalid
        "
	::= { pm1004mPerfLinePast15CntEntry 8 }


pm1004mPerfLinePast15CntSefsValuePortn OBJECT-TYPE
	SYNTAX  Unsigned32
	MAX-ACCESS read-only
	STATUS current
	DESCRIPTION
        "
        Previous 15-min SEFS counter :This 
        OID gives the previous 15-min severely 
        Errored Framing Second counter
         value
        "
	::= { pm1004mPerfLinePast15CntEntry 9 }


pm1004mPerfLinePast15CntInvUasPortn OBJECT-TYPE
	SYNTAX  EkiOnOff
	MAX-ACCESS read-only
	STATUS current
	DESCRIPTION
        "
        Previous 15-min UAS counter inv. 
        :This OID indicates that the previous 
        15-min UnAvailable Second counter 
        is invalid
        "
	::= { pm1004mPerfLinePast15CntEntry 10 }


pm1004mPerfLinePast15CntUasValuePortn OBJECT-TYPE
	SYNTAX  Unsigned32
	MAX-ACCESS read-only
	STATUS current
	DESCRIPTION
        "
        Previous 15-min UAS counter :This 
        OID gives the previous 15-min UnAvailable 
        Second counter value
        "
	::= { pm1004mPerfLinePast15CntEntry 11 }


--- *********************************************************
---     TABLE for the pm1004mPerfLineCurrent24Cnt articles
--- *********************************************************

pm1004mPerfLineCurrent24CntTable OBJECT-TYPE
	SYNTAX  SEQUENCE OF Pm1004mPerfLineCurrent24CntEntry
	MAX-ACCESS not-accessible
	STATUS current
	DESCRIPTION
        "
        List of pm1004mPerfLineCurrent24Cnt 
        Article
        "
	::= { pm1004mMonLinePerformance 130 }


pm1004mPerfLineCurrent24CntEntry OBJECT-TYPE
	SYNTAX Pm1004mPerfLineCurrent24CntEntry
	MAX-ACCESS not-accessible
	STATUS current
	DESCRIPTION
        "
        Row definition for the pm1004mPerfLineCurrent24Cnt 
        table
        "
	INDEX   { pm1004mPerfLineCurrent24CntIndex }
	::= { pm1004mPerfLineCurrent24CntTable 1 }


Pm1004mPerfLineCurrent24CntEntry ::=
	SEQUENCE {
	pm1004mPerfLineCurrent24CntIndex
		INTEGER,
	pm1004mPerfLineCurrent24CntInvCvPortn
		EkiOnOff,
	pm1004mPerfLineCurrent24CntCvValuePortn
		Unsigned32,
	pm1004mPerfLineCurrent24CntInvEsPortn
		EkiOnOff,
	pm1004mPerfLineCurrent24CntEsValuePortn
		Unsigned32,
	pm1004mPerfLineCurrent24CntInvSesPortn
		EkiOnOff,
	pm1004mPerfLineCurrent24CntSesValuePortn
		Unsigned32,
	pm1004mPerfLineCurrent24CntInvSefsPortn
		EkiOnOff,
	pm1004mPerfLineCurrent24CntSefsValuePortn
		Unsigned32,
	pm1004mPerfLineCurrent24CntInvUasPortn
		EkiOnOff,
	pm1004mPerfLineCurrent24CntUasValuePortn
		Unsigned32
	}


pm1004mPerfLineCurrent24CntIndex OBJECT-TYPE
	SYNTAX  INTEGER(0..128)
	MAX-ACCESS  read-only
	STATUS current
	DESCRIPTION
        "
        Index definition for the pm1004mPerfLineCurrent24Cnt 
        table
        "
	::= { pm1004mPerfLineCurrent24CntEntry 1 }


pm1004mPerfLineCurrent24CntInvCvPortn OBJECT-TYPE
	SYNTAX  EkiOnOff
	MAX-ACCESS read-only
	STATUS current
	DESCRIPTION
        "
        Current 24-hours CV counter inv. 
        :This OID indicates that the current 
        24-hours Coding Violation counter 
        is invalid
        "
	::= { pm1004mPerfLineCurrent24CntEntry 2 }


pm1004mPerfLineCurrent24CntCvValuePortn OBJECT-TYPE
	SYNTAX  Unsigned32
	MAX-ACCESS read-only
	STATUS current
	DESCRIPTION
        "
        Current 24-hours CV counter :This 
        OID gives the current 24-hours
         Coding Violation counter value
        "
	::= { pm1004mPerfLineCurrent24CntEntry 3 }


pm1004mPerfLineCurrent24CntInvEsPortn OBJECT-TYPE
	SYNTAX  EkiOnOff
	MAX-ACCESS read-only
	STATUS current
	DESCRIPTION
        "
        Current 24-hours ES counter inv. 
        :This OID indicates that the current 
        24-hours Errored Second counter 
        is invalid
        "
	::= { pm1004mPerfLineCurrent24CntEntry 4 }


pm1004mPerfLineCurrent24CntEsValuePortn OBJECT-TYPE
	SYNTAX  Unsigned32
	MAX-ACCESS read-only
	STATUS current
	DESCRIPTION
        "
        Current 24-hours ES counter :This 
        OID gives the current 24-hours
         Errored Second counter value
        "
	::= { pm1004mPerfLineCurrent24CntEntry 5 }


pm1004mPerfLineCurrent24CntInvSesPortn OBJECT-TYPE
	SYNTAX  EkiOnOff
	MAX-ACCESS read-only
	STATUS current
	DESCRIPTION
        "
        Current 24-hours SES counter inv. 
        :This OID indicates that the current 
        24-hours severely Errored Second 
        counter is invalid
        "
	::= { pm1004mPerfLineCurrent24CntEntry 6 }


pm1004mPerfLineCurrent24CntSesValuePortn OBJECT-TYPE
	SYNTAX  Unsigned32
	MAX-ACCESS read-only
	STATUS current
	DESCRIPTION
        "
        Current 24-hours SES counter :This 
        OID gives the current 24-hours
         severely Errored Second counter 
        value
        "
	::= { pm1004mPerfLineCurrent24CntEntry 7 }


pm1004mPerfLineCurrent24CntInvSefsPortn OBJECT-TYPE
	SYNTAX  EkiOnOff
	MAX-ACCESS read-only
	STATUS current
	DESCRIPTION
        "
        Current 24-hours SEFS counter
         inv. :This OID indicates that
         the current 24-hours severely
         Errored Framing Second counter 
        is invalid
        "
	::= { pm1004mPerfLineCurrent24CntEntry 8 }


pm1004mPerfLineCurrent24CntSefsValuePortn OBJECT-TYPE
	SYNTAX  Unsigned32
	MAX-ACCESS read-only
	STATUS current
	DESCRIPTION
        "
        Current 24-hours SEFS counter
         :This OID gives the current 24-hours 
        severely Errored Framing Second 
        counter value
        "
	::= { pm1004mPerfLineCurrent24CntEntry 9 }


pm1004mPerfLineCurrent24CntInvUasPortn OBJECT-TYPE
	SYNTAX  EkiOnOff
	MAX-ACCESS read-only
	STATUS current
	DESCRIPTION
        "
        Current 24-hours UAS counter inv. 
        :This OID indicates that the current 
        24-hours UnAvailable Second counter 
        is invalid
        "
	::= { pm1004mPerfLineCurrent24CntEntry 10 }


pm1004mPerfLineCurrent24CntUasValuePortn OBJECT-TYPE
	SYNTAX  Unsigned32
	MAX-ACCESS read-only
	STATUS current
	DESCRIPTION
        "
        Current 24-hours UAS counter :This 
        OID gives the current 24-hours
         UnAvailable Second counter value
        "
	::= { pm1004mPerfLineCurrent24CntEntry 11 }


--- *********************************************************
---     TABLE for the pm1004mPerfLinePast24Cnt articles
--- *********************************************************

pm1004mPerfLinePast24CntTable OBJECT-TYPE
	SYNTAX  SEQUENCE OF Pm1004mPerfLinePast24CntEntry
	MAX-ACCESS not-accessible
	STATUS current
	DESCRIPTION
        "
        List of pm1004mPerfLinePast24Cnt 
        Article
        "
	::= { pm1004mMonLinePerformance 131 }


pm1004mPerfLinePast24CntEntry OBJECT-TYPE
	SYNTAX Pm1004mPerfLinePast24CntEntry
	MAX-ACCESS not-accessible
	STATUS current
	DESCRIPTION
        "
        Row definition for the pm1004mPerfLinePast24Cnt 
        table
        "
	INDEX   { pm1004mPerfLinePast24CntIndex }
	::= { pm1004mPerfLinePast24CntTable 1 }


Pm1004mPerfLinePast24CntEntry ::=
	SEQUENCE {
	pm1004mPerfLinePast24CntIndex
		INTEGER,
	pm1004mPerfLinePast24CntInvCvPortn
		EkiOnOff,
	pm1004mPerfLinePast24CntCvValuePortn
		Unsigned32,
	pm1004mPerfLinePast24CntInvEsPortn
		EkiOnOff,
	pm1004mPerfLinePast24CntEsValuePortn
		Unsigned32,
	pm1004mPerfLinePast24CntInvSesPortn
		EkiOnOff,
	pm1004mPerfLinePast24CntSesValuePortn
		Unsigned32,
	pm1004mPerfLinePast24CntInvSefsPortn
		EkiOnOff,
	pm1004mPerfLinePast24CntSefsValuePortn
		Unsigned32,
	pm1004mPerfLinePast24CntInvUasPortn
		EkiOnOff,
	pm1004mPerfLinePast24CntUasValuePortn
		Unsigned32
	}


pm1004mPerfLinePast24CntIndex OBJECT-TYPE
	SYNTAX  INTEGER(0..128)
	MAX-ACCESS  read-only
	STATUS current
	DESCRIPTION
        "
        Index definition for the pm1004mPerfLinePast24Cnt 
        table
        "
	::= { pm1004mPerfLinePast24CntEntry 1 }


pm1004mPerfLinePast24CntInvCvPortn OBJECT-TYPE
	SYNTAX  EkiOnOff
	MAX-ACCESS read-only
	STATUS current
	DESCRIPTION
        "
        Previous 24-hours CV counter inv. 
        :This OID indicates that the previous 
        24-hours Coding Violation counter 
        is invalid
        "
	::= { pm1004mPerfLinePast24CntEntry 2 }


pm1004mPerfLinePast24CntCvValuePortn OBJECT-TYPE
	SYNTAX  Unsigned32
	MAX-ACCESS read-only
	STATUS current
	DESCRIPTION
        "
        Previous 24-hours CV counter :This 
        OID gives the previous 24-hours 
        Coding Violation counter value
        "
	::= { pm1004mPerfLinePast24CntEntry 3 }


pm1004mPerfLinePast24CntInvEsPortn OBJECT-TYPE
	SYNTAX  EkiOnOff
	MAX-ACCESS read-only
	STATUS current
	DESCRIPTION
        "
        Previous 24-hours ES counter inv. 
        :This OID indicates that the previous 
        24-hours Errored Second counter 
        is invalid
        "
	::= { pm1004mPerfLinePast24CntEntry 4 }


pm1004mPerfLinePast24CntEsValuePortn OBJECT-TYPE
	SYNTAX  Unsigned32
	MAX-ACCESS read-only
	STATUS current
	DESCRIPTION
        "
        Previous 24-hours ES counter :This 
        OID gives the previous 24-hours 
        Errored Second counter value
        "
	::= { pm1004mPerfLinePast24CntEntry 5 }


pm1004mPerfLinePast24CntInvSesPortn OBJECT-TYPE
	SYNTAX  EkiOnOff
	MAX-ACCESS read-only
	STATUS current
	DESCRIPTION
        "
        Previous 24-hours SES counter
         inv. :This OID indicates that
         the previous 24-hours severely 
        Errored Second counter is invalid
        "
	::= { pm1004mPerfLinePast24CntEntry 6 }


pm1004mPerfLinePast24CntSesValuePortn OBJECT-TYPE
	SYNTAX  Unsigned32
	MAX-ACCESS read-only
	STATUS current
	DESCRIPTION
        "
        Previous 24-hours SES counter
         :This OID gives the previous 24-hours 
        severely Errored Second counter 
        value
        "
	::= { pm1004mPerfLinePast24CntEntry 7 }


pm1004mPerfLinePast24CntInvSefsPortn OBJECT-TYPE
	SYNTAX  EkiOnOff
	MAX-ACCESS read-only
	STATUS current
	DESCRIPTION
        "
        Previous 24-hours SEFS counter 
        inv. :This OID indicates that the 
        previous 24-hours severely Errored 
        Framing Second counter is invalid
        "
	::= { pm1004mPerfLinePast24CntEntry 8 }


pm1004mPerfLinePast24CntSefsValuePortn OBJECT-TYPE
	SYNTAX  Unsigned32
	MAX-ACCESS read-only
	STATUS current
	DESCRIPTION
        "
        Previous 24-hours SEFS counter 
        :This OID gives the previous 24-hours 
        severely Errored Framing Second 
        counter value
        "
	::= { pm1004mPerfLinePast24CntEntry 9 }


pm1004mPerfLinePast24CntInvUasPortn OBJECT-TYPE
	SYNTAX  EkiOnOff
	MAX-ACCESS read-only
	STATUS current
	DESCRIPTION
        "
        Previous 24-hours UAS counter
         inv. :This OID indicates that
         the previous 24-hours UnAvailable 
        Second counter is invalid
        "
	::= { pm1004mPerfLinePast24CntEntry 10 }


pm1004mPerfLinePast24CntUasValuePortn OBJECT-TYPE
	SYNTAX  Unsigned32
	MAX-ACCESS read-only
	STATUS current
	DESCRIPTION
        "
        Previous 24-hours UAS counter
         :This OID gives the previous 24-hours 
        UnAvailable Second counter value
        "
	::= { pm1004mPerfLinePast24CntEntry 11 }



pm1004mPerfEnable OBJECT-TYPE
	SYNTAX EkiOnOff
	MAX-ACCESS read-write
	STATUS current
	DESCRIPTION
        "
        Perf. Mon. Enable :This OID enables 
        the Performance Monitoring application
        "
	::= { pm1004mMonSync 257 }


pm1004mPerfSyncSource OBJECT-TYPE
	SYNTAX EkiSynchroMode
	MAX-ACCESS read-write
	STATUS current
	DESCRIPTION
        "
        Perf. Mon. Sync. Source :This
         OID selects the Synchronisation 
        source for the Performance Monitoring 
        application (internal of external)
        "
	::= { pm1004mMonSync 258 }


pm1004mPerf15minSync OBJECT-TYPE
	SYNTAX EkiOnOff
	MAX-ACCESS read-write
	STATUS current
	DESCRIPTION
        "
        Perf. Mon. 15-min sync. :This
         OID must be used in external synchronisation 
        mode only to send a 15-min synchronisation 
        command
        "
	::= { pm1004mMonSync 259 }


pm1004mPerf24hSync OBJECT-TYPE
	SYNTAX EkiOnOff
	MAX-ACCESS read-write
	STATUS current
	DESCRIPTION
        "
        Perf. Mon. 24-hours sync. :This 
        OID must be used in external synchronisation 
        mode only to send a 24-hours synchronisation 
        command
        "
	::= { pm1004mMonSync 260 }


pm1004mPerfCurrent15MinElapsedTime OBJECT-TYPE
	SYNTAX Counter32
	MAX-ACCESS read-write
	STATUS current
	DESCRIPTION
        "
        Current 15min period Elapsed Time 
         :This OID gives the number of
         seconds elapsed in the current 
        15-minutes period
        "
	::= { pm1004mMonTimeStamp 5 }


pm1004mPerfCurrent24HoursElapsedTime OBJECT-TYPE
	SYNTAX Counter32
	MAX-ACCESS read-write
	STATUS current
	DESCRIPTION
        "
        Current 24hours period Elapsed 
        Time :This OID gives the number 
        of seconds elapsed in the current 
        24-hours period
        "
	::= { pm1004mMonTimeStamp 6 }


pm1004mPerfPast15MinElapsedTime OBJECT-TYPE
	SYNTAX Counter32
	MAX-ACCESS read-write
	STATUS current
	DESCRIPTION
        "
        Past 15min period Elapsed Time 
         :This OID gives the number of
         seconds elapsed in the past 15-minutes 
        period
        "
	::= { pm1004mMonTimeStamp 7 }


pm1004mPerfPast24HoursElapsedTime OBJECT-TYPE
	SYNTAX Counter32
	MAX-ACCESS read-write
	STATUS current
	DESCRIPTION
        "
        Past 24hours period Elapsed Time 
        :This OID gives the number of seconds 
        elapsed in the past 24-hours period
        "
	::= { pm1004mMonTimeStamp 8 }






--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm1004mDwlrestartProcess OBJECT IDENTIFIER ::= { pm1004mDwlOther 0 }




pm1004mDwlColdRestartProcessed OBJECT-TYPE
	  SYNTAX EkiOnOff
	  MAX-ACCESS read-only
	  STATUS current
	  DESCRIPTION
        "
        Cold Restart :This OID indicates 
        that the module last restart was 
        a Cold RESTART
        "
	  ::= { pm1004mDwlrestartProcess 2 }



pm1004mDwlWarmRestartProcessed OBJECT-TYPE
	  SYNTAX EkiOnOff
	  MAX-ACCESS read-only
	  STATUS current
	  DESCRIPTION
        "
        Warm Restart :This OID indicates 
        that the module last restart was 
        a Warm RESTART
        "
	  ::= { pm1004mDwlrestartProcess 1 }



--- *****************************************************
---     LEAF for the swBanksUsed article
--- *****************************************************
pm1004mDwlswBanksUsed OBJECT IDENTIFIER ::= { pm1004mDwlOther 1 }




pm1004mDwlSwBank2Notempty OBJECT-TYPE
	  SYNTAX EkiOnOff
	  MAX-ACCESS read-only
	  STATUS current
	  DESCRIPTION
        "
        SW bank 2 loaded  :This OID indicates 
        a software is loaded in SW bank 
        2  <Help>  This status indicates 
        if the SW bank 2 contains SW package
        "
	  ::= { pm1004mDwlswBanksUsed 6 }



pm1004mDwlSwBank1Notempty OBJECT-TYPE
	  SYNTAX EkiOnOff
	  MAX-ACCESS read-only
	  STATUS current
	  DESCRIPTION
        "
        SW bank 1 loaded  :This OID indicates 
        a software is loaded in SW bank 
        1  <Help>  This status indicates 
        if the SW bank 1 contains SW package
        "
	  ::= { pm1004mDwlswBanksUsed 5 }



pm1004mDwlSwBank2Used OBJECT-TYPE
	  SYNTAX EkiOnOff
	  MAX-ACCESS read-only
	  STATUS current
	  DESCRIPTION
        "
        SW bank 2 active  :This OID indicates 
        the module is working on SW bank 
        2  <Help>  This status indicates 
        if the SW bank 2 is active or standby
        "
	  ::= { pm1004mDwlswBanksUsed 2 }



pm1004mDwlSwBank1Used OBJECT-TYPE
	  SYNTAX EkiOnOff
	  MAX-ACCESS read-only
	  STATUS current
	  DESCRIPTION
        "
        SW bank 1 active  :This OID indicates 
        the module is working on SW bank 
        1  <Help>  This status indicates 
        if the SW bank 1 is active or standby
        "
	  ::= { pm1004mDwlswBanksUsed 1 }



--- *****************************************************
---     LEAF for the gwBanksUsed article
--- *****************************************************
pm1004mDwlgwBanksUsed OBJECT IDENTIFIER ::= { pm1004mDwlOther 2 }




pm1004mDwlGwBank4Notempty OBJECT-TYPE
	  SYNTAX EkiOnOff
	  MAX-ACCESS read-only
	  STATUS current
	  DESCRIPTION
        "
        GW bank 4 loaded  :This OID indicates 
        a gateware is loaded in GW bank 
        4
        "
	  ::= { pm1004mDwlgwBanksUsed 8 }



pm1004mDwlGwBank3Notempty OBJECT-TYPE
	  SYNTAX EkiOnOff
	  MAX-ACCESS read-only
	  STATUS current
	  DESCRIPTION
        "
        GW bank 3 loaded  :This OID indicates 
        a gateware is loaded in GW bank 
        3  <Help>  This status indicates 
        if the GW bank 3 contains GW package
        "
	  ::= { pm1004mDwlgwBanksUsed 7 }



pm1004mDwlGwBank2Notempty OBJECT-TYPE
	  SYNTAX EkiOnOff
	  MAX-ACCESS read-only
	  STATUS current
	  DESCRIPTION
        "
        GW bank 2 loaded  :This OID indicates 
        a gateware is loaded in GW bank 
        2
        "
	  ::= { pm1004mDwlgwBanksUsed 6 }



pm1004mDwlGwBank1Notempty OBJECT-TYPE
	  SYNTAX EkiOnOff
	  MAX-ACCESS read-only
	  STATUS current
	  DESCRIPTION
        "
        GW bank 1 loaded  :This OID indicates 
        a gateware is loaded in GW bank 
        1  <Help>  This status indicates 
        if the GW bank 1 contains GW package
        "
	  ::= { pm1004mDwlgwBanksUsed 5 }



pm1004mDwlGwBank4Used OBJECT-TYPE
	  SYNTAX EkiOnOff
	  MAX-ACCESS read-only
	  STATUS current
	  DESCRIPTION
        "
        GW bank 4 active  :This OID indicates 
        the module is working on GW bank 
        4
        "
	  ::= { pm1004mDwlgwBanksUsed 4 }



pm1004mDwlGwBank3Used OBJECT-TYPE
	  SYNTAX EkiOnOff
	  MAX-ACCESS read-only
	  STATUS current
	  DESCRIPTION
        "
        GW bank 3 active  :This OID indicates 
        the module is working on GW bank 
        3  <Help>  This status indicates 
        if the GW bank 3 is active or standby
        "
	  ::= { pm1004mDwlgwBanksUsed 3 }



pm1004mDwlGwBank2Used OBJECT-TYPE
	  SYNTAX EkiOnOff
	  MAX-ACCESS read-only
	  STATUS current
	  DESCRIPTION
        "
        GW bank 2 active  :This OID indicates 
        the module is working on GW bank 
        2
        "
	  ::= { pm1004mDwlgwBanksUsed 2 }



pm1004mDwlGwBank1Used OBJECT-TYPE
	  SYNTAX EkiOnOff
	  MAX-ACCESS read-only
	  STATUS current
	  DESCRIPTION
        "
        GW bank 1 active  :This OID indicates 
        the module is working on GW bank 
        1  <Help>  This status indicates 
        if the GW bank 1 is active or standby
        "
	  ::= { pm1004mDwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm1004mCfgAccessCAisCsf OBJECT IDENTIFIER ::= { pm1004mConfig 1 }



--- *****************************************************
---     LEAF for the table 0012
--- *****************************************************

pm1004mCfgClientcaiscsfTable OBJECT-TYPE
	SYNTAX  SEQUENCE OF Pm1004mCfgClientcaiscsfEntry
	MAX-ACCESS not-accessible
	STATUS current
	DESCRIPTION
        "
        List of  Article
        "
	::= { pm1004mCfgAccessCAisCsf 1 }


pm1004mCfgClientcaiscsfEntry OBJECT-TYPE
	SYNTAX Pm1004mCfgClientcaiscsfEntry
	MAX-ACCESS not-accessible
	STATUS current
	DESCRIPTION
        "
        Row definition for the accessCAisCsf 
        table
        "
	INDEX   { pm1004mCfgClientcaiscsfIndex }
	::= { pm1004mCfgClientcaiscsfTable 1 }


Pm1004mCfgClientcaiscsfEntry ::=
	SEQUENCE {
	pm1004mCfgClientcaiscsfIndex
		INTEGER,
	pm1004mCfgCAisModePortn
		Unsigned32,
	pm1004mCfgUpAccessioAlmPortn
		Unsigned32,
	pm1004mCfgUpMapperDeAlmPortn
		Unsigned32,
	pm1004mCfgUpAccessioSdhAlmPortn
		Unsigned32,
	pm1004mCfgDownAccessioAlmPortn
		Unsigned32,
	pm1004mCfgDownMapperDeAlmPortn
		Unsigned32,
	pm1004mCfgDownDfrmAlmPortn
		Unsigned32,
	pm1004mCfgDownLineSyncAlarmsPortn
		Unsigned32,
	pm1004mCfgDownAccessioSdhAlmPortn
		Unsigned32
	}


pm1004mCfgClientcaiscsfIndex OBJECT-TYPE
	SYNTAX  INTEGER(0..128)
	MAX-ACCESS  read-only
	STATUS current
	DESCRIPTION
        "
        Index definition for the clientcaiscsf 
        table
        "
	::= { pm1004mCfgClientcaiscsfEntry 1 }


pm1004mCfgCAisModePortn OBJECT-TYPE
	SYNTAX  Unsigned32 (0..65536)
	MAX-ACCESS read-write
	STATUS current
	DESCRIPTION
        "
        CAIS mode  on Client Port :This 
        register enables/disables port
          laser shutdown on CAIS insertion 
        condition
        "
	::= { pm1004mCfgClientcaiscsfEntry 3 }


pm1004mCfgUpAccessioAlmPortn OBJECT-TYPE
	SYNTAX  Unsigned32 (0..65536)
	MAX-ACCESS read-write
	STATUS current
	DESCRIPTION
        "
        CSF contributors on Client Port 
        :This register configures the contributors 
        to upstream CSF insertion on the 
        port.
        "
	::= { pm1004mCfgClientcaiscsfEntry 9 }


pm1004mCfgUpMapperDeAlmPortn OBJECT-TYPE
	SYNTAX  Unsigned32 (0..65536)
	MAX-ACCESS read-write
	STATUS current
	DESCRIPTION
        "
        CSF contributors on Client Port 
        :This register configures the contributors 
        to upstream CSF insertion on the 
        port.
        "
	::= { pm1004mCfgClientcaiscsfEntry 10 }


pm1004mCfgUpAccessioSdhAlmPortn OBJECT-TYPE
	SYNTAX  Unsigned32 (0..65536)
	MAX-ACCESS read-write
	STATUS current
	DESCRIPTION
        "
        CSF contributors on Client Port 
        :This register selects the contributors 
        of SDH register to upstream CAIS/CSF 
        on Port
        "
	::= { pm1004mCfgClientcaiscsfEntry 11 }


pm1004mCfgDownAccessioAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pm1004mCfgClientcaiscsfEntry 17 }


pm1004mCfgDownMapperDeAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pm1004mCfgClientcaiscsfEntry 18 }


pm1004mCfgDownDfrmAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pm1004mCfgClientcaiscsfEntry 19 }


pm1004mCfgDownLineSyncAlarmsPortn OBJECT-TYPE
	SYNTAX  Unsigned32 (0..65536)
	MAX-ACCESS read-write
	STATUS deprecated
	DESCRIPTION
        "
        CAIS contributors on Client Port 
        :This register configures the contributors 
        to downstream CAIS insertion on 
         port.
        "
	::= { pm1004mCfgClientcaiscsfEntry 20 }


pm1004mCfgDownAccessioSdhAlmPortn OBJECT-TYPE
	SYNTAX  Unsigned32 (0..65536)
	MAX-ACCESS read-write
	STATUS current
	DESCRIPTION
        "
        CAIS contributors on Client Port 
        :This register selects the contributors 
        of SDH register to downstream CAIS/CSF 
        on Port
        "
	::= { pm1004mCfgClientcaiscsfEntry 21 }


--- *****************************************************
---     LEAF for the table Group startup
--- *****************************************************

pm1004mCfgStartup OBJECT IDENTIFIER ::= { pm1004mConfig 2 }



--- *****************************************************
---     LEAF for the table 2111
--- *****************************************************

pm1004mCfgClientStartupTable OBJECT-TYPE
	SYNTAX  SEQUENCE OF Pm1004mCfgClientStartupEntry
	MAX-ACCESS not-accessible
	STATUS current
	DESCRIPTION
        "
        List of  Article
        "
	::= { pm1004mCfgStartup 1 }


pm1004mCfgClientStartupEntry OBJECT-TYPE
	SYNTAX Pm1004mCfgClientStartupEntry
	MAX-ACCESS not-accessible
	STATUS current
	DESCRIPTION
        "
        Row definition for the startup 
        table
        "
	INDEX   { pm1004mCfgClientStartupIndex }
	::= { pm1004mCfgClientStartupTable 1 }


Pm1004mCfgClientStartupEntry ::=
	SEQUENCE {
	pm1004mCfgClientStartupIndex
		INTEGER,
	pm1004mCfgSystConfPortPortn
		Unsigned32,
	pm1004mCfgNetConfPortPortn
		Unsigned32
	}


pm1004mCfgClientStartupIndex OBJECT-TYPE
	SYNTAX  INTEGER(0..128)
	MAX-ACCESS  read-only
	STATUS current
	DESCRIPTION
        "
        Index definition for the clientStartup 
        table
        "
	::= { pm1004mCfgClientStartupEntry 1 }


pm1004mCfgSystConfPortPortn OBJECT-TYPE
	SYNTAX  Unsigned32 (0..65536)
	MAX-ACCESS read-write
	STATUS current
	DESCRIPTION
        "
        Default Settings on Client Port 
        :This  register configures the
         default initialisation settings 
        on the port.
        "
	::= { pm1004mCfgClientStartupEntry 3 }


pm1004mCfgNetConfPortPortn OBJECT-TYPE
	SYNTAX  Unsigned32 (0..65536)
	MAX-ACCESS read-write
	STATUS current
	DESCRIPTION
        "
        Default Protocol on Client Port 
        :This register configures the default 
        initialisation protocol on the
         port.
        "
	::= { pm1004mCfgClientStartupEntry 4 }


--- *****************************************************
---     LEAF for the table 2191
--- *****************************************************

pm1004mtablelineStartup OBJECT IDENTIFIER ::= { pm1004mCfgStartup 2 }



pm1004mCfgsystConfLine1 OBJECT-TYPE
	  SYNTAX Unsigned32 (0..65536)
	  MAX-ACCESS read-write
	  STATUS current
	  DESCRIPTION
        "
        Default Settings on Line 1 :This 
        register configures the default 
        initialisation settings on Line 
        port 1.
        "
	  ::= { pm1004mtablelineStartup 2 }



pm1004mCfglineOptions1 OBJECT-TYPE
	  SYNTAX Unsigned32 (0..65536)
	  MAX-ACCESS read-write
	  STATUS current
	  DESCRIPTION
        "
        Default Options on Active Line 
        Port :This register configures
         the default options on the active 
        line port
        "
	  ::= { pm1004mtablelineStartup 5 }



pm1004mCfgsystConfLine2 OBJECT-TYPE
	  SYNTAX Unsigned32 (0..65536)
	  MAX-ACCESS read-write
	  STATUS current
	  DESCRIPTION
        "
        Default Settings on Line 2 :This 
        register configures the default 
        initialisation settings on Line 
        port 2.
        "
	  ::= { pm1004mtablelineStartup 6 }



pm1004mCfglineSelection OBJECT-TYPE
	  SYNTAX Unsigned32 (0..65536)
	  MAX-ACCESS read-write
	  STATUS current
	  DESCRIPTION
        "
        Default Settings of active line 
        :This  register configures the
         start up active line.
        "
	  ::= { pm1004mtablelineStartup 7 }



--- *****************************************************
---     LEAF for the table 21AB
--- *****************************************************

pm1004mCfgXfpTable OBJECT-TYPE
	SYNTAX  SEQUENCE OF Pm1004mCfgXfpEntry
	MAX-ACCESS not-accessible
	STATUS current
	DESCRIPTION
        "
        List of  Article
        "
	::= { pm1004mCfgStartup 3 }


pm1004mCfgXfpEntry OBJECT-TYPE
	SYNTAX Pm1004mCfgXfpEntry
	MAX-ACCESS not-accessible
	STATUS current
	DESCRIPTION
        "
        Row definition for the startup 
        table
        "
	INDEX   { pm1004mCfgXfpIndex }
	::= { pm1004mCfgXfpTable 1 }


Pm1004mCfgXfpEntry ::=
	SEQUENCE {
	pm1004mCfgXfpIndex
		INTEGER,
	pm1004mCfgSystConfXfpPortn
		Unsigned32,
	pm1004mCfgDataRateConfXfpPortn
		Unsigned32
	}


pm1004mCfgXfpIndex OBJECT-TYPE
	SYNTAX  INTEGER(0..128)
	MAX-ACCESS  read-only
	STATUS current
	DESCRIPTION
        "
        Index definition for the xfp table
        "
	::= { pm1004mCfgXfpEntry 1 }


pm1004mCfgSystConfXfpPortn OBJECT-TYPE
	SYNTAX  Unsigned32 (0..65536)
	MAX-ACCESS read-write
	STATUS current
	DESCRIPTION
        "
        Default settings on XFP Port :This 
        register configures the default 
        initialisation settings on XFP
         port.
        "
	::= { pm1004mCfgXfpEntry 3 }


pm1004mCfgDataRateConfXfpPortn OBJECT-TYPE
	SYNTAX  Unsigned32 (0..65536)
	MAX-ACCESS read-write
	STATUS deprecated
	DESCRIPTION
        "
        :Reserved
        "
	::= { pm1004mCfgXfpEntry 4 }


--- *****************************************************
---     LEAF for the table Group labels
--- *****************************************************

pm1004mCfgLabels OBJECT IDENTIFIER ::= { pm1004mConfig 3 }



--- *****************************************************
---     LEAF for the table NO_VALUE
--- *****************************************************

pm1004mCfgLabelclientTable OBJECT-TYPE
	SYNTAX  SEQUENCE OF Pm1004mCfgLabelclientEntry
	MAX-ACCESS not-accessible
	STATUS current
	DESCRIPTION
        "
        List of  Article
        "
	::= { pm1004mCfgLabels 1 }


pm1004mCfgLabelclientEntry OBJECT-TYPE
	SYNTAX Pm1004mCfgLabelclientEntry
	MAX-ACCESS not-accessible
	STATUS current
	DESCRIPTION
        "
        Row definition for the labels
         table
        "
	INDEX   { pm1004mCfgLabelclientIndex }
	::= { pm1004mCfgLabelclientTable 1 }


Pm1004mCfgLabelclientEntry ::=
	SEQUENCE {
	pm1004mCfgLabelclientIndex
		INTEGER,
	pm1004mCfgLabelclientPortn
		DisplayString
	}


pm1004mCfgLabelclientIndex OBJECT-TYPE
	SYNTAX  INTEGER(0..128)
	MAX-ACCESS  read-only
	STATUS current
	DESCRIPTION
        "
        Index definition for the labelclient 
        table
        "
	::= { pm1004mCfgLabelclientEntry 1 }


pm1004mCfgLabelclientPortn OBJECT-TYPE
	SYNTAX  DisplayString( SIZE(1..16))
	MAX-ACCESS read-write
	STATUS current
	DESCRIPTION
        "
        Default settings on the label
         of the Ports :These registers
         configures the default initialisation 
        settings of the labels of the ports.
        "
	::= { pm1004mCfgLabelclientEntry 3 }


--- *****************************************************
---     LEAF for the table NO_VALUE
--- *****************************************************

pm1004mCfgLabellineTable OBJECT-TYPE
	SYNTAX  SEQUENCE OF Pm1004mCfgLabellineEntry
	MAX-ACCESS not-accessible
	STATUS current
	DESCRIPTION
        "
        List of  Article
        "
	::= { pm1004mCfgLabels 2 }


pm1004mCfgLabellineEntry OBJECT-TYPE
	SYNTAX Pm1004mCfgLabellineEntry
	MAX-ACCESS not-accessible
	STATUS current
	DESCRIPTION
        "
        Row definition for the labels
         table
        "
	INDEX   { pm1004mCfgLabellineIndex }
	::= { pm1004mCfgLabellineTable 1 }


Pm1004mCfgLabellineEntry ::=
	SEQUENCE {
	pm1004mCfgLabellineIndex
		INTEGER,
	pm1004mCfgLabellinePortn
		DisplayString
	}


pm1004mCfgLabellineIndex OBJECT-TYPE
	SYNTAX  INTEGER(0..128)
	MAX-ACCESS  read-only
	STATUS current
	DESCRIPTION
        "
        Index definition for the labelline 
        table
        "
	::= { pm1004mCfgLabellineEntry 1 }


pm1004mCfgLabellinePortn OBJECT-TYPE
	SYNTAX  DisplayString( SIZE(1..16))
	MAX-ACCESS read-write
	STATUS current
	DESCRIPTION
        "
        Default settings on the label
         of the lines :These registers
         configures the default initialisation 
        settings of the labels of the lines.
        "
	::= { pm1004mCfgLabellineEntry 3 }


--- *****************************************************
---     LEAF for the table Group modPerfConfig
--- *****************************************************

pm1004mCfgModPerfConfig OBJECT IDENTIFIER ::= { pm1004mConfig 4 }



--- *****************************************************
---     LEAF for the table 5002
--- *****************************************************

pm1004mtablemodPerfConfig OBJECT IDENTIFIER ::= { pm1004mCfgModPerfConfig 1 }



pm1004mCfgperfMode OBJECT-TYPE
	  SYNTAX Unsigned32 (0..65536)
	  MAX-ACCESS read-write
	  STATUS current
	  DESCRIPTION
        "
        SONET or SDH monitoring mode :This 
        OID defines the line monitoring 
        mode (SONET or SDH mode)
        "
	  ::= { pm1004mtablemodPerfConfig 2 }



--- *****************************************************
---     LEAF for the table Group j0Client
--- *****************************************************

pm1004mCfgJ0Client OBJECT IDENTIFIER ::= { pm1004mConfig 5 }



--- *****************************************************
---     LEAF for the table 0013
--- *****************************************************

pm1004mCfgEmptyTable OBJECT-TYPE
	SYNTAX  SEQUENCE OF Pm1004mCfgEmptyEntry
	MAX-ACCESS not-accessible
	STATUS current
	DESCRIPTION
        "
        List of  Article
        "
	::= { pm1004mCfgJ0Client 1 }


pm1004mCfgEmptyEntry OBJECT-TYPE
	SYNTAX Pm1004mCfgEmptyEntry
	MAX-ACCESS not-accessible
	STATUS current
	DESCRIPTION
        "
        Row definition for the j0Client 
        table
        "
	INDEX   { pm1004mCfgEmptyIndex }
	::= { pm1004mCfgEmptyTable 1 }


Pm1004mCfgEmptyEntry ::=
	SEQUENCE {
	pm1004mCfgEmptyIndex
		INTEGER,
	pm1004mCfgClientExpectJ0SetupPortn
		Unsigned32
	}


pm1004mCfgEmptyIndex OBJECT-TYPE
	SYNTAX  INTEGER(0..128)
	MAX-ACCESS  read-only
	STATUS current
	DESCRIPTION
        "
        Index definition for the empty 
        table
        "
	::= { pm1004mCfgEmptyEntry 1 }


pm1004mCfgClientExpectJ0SetupPortn OBJECT-TYPE
	SYNTAX  Unsigned32 (0..65536)
	MAX-ACCESS read-write
	STATUS current
	DESCRIPTION
        "
        Expected Trace Identifier mode 
        :This register configures the Expected 
        Trace Identifier Mode (single byte, 
        16 bytes with CRC7, 64 bytes with 
        CRC7 or 64 bytes with CR/LF terminaison)
        "
	::= { pm1004mCfgEmptyEntry 3 }


--- *****************************************************
---     LEAF for the table Group startuptlh
--- *****************************************************

pm1004mCfgStartuptlh OBJECT IDENTIFIER ::= { pm1004mConfig 6 }



--- *****************************************************
---     LEAF for the table 25A8
--- *****************************************************

pm1004mCfgOtxtlhTable OBJECT-TYPE
	SYNTAX  SEQUENCE OF Pm1004mCfgOtxtlhEntry
	MAX-ACCESS not-accessible
	STATUS current
	DESCRIPTION
        "
        List of  Article
        "
	::= { pm1004mCfgStartuptlh 1 }


pm1004mCfgOtxtlhEntry OBJECT-TYPE
	SYNTAX Pm1004mCfgOtxtlhEntry
	MAX-ACCESS not-accessible
	STATUS current
	DESCRIPTION
        "
        Row definition for the startuptlh 
        table
        "
	INDEX   { pm1004mCfgOtxtlhIndex }
	::= { pm1004mCfgOtxtlhTable 1 }


Pm1004mCfgOtxtlhEntry ::=
	SEQUENCE {
	pm1004mCfgOtxtlhIndex
		INTEGER,
	pm1004mCfgNuPortn
		Unsigned32,
	pm1004mCfgLineDitherRatePortn
		Unsigned32,
	pm1004mCfgLineDitherFhzPortn
		Unsigned32,
	pm1004mCfgLinePwrLaserPortn
		Unsigned32,
	pm1004mCfgLineFCurrentPortn
		Unsigned32,
	pm1004mCfgLineGridCurrentPortn
		Unsigned32,
	pm1004mCfgFPortn
		Unsigned32,
	pm1004mCfgReservedPortn
		Unsigned32,
	pm1004mCfgLinePhotodiodeModePortn
		Unsigned32,
	pm1004mCfgLinePhotodiodeValuePortn
		Unsigned32
	}


pm1004mCfgOtxtlhIndex OBJECT-TYPE
	SYNTAX  INTEGER(0..128)
	MAX-ACCESS  read-only
	STATUS current
	DESCRIPTION
        "
        Index definition for the otxtlh 
        table
        "
	::= { pm1004mCfgOtxtlhEntry 1 }


pm1004mCfgNuPortn OBJECT-TYPE
	SYNTAX  Unsigned32 (0..65536)
	MAX-ACCESS read-write
	STATUS deprecated
	DESCRIPTION
        "
        :
        "
	::= { pm1004mCfgOtxtlhEntry 3 }


pm1004mCfgLineDitherRatePortn OBJECT-TYPE
	SYNTAX  Unsigned32 (0..65536)
	MAX-ACCESS read-write
	STATUS current
	DESCRIPTION
        "
        Default Line OTX TLH FM amplitude 
        :This register configures the start-up 
        width of the frequency modulation 
        of the Line OTX TLH
        "
	::= { pm1004mCfgOtxtlhEntry 4 }


pm1004mCfgLineDitherFhzPortn OBJECT-TYPE
	SYNTAX  Unsigned32 (0..65536)
	MAX-ACCESS read-write
	STATUS current
	DESCRIPTION
        "
        Default Line OTX TLH FM frequency 
        :This register configures the start-up 
        frequency of the frequency modulation 
        of the Line OTX TLH
        "
	::= { pm1004mCfgOtxtlhEntry 5 }


pm1004mCfgLinePwrLaserPortn OBJECT-TYPE
	SYNTAX  Unsigned32 (0..65536)
	MAX-ACCESS read-write
	STATUS current
	DESCRIPTION
        "
        Defaut Line OTX TLH output Power 
        :This register configures the start-up 
        output power of the Line OTX TLH 
         (Unit = dBm)
        "
	::= { pm1004mCfgOtxtlhEntry 6 }


pm1004mCfgLineFCurrentPortn OBJECT-TYPE
	SYNTAX  Unsigned32 (0..65536)
	MAX-ACCESS read-write
	STATUS current
	DESCRIPTION
        "
        Default Line OTX TLH Channel :This 
        register configures the start-up 
        laser channel of the Line OTX TLH
        "
	::= { pm1004mCfgOtxtlhEntry 7 }


pm1004mCfgLineGridCurrentPortn OBJECT-TYPE
	SYNTAX  Unsigned32 (0..65536)
	MAX-ACCESS read-write
	STATUS current
	DESCRIPTION
        "
        Default Line OTX TLH Grid :This 
        register configures the start-up 
        laser grid of the Line OTX TLH
        "
	::= { pm1004mCfgOtxtlhEntry 8 }


pm1004mCfgFPortn OBJECT-TYPE
	SYNTAX  Unsigned32 (0..65536)
	MAX-ACCESS read-write
	STATUS current
	DESCRIPTION
        "
        Default Line OTX TLH lowest Freq 
        :This register configures the start-up 
        lowest frequency supported on the 
        Line OTX TLH
        "
	::= { pm1004mCfgOtxtlhEntry 9 }


pm1004mCfgReservedPortn OBJECT-TYPE
	SYNTAX  Unsigned32 (0..65536)
	MAX-ACCESS read-write
	STATUS deprecated
	DESCRIPTION
        "
        :
        "
	::= { pm1004mCfgOtxtlhEntry 10 }


pm1004mCfgLinePhotodiodeModePortn OBJECT-TYPE
	SYNTAX  Unsigned32 (0..65536)
	MAX-ACCESS read-write
	STATUS current
	DESCRIPTION
        "
        Default Line OTX TLH APD mode
         :This register configures the
         start-up APD mode of the Line
         OTX TLH
        "
	::= { pm1004mCfgOtxtlhEntry 11 }


pm1004mCfgLinePhotodiodeValuePortn OBJECT-TYPE
	SYNTAX  Unsigned32 (0..65536)
	MAX-ACCESS read-write
	STATUS current
	DESCRIPTION
        "
        Default Line OTX TLH APD atten. 
        :This register configures the start-up 
        APD attenuation on the Line OTX 
        TLH
        "
	::= { pm1004mCfgOtxtlhEntry 12 }


--- *****************************************************
---     LEAF for the table Group startuptablefive
--- *****************************************************

pm1004mCfgStartuptablefive OBJECT IDENTIFIER ::= { pm1004mConfig 7 }



--- *****************************************************
---     LEAF for the table 0005
--- *****************************************************

pm1004mCfgOtxtlhcapabilitiesTable OBJECT-TYPE
	SYNTAX  SEQUENCE OF Pm1004mCfgOtxtlhcapabilitiesEntry
	MAX-ACCESS not-accessible
	STATUS current
	DESCRIPTION
        "
        List of  Article
        "
	::= { pm1004mCfgStartuptablefive 1 }


pm1004mCfgOtxtlhcapabilitiesEntry OBJECT-TYPE
	SYNTAX Pm1004mCfgOtxtlhcapabilitiesEntry
	MAX-ACCESS not-accessible
	STATUS current
	DESCRIPTION
        "
        Row definition for the startuptablefive 
        table
        "
	INDEX   { pm1004mCfgOtxtlhcapabilitiesIndex }
	::= { pm1004mCfgOtxtlhcapabilitiesTable 1 }


Pm1004mCfgOtxtlhcapabilitiesEntry ::=
	SEQUENCE {
	pm1004mCfgOtxtlhcapabilitiesIndex
		INTEGER,
	pm1004mCfgComponentTypePortn
		Unsigned32,
	pm1004mCfgMiscellaneousPortn
		Unsigned32,
	pm1004mCfgFirstChannelPortn
		Unsigned32,
	pm1004mCfgLastChannelPortn
		Unsigned32,
	pm1004mCfgGridPortn
		Unsigned32
	}


pm1004mCfgOtxtlhcapabilitiesIndex OBJECT-TYPE
	SYNTAX  INTEGER(0..128)
	MAX-ACCESS  read-only
	STATUS current
	DESCRIPTION
        "
        Index definition for the otxtlhcapabilities 
        table
        "
	::= { pm1004mCfgOtxtlhcapabilitiesEntry 1 }


pm1004mCfgComponentTypePortn OBJECT-TYPE
	SYNTAX  Unsigned32 (0..65536)
	MAX-ACCESS read-only
	STATUS current
	DESCRIPTION
        "
        Component parameters :This OID 
        defines the component parameters
        "
	::= { pm1004mCfgOtxtlhcapabilitiesEntry 3 }


pm1004mCfgMiscellaneousPortn OBJECT-TYPE
	SYNTAX  Unsigned32 (0..65536)
	MAX-ACCESS read-only
	STATUS current
	DESCRIPTION
        "
        Miscellaneous default settings 
        :This OID defines the miscellaneous 
        parameters
        "
	::= { pm1004mCfgOtxtlhcapabilitiesEntry 4 }


pm1004mCfgFirstChannelPortn OBJECT-TYPE
	SYNTAX  Unsigned32 (0..65536)
	MAX-ACCESS read-only
	STATUS current
	DESCRIPTION
        "
        Number of the first channel of 
        the component :This OID defines 
        the first channel number of the 
        PM
        "
	::= { pm1004mCfgOtxtlhcapabilitiesEntry 5 }


pm1004mCfgLastChannelPortn OBJECT-TYPE
	SYNTAX  Unsigned32 (0..65536)
	MAX-ACCESS read-only
	STATUS current
	DESCRIPTION
        "
        Number of the last channel of
         the component :This OID defines 
        the last channel number of the
         PM
        "
	::= { pm1004mCfgOtxtlhcapabilitiesEntry 6 }


pm1004mCfgGridPortn OBJECT-TYPE
	SYNTAX  Unsigned32 (0..65536)
	MAX-ACCESS read-only
	STATUS current
	DESCRIPTION
        "
        Grid value of the component :This 
        OID defines the grid of the PM
        "
	::= { pm1004mCfgOtxtlhcapabilitiesEntry 7 }



pm1004mCfgWriteConfiguration  OBJECT-TYPE
	SYNTAX EkiOnOff
	MAX-ACCESS read-write
	STATUS current
	DESCRIPTION
	"Write configuration to module:This OID 
	 writes the complete configuration to the module"
	::= { pm1004mConfig 257 }






--- *****************************************************
---     TRAP OBJECTS
--- *****************************************************

pm1004mtrapPortNumber OBJECT-TYPE
	SYNTAX INTEGER(1..64)
	MAX-ACCESS read-only
	STATUS current
	DESCRIPTION
	"Last port which generates a trap"
	::= { pm1004mtraps 2 }

pm1004mtrapLineNumber OBJECT-TYPE
	SYNTAX INTEGER(1..64)
	MAX-ACCESS read-only
	STATUS current
	DESCRIPTION
	"Last Line which generates a trap"
	::= { pm1004mtraps 3 }

pm1004mtrapBoardNumber OBJECT-TYPE
	SYNTAX INTEGER(1..64)
	MAX-ACCESS read-only
	STATUS current
	DESCRIPTION
	"Last module which generates a trap"
	::= { pm1004mtraps 4 }







--- *****************************************************
---     LINE TRAPS
--- *****************************************************

pm1004mLineTrapNotUrgentGoesOn NOTIFICATION-TYPE
	OBJECTS {pm1004mAlmLineDdmWarningPortn, pm1004mtrapLineNumber, pm1004mtrapBoardNumber}
	STATUS current
	--&FILTNAME    "PM1004M Line Not Urgent ON"
	--&ACTIONS     { log, minor }
	--&MATCH       { pm1004mAlmLineDdmWarningPortn "on", pm1004mtrapLineNumber "$2", pm1004mtrapBoardNumber "$3"}
	--&MESG        "DDM Warning appears on Line Port $2 of PM1004M in Slot $3 ($A)"
	DESCRIPTION "Not urgent Line default is activated"
	::= { pm1004mtraps 30 }

pm1004mLineTrapNotUrgentGoesOff NOTIFICATION-TYPE
	OBJECTS {pm1004mAlmLineDdmWarningPortn, pm1004mtrapLineNumber, pm1004mtrapBoardNumber}
	STATUS current
	--&FILTNAME    "PM1004M Line Not Urgent OFF"
	--&ACTIONS     { log, normal }
	--&CLEARS      { "PM1004M Line Not Urgent ON" }
	--&MATCH       { pm1004mAlmLineDdmWarningPortn "on", pm1004mtrapLineNumber "$2", pm1004mtrapBoardNumber "$3"}
	--&MESG        "DDM Warning disappears on Line Port $2 of PM1004M in Slot $3 ($A)"
	DESCRIPTION "Not urgent Line default disappeared"
	::= { pm1004mtraps 31 }

pm1004mLineTrapUrgentGoesOn NOTIFICATION-TYPE
	OBJECTS {pm1004mAlmLineDdmAlmPortn, pm1004mtrapLineNumber, pm1004mtrapBoardNumber}
	STATUS current
	--&FILTNAME    "PM1004M Line Urgent ON"
	--&ACTIONS     { log, major }
	--&MATCH       { pm1004mAlmLineDdmAlmPortn "on", pm1004mtrapLineNumber "$2", pm1004mtrapBoardNumber "$3"}
	--&MESG        "DDM Alarm appears on Line Port $2 of PM1004M in Slot $3 ($A)"
	DESCRIPTION "Urgent Line default is activated"
	::= { pm1004mtraps 32 }

pm1004mLineTrapUrgentGoesOff NOTIFICATION-TYPE
	OBJECTS {pm1004mAlmLineDdmAlmPortn, pm1004mtrapLineNumber, pm1004mtrapBoardNumber}
	STATUS current
	--&FILTNAME    "PM1004M Line Urgent OFF"
	--&ACTIONS     { log, normal }
	--&CLEARS      { "PM1004M Line Urgent ON" }
	--&MATCH       { pm1004mAlmLineDdmAlmPortn "on", pm1004mtrapLineNumber "$2", pm1004mtrapBoardNumber "$3"}
	--&MESG        "DDM Alarm disappears on Line Port $2 of PM1004M in Slot $3 ($A)"
	DESCRIPTION "Urgent Line default disappeared"
	::= { pm1004mtraps 33 }

pm1004mLineTrapCritGoesOn NOTIFICATION-TYPE
	OBJECTS {pm1004mAlmLineFailPortn , pm1004mAlmLineHwFailPortn , pm1004mtrapLineNumber, pm1004mtrapBoardNumber}
	STATUS current
	--&FILTNAME    "PM1004M Line Fail ON"
	--&ACTIONS     { log, critical }
	--&MATCH       { pm1004mAlmLineFailPortn "on", pm1004mAlmLineHwFailPortn "*", pm1004mtrapLineNumber "$3", pm1004mtrapBoardNumber "$4"}
	--&MESG        "Line Port $3 Down on PM1004M in Slot $4 ($A)"
	
	--&FILTNAME    "PM1004M Line HW Fail ON (Hidden)"
	--&ACTIONS     { info }
	--&MATCH       { pm1004mAlmLineFailPortn "*", pm1004mAlmLineHwFailPortn "on", pm1004mtrapLineNumber "$3", pm1004mtrapBoardNumber "$4"}
	--&MESG        "Line Port $3 Down on PM1004M in Slot $4 ($A)"
	DESCRIPTION "Critical Line default is activated"
	::= { pm1004mtraps 34 }

pm1004mLineTrapCritGoesOff NOTIFICATION-TYPE
	OBJECTS {pm1004mAlmLineFailPortn , pm1004mAlmLineHwFailPortn , pm1004mtrapLineNumber, pm1004mtrapBoardNumber}
	STATUS current
	--&FILTNAME    "PM1004M Line Fail OFF"
	--&ACTIONS     { log,  normal }
	--&CLEARS      { "PM1004M Line Fail ON" }
	--&MATCH       { pm1004mAlmLineFailPortn "on", pm1004mAlmLineHwFailPortn "*", pm1004mtrapLineNumber "$3", pm1004mtrapBoardNumber "$4"}
	--&MESG        "Line Port $3 Up on PM1004M in Slot $4 ($A)"

	--&FILTNAME    "PM1004M Line HW Fail OFF (Hidden)"
	--&ACTIONS     { info }
	--&MATCH       { pm1004mAlmLineFailPortn "*", pm1004mAlmLineHwFailPortn "on", pm1004mtrapLineNumber "$3", pm1004mtrapBoardNumber "$4"}
	--&MESG        "Line Port $3 Up on PM1004M in Slot $4 ($A)"
	DESCRIPTION "Critical Line default disappeared"
	::= { pm1004mtraps 35 }






--- *****************************************************
---     CLIENT TRAPS
--- *****************************************************

pm1004mClientTrapNotUrgentGoesOn NOTIFICATION-TYPE
	OBJECTS {pm1004mAlmSfpDdmWarningPortn, pm1004mtrapPortNumber, pm1004mtrapBoardNumber}
	STATUS current
	--&FILTNAME    "PM1004M Client Not Urgent ON"
	--&ACTIONS     { log, minor }
	--&MATCH       { pm1004mAlmSfpDdmWarningPortn "on", pm1004mtrapPortNumber "$2", pm1004mtrapBoardNumber "$3"}
	--&MESG        "DDM Warning appears on Client Port $2 of PM1004M in Slot $3 ($A)"
	DESCRIPTION "Not urgent client default is activated"
	::= { pm1004mtraps 40 }

pm1004mClientTrapNotUrgentGoesOff NOTIFICATION-TYPE
	OBJECTS {pm1004mAlmSfpDdmWarningPortn, pm1004mtrapPortNumber, pm1004mtrapBoardNumber}
	STATUS current
	--&FILTNAME    "PM1004M Client Not Urgent OFF"
	--&ACTIONS     { log, normal }
	--&CLEARS      { "PM1004M Client Not Urgent ON" }
	--&MATCH       { pm1004mAlmSfpDdmWarningPortn "on", pm1004mtrapPortNumber "$2", pm1004mtrapBoardNumber "$3"}
	--&MESG        "DDM Warning appears on Client Port $2 of PM1004M in Slot $3 ($A)"
	DESCRIPTION "Not urgent client default disappeared"
	::= { pm1004mtraps 41 }

pm1004mClientTrapUrgentGoesOn NOTIFICATION-TYPE
	OBJECTS {pm1004mAlmSfpDdmAlmPortn, pm1004mtrapPortNumber, pm1004mtrapBoardNumber}
	STATUS current
	--&FILTNAME    "PM1004M Client Urgent ON"
	--&ACTIONS     { log, major }
	--&MATCH       { pm1004mAlmSfpDdmAlmPortn "on", pm1004mtrapPortNumber "$2", pm1004mtrapBoardNumber "$3"}
	--&MESG        "DDM Alarm appears on Client Port $2 of PM1004M in Slot $3 ($A)"
	DESCRIPTION "Urgent client default is activated"
	::= { pm1004mtraps 42 }

pm1004mClientTrapUrgentGoesOff NOTIFICATION-TYPE
	OBJECTS {pm1004mAlmSfpDdmAlmPortn, pm1004mtrapPortNumber, pm1004mtrapBoardNumber}
	STATUS current
	--&FILTNAME    "PM1004M Client Urgent OFF"
	--&ACTIONS     { log, normal }
	--&CLEARS      { "PM1004M Client Urgent ON" }
	--&MATCH       { pm1004mAlmSfpDdmAlmPortn "on", pm1004mtrapPortNumber "$2", pm1004mtrapBoardNumber "$3"}
	--&MESG        "DDM Alarm disappears on Client Port $2 of PM1004M in Slot $3 ($A)"
	DESCRIPTION "Urgent client default disappeared"
	::= { pm1004mtraps 43 }

pm1004mClientTrapCritGoesOn NOTIFICATION-TYPE
	OBJECTS {pm1004mAlmFailAccPortn, pm1004mAlmHwFailAccPortn, pm1004mtrapPortNumber, pm1004mtrapBoardNumber}
	STATUS current
	--&FILTNAME    "PM1004M Client Fail ON"
	--&ACTIONS     { log, critical }
	--&MATCH       { pm1004mAlmFailAccPortn "on", pm1004mAlmHwFailAccPortn "*", pm1004mtrapPortNumber "$3", pm1004mtrapBoardNumber "$4"}
	--&MESG        "Client Port $3 Down on PM1004M in Slot $4 ($A)"
	
	--&FILTNAME    "PM1004M Client HW Fail ON (Hidden)"
	--&ACTIONS     { info }
	--&MATCH       { pm1004mAlmFailAccPortn "*", pm1004mAlmHwFailAccPortn "on", pm1004mtrapPortNumber "$3", pm1004mtrapBoardNumber "$4"}
	--&MESG        "Client Port $3 Down on PM1004M in Slot $4 ($A)"
	DESCRIPTION "Critical client default is activated"
	::= { pm1004mtraps 44 }

pm1004mClientTrapCritGoesOff NOTIFICATION-TYPE
	OBJECTS {pm1004mAlmFailAccPortn, pm1004mAlmHwFailAccPortn, pm1004mtrapPortNumber, pm1004mtrapBoardNumber}
	STATUS current
	--&FILTNAME    "PM1004M Client Fail OFF"
	--&ACTIONS     { log, normal }
	--&CLEARS      { "PM1004M Client Fail ON" }
	--&MATCH       { pm1004mAlmFailAccPortn "on", pm1004mAlmHwFailAccPortn "*", pm1004mtrapPortNumber "$3", pm1004mtrapBoardNumber "$4"}
	--&MESG        "Client Port $3 Up on PM1004M in Slot $4 ($A)"
	
	--&FILTNAME    "PM1004M Client HW Fail OFF (Hidden)"
	--&ACTIONS     { info }
	--&MATCH       { pm1004mAlmFailAccPortn "*", pm1004mAlmHwFailAccPortn "on", pm1004mtrapPortNumber "$3", pm1004mtrapBoardNumber "$4"}
	--&MESG        "Client Port $3 Up on PM1004M in Slot $4 ($A)"
	DESCRIPTION "Critical client default disappeared"
	::= { pm1004mtraps 45 }






--- *****************************************************
---     HW TRAPS
--- *****************************************************

pm1004mPowerTrapUrgentGoesOn NOTIFICATION-TYPE
	OBJECTS {pm1004mAlmDefFuseB, pm1004mAlmDefFuseA , pm1004mtrapBoardNumber}
	STATUS current
	--&FILTNAME    "PM1004M Fuse A Fail ON"
	--&ACTIONS     { log, major }
	--&MATCH       { pm1004mAlmDefFuseB "*", pm1004mAlmDefFuseA "on", pm1004mtrapBoardNumber "$3"}
	--&MESG        "Power Input A Fail on PM1004M in Slot $3 ($A)"

	--&FILTNAME    "PM1004M Fuse B Fail ON"
	--&ACTIONS     { log, major }
	--&MATCH       { pm1004mAlmDefFuseB "on", pm1004mAlmDefFuseA "*", pm1004mtrapBoardNumber "$3"}
	--&MESG        "Power Input B Fail on PM1004M in Slot $3 ($A)"
	DESCRIPTION "Urgent power supply default is activated"
	::= { pm1004mtraps 50 }

pm1004mPowerTrapUrgentGoesOff NOTIFICATION-TYPE
	OBJECTS {pm1004mAlmDefFuseB, pm1004mAlmDefFuseA , pm1004mtrapBoardNumber}
	STATUS current
	--&FILTNAME    "PM1004M Fuse A&B Fail OFF"
	--&ACTIONS     { log, normal}
	--&CLEARS      { "PM1004M Fuse A Fail ON", "PM1004M Fuse B Fail ON" }
	--&MATCH       { pm1004mAlmDefFuseB "on", pm1004mAlmDefFuseA "on", pm1004mtrapBoardNumber "$3"}
	--&MESG        "Power Inputs A and B Present on PM1004M in Slot $3 ($A)"
	DESCRIPTION "Urgent power supply default disappeared"
	::= { pm1004mtraps 51 }






END
