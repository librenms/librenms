-- *****************************************************************
-- EKINOPS-Pm1005.TXT:  MIB
--
--MIB Part Number:3MI00013AJAE
--MIB Version:02
--
-- Copyright (c) 2016 by Ekinops
-- All rights reserved.
-- 
-- *****************************************************************

EKINOPS-Pm1005-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress                
        		FROM SNMPv2-SMI
 	TEXTUAL-CONVENTION,
	DisplayString
                FROM SNMPv2-TC;

modulePm1005 MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.net"
        DESCRIPTION
          "MIB for managing Ekinops modules with PM1005 software"
	REVISION "200706120000Z"
	DESCRIPTION
	  "Initial Version."	
	REVISION "200707100000Z"
	DESCRIPTION
	  "Add DCC alarms"	
	REVISION "200709170000Z"
	DESCRIPTION
	  "Inventory syntax is DisplayString instead of OCTET STRING"
	REVISION "200711260000Z"
	DESCRIPTION
	  "Update Ekinops Address,Helps on objects, Ports Labels"
	REVISION "200810210000Z"
	DESCRIPTION
	  "Add OTX-TLH features"

	REVISION "200904060000Z"
	DESCRIPTION
	  "DCC storm info suppress.Cosmetics for mib compilers"
	REVISION "200904090000Z"
	DESCRIPTION
	  "Add DCC ans MAINTENANCE control"
	REVISION "200906240000Z"
	DESCRIPTION
	  "CondType parameters insertion"
	REVISION "201002170000Z"
	DESCRIPTION
	  "Probcause,AlarmType - NMS"
	REVISION "201102030000Z"
	DESCRIPTION
	  "Formulas and Event on XFP init"
	REVISION "201207030000Z"
	DESCRIPTION
	  "Minor cosmetic updates"
	REVISION "201304020000Z"
	DESCRIPTION
	  "S1,K1,K2 suppress"
	REVISION "201403250000Z"
	DESCRIPTION
	  "Probcause,AlarmType - NMS completion"
	REVISION "201412190000Z"
	DESCRIPTION
	  "Labels cosmetic updates"
	REVISION "201605190000Z"
	DESCRIPTION
	  "New AlarmType - synthesisAlarm(12)"
	REVISION "201606020000Z"
	DESCRIPTION
	  "Capabilities objects of Table 5"
        ::= { ekinops 26 }



--- *****************************************************
---     LEAF LEVEL 2
--- *****************************************************


pm1005alarms OBJECT IDENTIFIER ::= { modulePm1005 2 }	
pm1005AlmOther OBJECT IDENTIFIER ::= { pm1005alarms 1 }
pm1005AlmOtherNurg OBJECT IDENTIFIER ::= { pm1005AlmOther 1 }
pm1005AlmOtherUrg OBJECT IDENTIFIER ::= { pm1005AlmOther 2 }
pm1005AlmOtherCrit OBJECT IDENTIFIER ::= { pm1005AlmOther 3 }

pm1005AlmClient OBJECT IDENTIFIER ::= { pm1005alarms 2 }
pm1005AlmClientNurg OBJECT IDENTIFIER ::= { pm1005AlmClient 1 }
pm1005AlmClientUrg OBJECT IDENTIFIER ::= { pm1005AlmClient 2 }
pm1005AlmClientCrit OBJECT IDENTIFIER ::= { pm1005AlmClient 3 }
	
pm1005AlmLine OBJECT IDENTIFIER ::= { pm1005alarms 3 }
pm1005AlmLineNurg OBJECT IDENTIFIER ::= { pm1005AlmLine 1 }
pm1005AlmLineUrg OBJECT IDENTIFIER ::= { pm1005AlmLine 2 }
pm1005AlmLineCrit OBJECT IDENTIFIER ::= { pm1005AlmLine 3 }





pm1005measures OBJECT IDENTIFIER ::= { modulePm1005 3 }	
pm1005MesrOther OBJECT IDENTIFIER ::= { pm1005measures 1 }	
pm1005MesrClient OBJECT IDENTIFIER ::= { pm1005measures 2 }	
pm1005MesrLine OBJECT IDENTIFIER ::= { pm1005measures 3 }	




pm1005counters OBJECT IDENTIFIER ::= { modulePm1005 4 }
pm1005CntOther OBJECT IDENTIFIER ::= { pm1005counters 1 }
pm1005CntClient OBJECT IDENTIFIER ::= { pm1005counters 2 }
pm1005CntLine OBJECT IDENTIFIER ::= { pm1005counters 3 }


pm1005controlsWrite OBJECT IDENTIFIER ::= { modulePm1005 6 }
pm1005CtrlOther OBJECT IDENTIFIER ::= { pm1005controlsWrite 1 }
pm1005CtrlClient OBJECT IDENTIFIER ::= { pm1005controlsWrite 2 }
pm1005CtrlLine OBJECT IDENTIFIER ::= { pm1005controlsWrite 3 }

pm1005ri OBJECT IDENTIFIER ::= { modulePm1005 7 }
pm1005riTable OBJECT IDENTIFIER ::= { pm1005ri 1 }

pm1005download OBJECT IDENTIFIER ::= { modulePm1005 8 }
pm1005DwlOther OBJECT IDENTIFIER ::= { pm1005download 1 }
pm1005DwlClient OBJECT IDENTIFIER ::= { pm1005download 2 }
pm1005DwlLine OBJECT IDENTIFIER ::= { pm1005download 3 }


pm1005Config OBJECT IDENTIFIER ::= { modulePm1005 9 }

pm1005traps OBJECT IDENTIFIER ::= { modulePm1005 10 }



pm1005Monitoring OBJECT IDENTIFIER ::= { modulePm1005 11}

pm1005MonOther OBJECT IDENTIFIER ::= { pm1005Monitoring 1 }
pm1005MonRmon OBJECT IDENTIFIER ::= { pm1005MonOther 3 }

pm1005MonClient OBJECT IDENTIFIER ::= { pm1005Monitoring 2 }
pm1005MonClientRmonCounter OBJECT IDENTIFIER ::= { pm1005MonClient 4 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************


Pm1005OtxMode ::= TEXTUAL-CONVENTION
    STATUS      current
    DESCRIPTION "Different modes on OTX-TLH on line ports"
    SYNTAX INTEGER {
		otx80mode(1),
		otx60mode(2),
		otxadjustmode(4)
           }

Pm1005OtxGrid ::= TEXTUAL-CONVENTION
    STATUS      current
    DESCRIPTION "Different grids on OTX-TLH on line ports"
    SYNTAX INTEGER {
		otxgrid200(200),
		otxgrid100(100),
		otxgrid50(50)
           }

Pm1005AdjustValue ::= TEXTUAL-CONVENTION
    STATUS      current
    DESCRIPTION "Different values in Adjust mode on OTX-TLH on line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm1005OtxChannel ::= TEXTUAL-CONVENTION
    STATUS      current
    DESCRIPTION "Channel selection on OTX-TLH on line ports"
    SYNTAX INTEGER 


--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm1005RinvReloadInventory OBJECT-TYPE
  SYNTAX EkiOnOff
  MAX-ACCESS read-write
  STATUS current
  DESCRIPTION
        "Reload the inventory: This OID triggers an 
         inventory reload."
  ::= { pm1005ri 2 }

pm1005RinvHwPlatform OBJECT-TYPE
  SYNTAX DisplayString
  MAX-ACCESS read-only
  STATUS current
  DESCRIPTION
        "HW platform description: This OID contains the 
         description of the Hardware platform."
  ::= { pm1005ri 3 }
  
pm1005RinvModulePlatform OBJECT-TYPE
  SYNTAX DisplayString
  MAX-ACCESS read-only
  STATUS current
  DESCRIPTION
        "Module platform description: This OID contains the 
         description of the Module."
  ::= { pm1005ri 4 }
  
pm1005RinvSwPlatform OBJECT-TYPE
  SYNTAX DisplayString
  MAX-ACCESS read-only
  STATUS current
  DESCRIPTION
        "SW platform description: This OID contains the 
         description of the Software platform."
  ::= { pm1005ri 5 }
  
pm1005RinvGwPlatform OBJECT-TYPE
  SYNTAX DisplayString
  MAX-ACCESS read-only
  STATUS current
  DESCRIPTION
        "GW platform desciption: This OID contains the 
         description of the Gateware platform."
  ::= { pm1005ri 6 }


pm1005RinvSfpTable OBJECT-TYPE
      SYNTAX  SEQUENCE OF Pm1005RinvSfpEntry
      MAX-ACCESS  not-accessible
      STATUS  current
      DESCRIPTION
              "List of the SFPs on the selected module"
      ::= { pm1005riTable 1 }

pm1005RinvSfpEntry OBJECT-TYPE
        SYNTAX  Pm1005RinvSfpEntry
        MAX-ACCESS  not-accessible
        STATUS  current
        DESCRIPTION
              "Row definition for the SFP table"
        INDEX   { pm1005RinvSfpIndex }
        ::= { pm1005RinvSfpTable 1 }
    


Pm1005RinvSfpEntry::=
        SEQUENCE {
          pm1005RinvSfpIndex 
              Integer32,
          pm1005Rinvsfp
              DisplayString
        }


    pm1005RinvSfpIndex OBJECT-TYPE
        SYNTAX  Integer32(1..16)
        MAX-ACCESS  read-only
        STATUS  current
        DESCRIPTION
              "Index for SFP table"
        ::= { pm1005RinvSfpEntry 1 }


    pm1005Rinvsfp OBJECT-TYPE
        SYNTAX  DisplayString
        MAX-ACCESS  read-only
        STATUS  current
        DESCRIPTION
              "Inventory for the SFP: This OID contains the inventory for the SFP"
        ::= { pm1005RinvSfpEntry 2 }




pm1005RinvLineTable OBJECT-TYPE
      SYNTAX  SEQUENCE OF Pm1005RinvLineEntry
      MAX-ACCESS  not-accessible
      STATUS  current
      DESCRIPTION
              "List of the XFPs on the selected module"
      ::= { pm1005riTable 2 }

pm1005RinvLineEntry OBJECT-TYPE
        SYNTAX  Pm1005RinvLineEntry
        MAX-ACCESS  not-accessible
        STATUS  current
        DESCRIPTION
              "Row definition for the XFP table"
        INDEX   { pm1005RinvLineIndex }
        ::= { pm1005RinvLineTable 1 }
    


Pm1005RinvLineEntry::=
        SEQUENCE {
          pm1005RinvLineIndex 
              Integer32,
          pm1005RinvxfpLine
              DisplayString
        }


    pm1005RinvLineIndex OBJECT-TYPE
        SYNTAX  Integer32(1..16)
        MAX-ACCESS  read-only
        STATUS  current
        DESCRIPTION
              "Index for XFP table"
        ::= { pm1005RinvLineEntry 1 }


    pm1005RinvxfpLine OBJECT-TYPE
        SYNTAX  DisplayString
        MAX-ACCESS  read-only
        STATUS  current
        DESCRIPTION
              "Inventory for the XFP: This OID contains the inventory for the XFP"
        ::= { pm1005RinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm1005AlmsynthAlm0 OBJECT IDENTIFIER ::= { pm1005AlmOtherCrit 0 }




pm1005AlmDefFuseB OBJECT-TYPE
	  SYNTAX EkiOnOff
	  MAX-ACCESS read-only
	  STATUS current
	  DESCRIPTION
        "
        Fuse B Fail :This OID indicates 
        that the fuse of the power input 
        B is in fail condition  <Help>
          Status of the Fuse B <Condtype> 
        DEF_FUSE_B <Probcause> powerProblem 
        (36) <Alarmtype> equipmentAlarm 
        (5) <Polarity> (2) 
        "
	  ::= { pm1005AlmsynthAlm0 16 }



pm1005AlmDefFuseA OBJECT-TYPE
	  SYNTAX EkiOnOff
	  MAX-ACCESS read-only
	  STATUS current
	  DESCRIPTION
        "
        Fuse A Fail :This OID indicates 
        that the fuse of the power input 
        A is in fail condition  <Help>
          Status of the Fuse A <Condtype> 
        DEF_FUSE_A <Probcause> powerProblem 
        (36) <Alarmtype> equipmentAlarm 
        (5) <Polarity> (2) 
        "
	  ::= { pm1005AlmsynthAlm0 15 }



pm1005AlmModGlobFail OBJECT-TYPE
	  SYNTAX EkiOnOff
	  MAX-ACCESS read-only
	  STATUS current
	  DESCRIPTION
        "
        Module Failure :This OID is set 
        on detection of a failure originating 
        from the PM <Condtype> MOD_GLOB_FAIL 
        <Probcause> equipmentMalfunction 
        (16) <Alarmtype> synthesisAlarm 
        (12)  <Polarity> (2) 
        "
	  ::= { pm1005AlmsynthAlm0 9 }



--- *****************************************************
---     LEAF for the synthAlm2 article
--- *****************************************************
pm1005AlmsynthAlm2 OBJECT IDENTIFIER ::= { pm1005AlmOtherNurg 2 }




pm1005AlmMaintenanceOn OBJECT-TYPE
	  SYNTAX EkiOnOff
	  MAX-ACCESS read-only
	  STATUS current
	  DESCRIPTION
        "
        Maintenance Mode :This OID indicates 
        that the PM is in maintenance mode. 
         <Help>  This alarm indicates that 
        the maintenance mode is enabled 
        on the PM <Condtype> MAINTENANCE_ON 
        <Probcause> other (1) <Alarmtype> 
         <Polarity> (2) 
        "
	  ::= { pm1005AlmsynthAlm2 5 }



pm1005AlmCorrelatOff OBJECT-TYPE
	  SYNTAX EkiOnOff
	  MAX-ACCESS read-only
	  STATUS current
	  DESCRIPTION
        "
        Not Used :This OID, when set,
         indicates that alarm correlation 
        is not being performed. <Condtype> 
        CORRELAT_OFF <Probcause> other
         (1) <Alarmtype>  <Polarity> (2) 
        "
	  ::= { pm1005AlmsynthAlm2 4 }



pm1005AlmConfTableLoad OBJECT-TYPE
	  SYNTAX EkiOnOff
	  MAX-ACCESS read-only
	  STATUS current
	  DESCRIPTION
        "
        PM Configuration Load :This OID 
         is at 1 during the loading of
         configuration tables in the modules 
        RAM. <Condtype> CONF_TABLE_LOAD 
        <Probcause> other (1) <Alarmtype> 
         <Polarity> (2) 
        "
	  ::= { pm1005AlmsynthAlm2 3 }



pm1005AlmInvUpload OBJECT-TYPE
	  SYNTAX EkiOnOff
	  MAX-ACCESS read-only
	  STATUS current
	  DESCRIPTION
        "
        Inventory Upload :This OID is
         at 1 during the uploading of PM 
        inventory information. <Condtype> 
        INV_UPLOAD <Probcause> other (1) 
        <Alarmtype>  <Polarity> (2) 
        "
	  ::= { pm1005AlmsynthAlm2 2 }



pm1005AlmConfTableSave OBJECT-TYPE
	  SYNTAX EkiOnOff
	  MAX-ACCESS read-only
	  STATUS current
	  DESCRIPTION
        "
        PM Configuration Save :This OID 
        is at 1 during the saving of a
         new configuration table in the 
        module Flash memory. <Condtype> 
        CONF_TABLE_SAVE <Probcause> other 
        (1) <Alarmtype>  <Polarity> (2) 
        "
	  ::= { pm1005AlmsynthAlm2 1 }



--- *********************************************************
---     TABLE for the pm1005AlmsynthAlmLine articles
--- *********************************************************

pm1005AlmsynthAlmLineTable OBJECT-TYPE
	SYNTAX  SEQUENCE OF Pm1005AlmsynthAlmLineEntry
	MAX-ACCESS not-accessible
	STATUS current
	DESCRIPTION
        "
        List of pm1005AlmsynthAlmLine
         Article
        "
	::= { pm1005AlmLineCrit 7 }


pm1005AlmsynthAlmLineEntry OBJECT-TYPE
	SYNTAX Pm1005AlmsynthAlmLineEntry
	MAX-ACCESS not-accessible
	STATUS current
	DESCRIPTION
        "
        Row definition for the pm1005AlmsynthAlmLine 
        table
        "
	INDEX   { pm1005AlmsynthAlmLineIndex }
	::= { pm1005AlmsynthAlmLineTable 1 }


Pm1005AlmsynthAlmLineEntry ::=
	SEQUENCE {
	pm1005AlmsynthAlmLineIndex
		INTEGER,
	pm1005AlmLineActivePortn
		EkiOnOff,
	pm1005AlmLineFailPortn
		EkiOnOff,
	pm1005AlmLineDdmAlmPortn
		EkiOnOff,
	pm1005AlmLineDdmWarningPortn
		EkiOnOff,
	pm1005AlmUpRdiInsPortn
		EkiOnOff,
	pm1005AlmLineLocalOosPortn
		EkiOnOff,
	pm1005AlmXfpTxOffPortn
		EkiOnOff,
	pm1005AlmLineHwFailPortn
		EkiOnOff,
	pm1005AlmXfpInitNotComplPortn
		EkiOnOff,
	pm1005AlmXfpAbsentPortn
		EkiOnOff
	}


pm1005AlmsynthAlmLineIndex OBJECT-TYPE
	SYNTAX  INTEGER(0..128)
	MAX-ACCESS  read-only
	STATUS current
	DESCRIPTION
        "
        Index definition for the pm1005AlmsynthAlmLine 
        table
        "
	::= { pm1005AlmsynthAlmLineEntry 1 }


pm1005AlmLineActivePortn OBJECT-TYPE
	SYNTAX  EkiOnOff
	MAX-ACCESS read-only
	STATUS current
	DESCRIPTION
        "
        Line Active :This bit indicates 
        the line #n is active on receive 
        side  <Help>  This status indicates 
        whether the line is active or standby. 
        <Condtype> LINE_ACTIVE <Probcause> 
        informationalStatus(1000) <Alarmtype> 
        other (1) <Polarity> (2) 
        "
	::= { pm1005AlmsynthAlmLineEntry 17 }


pm1005AlmLineFailPortn OBJECT-TYPE
	SYNTAX  EkiOnOff
	MAX-ACCESS read-only
	STATUS current
	DESCRIPTION
        "
        Line Port Failure :This OID indicates 
        a failure on the line port <Condtype> 
        LINE_FAIL <Probcause> equipmentMalfunction 
        (16) <Alarmtype> synthesisAlarm 
        (12)  <Polarity> (2)
        "
	::= { pm1005AlmsynthAlmLineEntry 13 }


pm1005AlmLineDdmAlmPortn OBJECT-TYPE
	SYNTAX  EkiOnOff
	MAX-ACCESS read-only
	STATUS current
	DESCRIPTION
        "
        Alarm On Line Optical Module DDM 
        :This OID indicates an alarm is 
        present coming out of Line optical 
        interface DDM  <Help>  This alarm 
        indicates if a DDM Alarm has been 
        detected on the line transceiver 
        <Condtype> LINE_DDM_ALM <Probcause> 
        equipmentMalfunction (16) <Alarmtype> 
        synthesisAlarm (12)  <Polarity> 
        (2)
        "
	::= { pm1005AlmsynthAlmLineEntry 11 }


pm1005AlmLineDdmWarningPortn OBJECT-TYPE
	SYNTAX  EkiOnOff
	MAX-ACCESS read-only
	STATUS current
	DESCRIPTION
        "
        Warning On Line Optical Module 
        DDM :This OID indicates a warning 
        is present coming out of Line optical 
        interface DDM  <Help>  This alarm 
        indicates if a DDM Warning has
         been detected on the line transceiver 
        <Condtype> LINE_DDM_WARNING <Probcause> 
        equipmentMalfunction (16) <Alarmtype> 
        synthesisAlarm (12)  <Polarity> 
        (2)
        "
	::= { pm1005AlmsynthAlmLineEntry 10 }


pm1005AlmUpRdiInsPortn OBJECT-TYPE
	SYNTAX  EkiOnOff
	MAX-ACCESS read-only
	STATUS current
	DESCRIPTION
        "
        MS-RDI/L-RDI Inserted On Line
         :This OID indicates an upstream 
        MS-RDI/L-RDI has been inserted
         in the outgoing 10 Gb/s SDH/SONET 
        signal.   <Help>  This status indicates 
        if a MS-RDI/L-RDI is currently
         inserted on the line interface. 
        <Condtype> UP_RDI_INS <Probcause> 
        informationalStatus(1000) <Alarmtype> 
        other (1) <Polarity> (2) 
        "
	::= { pm1005AlmsynthAlmLineEntry 9 }


pm1005AlmLineLocalOosPortn OBJECT-TYPE
	SYNTAX  EkiOnOff
	MAX-ACCESS read-only
	STATUS current
	DESCRIPTION
        "
        Line Port In Service :This OID 
        indicates that the Line port is 
        In Service (1) of Out or Service 
        (2)  <Help>  This status indicates 
        if the line port is in service
         <Condtype> LINE_LOCAL_OOS <Probcause> 
        informationalStatus(1000) <Alarmtype> 
        other (1) <Polarity> (2) 
        "
	::= { pm1005AlmsynthAlmLineEntry 7 }


pm1005AlmXfpTxOffPortn OBJECT-TYPE
	SYNTAX  EkiOnOff
	MAX-ACCESS read-only
	STATUS current
	DESCRIPTION
        "
        Line Optical Module Laser Shutdown 
        :This OID indicates the line optical 
        output power is on  <Help>  This 
        status indicates if the line transceiver 
        laser is ON or OFF <Condtype> XFP_TX_OFF 
        <Probcause> other (1) <Alarmtype> 
        equipmentAlarm (5) <Polarity> (2) 
        "
	::= { pm1005AlmsynthAlmLineEntry 6 }


pm1005AlmLineHwFailPortn OBJECT-TYPE
	SYNTAX  EkiOnOff
	MAX-ACCESS read-only
	STATUS current
	DESCRIPTION
        "
        Line Port HW Failure :This OID 
        indicates a failure on line port, 
        most probably caused by a HW issue 
        <Condtype> LINE_HW_FAIL <Probcause> 
        equipmentMalfunction (16) <Alarmtype> 
        synthesisAlarm (12)  <Polarity> 
        (2) 
        "
	::= { pm1005AlmsynthAlmLineEntry 5 }


pm1005AlmXfpInitNotComplPortn OBJECT-TYPE
	SYNTAX  EkiOnOff
	MAX-ACCESS read-only
	STATUS current
	DESCRIPTION
        "
        Line Optical Module Ready :This 
        OID indicates that the optical
         interface (XFP or OTX) is not
         operational.  <Help>  This status 
        indicates if the line transceiver 
        has been correctly initialized
         <Condtype> XFP_INIT_NOT_COMPL
         <Probcause> equipmentMalfunction 
        (16) <Alarmtype> equipmentAlarm 
        (5) <Polarity> (2) <Event> ObjectCDINV
        "
	::= { pm1005AlmsynthAlmLineEntry 3 }


pm1005AlmXfpAbsentPortn OBJECT-TYPE
	SYNTAX  EkiOnOff
	MAX-ACCESS read-only
	STATUS current
	DESCRIPTION
        "
        Line Optical Module Absent :This 
        OID indicates that the line optical 
        interface (XFP or OTX) is not plugged 
        in.  <Help>  This alarm indicates 
        if the line transceiver is present. 
        <Condtype> XFP_ABSENT <Probcause> 
        inputOutputDeviceError (24) <Alarmtype> 
        equipmentAlarm (5) <Polarity> (2) 
        <Event> ObjectCDINV
        "
	::= { pm1005AlmsynthAlmLineEntry 2 }


--- *********************************************************
---     TABLE for the pm1005AlmsynthAlmPort articles
--- *********************************************************

pm1005AlmsynthAlmPortTable OBJECT-TYPE
	SYNTAX  SEQUENCE OF Pm1005AlmsynthAlmPortEntry
	MAX-ACCESS not-accessible
	STATUS current
	DESCRIPTION
        "
        List of pm1005AlmsynthAlmPort
         Article
        "
	::= { pm1005AlmClientCrit 8 }


pm1005AlmsynthAlmPortEntry OBJECT-TYPE
	SYNTAX Pm1005AlmsynthAlmPortEntry
	MAX-ACCESS not-accessible
	STATUS current
	DESCRIPTION
        "
        Row definition for the pm1005AlmsynthAlmPort 
        table
        "
	INDEX   { pm1005AlmsynthAlmPortIndex }
	::= { pm1005AlmsynthAlmPortTable 1 }


Pm1005AlmsynthAlmPortEntry ::=
	SEQUENCE {
	pm1005AlmsynthAlmPortIndex
		INTEGER,
	pm1005AlmUpCsfPortn
		EkiOnOff,
	pm1005AlmFailAccPortn
		EkiOnOff,
	pm1005AlmSfpDdmAlmPortn
		EkiOnOff,
	pm1005AlmSfpDdmWarningPortn
		EkiOnOff,
	pm1005AlmDwCaisPortn
		EkiOnOff,
	pm1005AlmClientRemoteOosPortn
		EkiOnOff,
	pm1005AlmClientLocalOosPortn
		EkiOnOff,
	pm1005AlmDwLsdPortn
		EkiOnOff,
	pm1005AlmHwFailAccPortn
		EkiOnOff,
	pm1005AlmDdmAbsentPortn
		EkiOnOff,
	pm1005AlmSfpAbsentPortn
		EkiOnOff
	}


pm1005AlmsynthAlmPortIndex OBJECT-TYPE
	SYNTAX  INTEGER(0..128)
	MAX-ACCESS  read-only
	STATUS current
	DESCRIPTION
        "
        Index definition for the pm1005AlmsynthAlmPort 
        table
        "
	::= { pm1005AlmsynthAlmPortEntry 1 }


pm1005AlmUpCsfPortn OBJECT-TYPE
	SYNTAX  EkiOnOff
	MAX-ACCESS read-only
	STATUS current
	DESCRIPTION
        "
        Client Signal Fail Inserted :This 
        OID indicates a CSF has been inserted 
        in the upstream client port.  <Help> 
         This status indicates if a Client 
        Signal Fail is currently inserted 
        on the line signal for this client 
        port <Condtype> UP_CSF_1 <Probcause> 
        other (1) <Alarmtype> other (1) 
        <Polarity> (2) 
        "
	::= { pm1005AlmsynthAlmPortEntry 17 }


pm1005AlmFailAccPortn OBJECT-TYPE
	SYNTAX  EkiOnOff
	MAX-ACCESS read-only
	STATUS current
	DESCRIPTION
        "
        Client Access Fail :This OID indicates 
        a failure on the Client port <Condtype> 
        FAIL_ACC_1 <Probcause> equipmentMalfunction 
        (16) <Alarmtype> synthesisAlarm 
        (12)  <Polarity> (2)
        "
	::= { pm1005AlmsynthAlmPortEntry 13 }


pm1005AlmSfpDdmAlmPortn OBJECT-TYPE
	SYNTAX  EkiOnOff
	MAX-ACCESS read-only
	STATUS current
	DESCRIPTION
        "
        Alarm On Client SFP DDM :This
         OID indicates an alarm is being 
        received from the Client SFP DDM 
         <Help>  This alarm indicates if 
        a DDM Alarm has been detected on 
        the client transceiver <Condtype> 
        SFP_DDM_ALM_1 <Probcause> equipmentMalfunction 
        (16) <Alarmtype> synthesisAlarm 
        (12)  <Polarity> (2)
        "
	::= { pm1005AlmsynthAlmPortEntry 11 }


pm1005AlmSfpDdmWarningPortn OBJECT-TYPE
	SYNTAX  EkiOnOff
	MAX-ACCESS read-only
	STATUS current
	DESCRIPTION
        "
        Warning On Client SFP DDM :This 
        OID indicates a warning is being 
        received from the Client SFP DDM 
         <Help>  This alarm indicates if 
        a DDM Warning has been detected 
        on the client transceiver <Condtype> 
        SFP_DDM_WARNING_1 <Probcause> equipmentMalfunction 
        (16) <Alarmtype> synthesisAlarm 
        (12)  <Polarity> (2)
        "
	::= { pm1005AlmsynthAlmPortEntry 10 }


pm1005AlmDwCaisPortn OBJECT-TYPE
	SYNTAX  EkiOnOff
	MAX-ACCESS read-only
	STATUS current
	DESCRIPTION
        "
        Client AIS Inserted :This OID
         indicates a CAIS has been inserted 
        on the output client port.  <Help> 
         This status indicates if a Client 
        Alarm Indication Signal is currently 
        inserted on the client interface 
        <Condtype> DW_CAIS_1 <Probcause> 
        informationalStatus(1000) <Alarmtype> 
        other (1) <Polarity> (2) 
        "
	::= { pm1005AlmsynthAlmPortEntry 9 }


pm1005AlmClientRemoteOosPortn OBJECT-TYPE
	SYNTAX  EkiOnOff
	MAX-ACCESS read-only
	STATUS current
	DESCRIPTION
        "
        Remote Client Port In Service
         :This OID indicates that the remote 
        Client port is In Service (1) or 
        Out of Service (2)  <Help>  This 
        status indicates if the remote
         client port is in service <Condtype> 
        CLIENT_REMOTE_OOS <Probcause> informationalStatus(1000) 
        <Alarmtype> other (1) <Polarity> 
        (2) 
        "
	::= { pm1005AlmsynthAlmPortEntry 8 }


pm1005AlmClientLocalOosPortn OBJECT-TYPE
	SYNTAX  EkiOnOff
	MAX-ACCESS read-only
	STATUS current
	DESCRIPTION
        "
        Local Client Port In Service :This 
        OID indicates that the local Client 
        port is In Service (1) or Out of 
        Service (2)  <Help>  This status 
        indicates if the local client port 
        is in service <Condtype> CLIENT_LOCAL_OOS 
        <Probcause> informationalStatus(1000) 
        <Alarmtype> other (1) <Polarity> 
        (2) 
        "
	::= { pm1005AlmsynthAlmPortEntry 7 }


pm1005AlmDwLsdPortn OBJECT-TYPE
	SYNTAX  EkiOnOff
	MAX-ACCESS read-only
	STATUS current
	DESCRIPTION
        "
        Client SFP Laser Shutdown :This 
        OID indicates the Client SFP transmitter 
        output is ON.   <Help>  This status 
        indicates if the client transceiver 
        laser is ON or OFF <Condtype> DW_LSD_1 
        <Probcause> other (1) <Alarmtype> 
        equipmentAlarm (5) <Polarity> (2) 
        "
	::= { pm1005AlmsynthAlmPortEntry 6 }


pm1005AlmHwFailAccPortn OBJECT-TYPE
	SYNTAX  EkiOnOff
	MAX-ACCESS read-only
	STATUS current
	DESCRIPTION
        "
        Client HW Fail :This OID indicates 
        a failure on client port, most
         probably caused by a HW issue. 
        <Condtype> HW_FAIL_ACC_1 <Probcause> 
        equipmentMalfunction (16) <Alarmtype> 
        synthesisAlarm (12)  <Polarity> 
        (2) 
        "
	::= { pm1005AlmsynthAlmPortEntry 5 }


pm1005AlmDdmAbsentPortn OBJECT-TYPE
	SYNTAX  EkiOnOff
	MAX-ACCESS read-only
	STATUS current
	DESCRIPTION
        "
        DDM Supported On Client SFP :This 
        OID indicates that the Client SFP 
        module supports the Digital Diagnostic 
        Monitoring function  <Help>  This 
        status indicates if the client
         transceiver includes the DDM feature 
        <Condtype> DDM_ABSENT_1 <Probcause> 
        informationalStatus(1000) <Alarmtype> 
        other (1) <Polarity> (2) 
        "
	::= { pm1005AlmsynthAlmPortEntry 3 }


pm1005AlmSfpAbsentPortn OBJECT-TYPE
	SYNTAX  EkiOnOff
	MAX-ACCESS read-only
	STATUS current
	DESCRIPTION
        "
        Client SFP Absent :This OID indicates 
        that the SFP module is not present 
        in the client port.  <Help>  This 
        alarm indicates if the client transceiver 
        is present. <Condtype> SFP_ABSENT_1 
        <Probcause> inputOutputDeviceError 
        (24) <Alarmtype> equipmentAlarm 
        (5) <Polarity> (2) <Event> ObjectCDINV
        "
	::= { pm1005AlmsynthAlmPortEntry 2 }


--- *********************************************************
---     TABLE for the pm1005AlmaccessioAlm articles
--- *********************************************************

pm1005AlmaccessioAlmTable OBJECT-TYPE
	SYNTAX  SEQUENCE OF Pm1005AlmaccessioAlmEntry
	MAX-ACCESS not-accessible
	STATUS current
	DESCRIPTION
        "
        List of pm1005AlmaccessioAlm Article
        "
	::= { pm1005AlmClientCrit 16 }


pm1005AlmaccessioAlmEntry OBJECT-TYPE
	SYNTAX Pm1005AlmaccessioAlmEntry
	MAX-ACCESS not-accessible
	STATUS current
	DESCRIPTION
        "
        Row definition for the pm1005AlmaccessioAlm 
        table
        "
	INDEX   { pm1005AlmaccessioAlmIndex }
	::= { pm1005AlmaccessioAlmTable 1 }


Pm1005AlmaccessioAlmEntry ::=
	SEQUENCE {
	pm1005AlmaccessioAlmIndex
		INTEGER,
	pm1005AlmUpLosPortn
		EkiOnOff,
	pm1005AlmDwLasFailPortn
		EkiOnOff
	}


pm1005AlmaccessioAlmIndex OBJECT-TYPE
	SYNTAX  INTEGER(0..128)
	MAX-ACCESS  read-only
	STATUS current
	DESCRIPTION
        "
        Index definition for the pm1005AlmaccessioAlm 
        table
        "
	::= { pm1005AlmaccessioAlmEntry 1 }


pm1005AlmUpLosPortn OBJECT-TYPE
	SYNTAX  EkiOnOff
	MAX-ACCESS read-only
	STATUS current
	DESCRIPTION
        "
        Client Input Loss Of Signal :This 
        OID indicates that no signal is 
        present on the SFP of the client 
        port  <Help>  This alarm indicates 
        if an optical signal is detected 
        on the client transceiver input 
        <Condtype> UP_LOS_1 <Probcause> 
        receiveFailure (41) <Alarmtype> 
        physicalViolation (9) <Polarity> 
        (2) 
        "
	::= { pm1005AlmaccessioAlmEntry 5 }


pm1005AlmDwLasFailPortn OBJECT-TYPE
	SYNTAX  EkiOnOff
	MAX-ACCESS read-only
	STATUS current
	DESCRIPTION
        "
        Client SFP Tx Failed :This OID 
        indicates that the transmitter
         fails for the SFP plugged into 
        the client port (this alarm reports 
        the transmitter failure alarm generated 
        by the SFPs)  <Help>  This alarm 
        indicates if the laser of the client 
        transceiver is in <Condtype> DW_LAS_FAIL_1 
        <Probcause> transmitterFailure
         (56) <Alarmtype> equipmentAlarm 
        (5) <Polarity> (2) 
        "
	::= { pm1005AlmaccessioAlmEntry 2 }


--- *********************************************************
---     TABLE for the pm1005AlmsfpAlmDdm articles
--- *********************************************************

pm1005AlmsfpAlmDdmTable OBJECT-TYPE
	SYNTAX  SEQUENCE OF Pm1005AlmsfpAlmDdmEntry
	MAX-ACCESS not-accessible
	STATUS current
	DESCRIPTION
        "
        List of pm1005AlmsfpAlmDdm Article
        "
	::= { pm1005AlmClientUrg 32 }


pm1005AlmsfpAlmDdmEntry OBJECT-TYPE
	SYNTAX Pm1005AlmsfpAlmDdmEntry
	MAX-ACCESS not-accessible
	STATUS current
	DESCRIPTION
        "
        Row definition for the pm1005AlmsfpAlmDdm 
        table
        "
	INDEX   { pm1005AlmsfpAlmDdmIndex }
	::= { pm1005AlmsfpAlmDdmTable 1 }


Pm1005AlmsfpAlmDdmEntry ::=
	SEQUENCE {
	pm1005AlmsfpAlmDdmIndex
		INTEGER,
	pm1005AlmRxPwrHighAlaPortn
		EkiOnOff,
	pm1005AlmRxPwrLowAlaPortn
		EkiOnOff,
	pm1005AlmTempHighAlaPortn
		EkiOnOff,
	pm1005AlmTempLowAlaPortn
		EkiOnOff,
	pm1005AlmVccHighAlaPortn
		EkiOnOff,
	pm1005AlmVccLowAlaPortn
		EkiOnOff,
	pm1005AlmTxBiasHighAlaPortn
		EkiOnOff,
	pm1005AlmTxBiasLowAlaPortn
		EkiOnOff,
	pm1005AlmTxPwrHighAlaPortn
		EkiOnOff,
	pm1005AlmTxPwrLowAlaPortn
		EkiOnOff
	}


pm1005AlmsfpAlmDdmIndex OBJECT-TYPE
	SYNTAX  INTEGER(0..128)
	MAX-ACCESS  read-only
	STATUS current
	DESCRIPTION
        "
        Index definition for the pm1005AlmsfpAlmDdm 
        table
        "
	::= { pm1005AlmsfpAlmDdmEntry 1 }


pm1005AlmRxPwrHighAlaPortn OBJECT-TYPE
	SYNTAX  EkiOnOff
	MAX-ACCESS read-only
	STATUS current
	DESCRIPTION
        "
        Client SFP Rx Power High :Alarm 
        indicating that the SFP input power 
        of port is higher than the threshold 
        value written in the SFP EEPROM 
        <Condtype> RX_PWR_HIGH_ALA_1 <Probcause> 
        receiveFailure (41) <Alarmtype> 
        equipmentAlarm (5) <Polarity> (2) 
        "
	::= { pm1005AlmsfpAlmDdmEntry 17 }


pm1005AlmRxPwrLowAlaPortn OBJECT-TYPE
	SYNTAX  EkiOnOff
	MAX-ACCESS read-only
	STATUS current
	DESCRIPTION
        "
        Client SFP Rx Power Low :Alarm 
        indicating that the SFP input power 
        of port is lower than the threshold 
        value written in the SFP EEPROM 
        <Condtype> RX_PWR_LOW_ALA_1 <Probcause> 
        receiveFailure (41) <Alarmtype> 
        equipmentAlarm (5) <Polarity> (2) 
        "
	::= { pm1005AlmsfpAlmDdmEntry 16 }


pm1005AlmTempHighAlaPortn OBJECT-TYPE
	SYNTAX  EkiOnOff
	MAX-ACCESS read-only
	STATUS current
	DESCRIPTION
        "
        Client SFP Temp High :Alarm indicating 
        that the SFP temperature of port 
        is higher than the threshold value 
        written in the SFP EEPROM <Condtype> 
        TEMP_HIGH_ALA_1 <Probcause> temperatureUnacceptable 
        (51) <Alarmtype> equipmentAlarm 
        (5) <Polarity> (2) 
        "
	::= { pm1005AlmsfpAlmDdmEntry 9 }


pm1005AlmTempLowAlaPortn OBJECT-TYPE
	SYNTAX  EkiOnOff
	MAX-ACCESS read-only
	STATUS current
	DESCRIPTION
        "
        Client SFP Temp Low :Alarm indicating 
        that the SFP temperature of port 
        is lower than the threshold value 
        written in the SFP EEPROM <Condtype> 
        TEMP_LOW_ALA_1 <Probcause> temperatureUnacceptable 
        (51) <Alarmtype> equipmentAlarm 
        (5) <Polarity> (2) 
        "
	::= { pm1005AlmsfpAlmDdmEntry 8 }


pm1005AlmVccHighAlaPortn OBJECT-TYPE
	SYNTAX  EkiOnOff
	MAX-ACCESS read-only
	STATUS current
	DESCRIPTION
        "
        Client SFP Power Supply High :Alarm 
        indicating that the SFP power supply 
        of port is higher than the threshold 
        value written in the SFP EEPROM 
         <Condtype> VCC_HIGH_ALA_1 <Probcause> 
        powerProblem (36) <Alarmtype> equipmentAlarm 
        (5) <Polarity> (2) 
        "
	::= { pm1005AlmsfpAlmDdmEntry 7 }


pm1005AlmVccLowAlaPortn OBJECT-TYPE
	SYNTAX  EkiOnOff
	MAX-ACCESS read-only
	STATUS current
	DESCRIPTION
        "
        Client SFP Power Supply Low :Alarm 
        indicating that the SFP power supply 
        of port is lower than the threshold 
        value written in the SFP EEPROM 
         <Condtype> VCC_LOW_ALA_1 <Probcause> 
        powerProblem (36) <Alarmtype> equipmentAlarm 
        (5) <Polarity> (2) 
        "
	::= { pm1005AlmsfpAlmDdmEntry 6 }


pm1005AlmTxBiasHighAlaPortn OBJECT-TYPE
	SYNTAX  EkiOnOff
	MAX-ACCESS read-only
	STATUS current
	DESCRIPTION
        "
        Client SFP Bias High :Alarm indicating 
        that the SFP laser bias current 
        of port is higher than the threshold 
        value written in the SFP EEPROM 
        <Condtype> TX_BIAS_HIGH_ALA_1 <Probcause> 
        transmitterFailure (56) <Alarmtype> 
        equipmentAlarm (5) <Polarity> (2) 
        "
	::= { pm1005AlmsfpAlmDdmEntry 5 }


pm1005AlmTxBiasLowAlaPortn OBJECT-TYPE
	SYNTAX  EkiOnOff
	MAX-ACCESS read-only
	STATUS current
	DESCRIPTION
        "
        Client SFP Bias Low :Alarm indicating 
        that the SFP laser bias current 
        of port is lower than the threshold 
        value written in the SFP EEPROM 
        <Condtype> TX_BIAS_LOW_ALA_1 <Probcause> 
        transmitterFailure (56) <Alarmtype> 
        equipmentAlarm (5) <Polarity> (2) 
        "
	::= { pm1005AlmsfpAlmDdmEntry 4 }


pm1005AlmTxPwrHighAlaPortn OBJECT-TYPE
	SYNTAX  EkiOnOff
	MAX-ACCESS read-only
	STATUS current
	DESCRIPTION
        "
        Client SFP Tx Power High :Alarm 
        indicating that the SFP output
         power of port is higher than the 
        threshold value written in the
         SFP EEPROM <Condtype> TX_PWR_HIGH_ALA_1 
        <Probcause> transmitterFailure
         (56) <Alarmtype> equipmentAlarm 
        (5) <Polarity> (2) 
        "
	::= { pm1005AlmsfpAlmDdmEntry 3 }


pm1005AlmTxPwrLowAlaPortn OBJECT-TYPE
	SYNTAX  EkiOnOff
	MAX-ACCESS read-only
	STATUS current
	DESCRIPTION
        "
        Client SFP Tx Power Low :Alarm 
        indicating that the SFP output
         power of port is lower than the 
        threshold value written in the
         SFP EEPROM <Condtype> TX_PWR_LOW_ALA_1 
        <Probcause> transmitterFailure
         (56) <Alarmtype> equipmentAlarm 
        (5) <Polarity> (2) 
        "
	::= { pm1005AlmsfpAlmDdmEntry 2 }


--- *********************************************************
---     TABLE for the pm1005AlmsfpWarnDdm articles
--- *********************************************************

pm1005AlmsfpWarnDdmTable OBJECT-TYPE
	SYNTAX  SEQUENCE OF Pm1005AlmsfpWarnDdmEntry
	MAX-ACCESS not-accessible
	STATUS current
	DESCRIPTION
        "
        List of pm1005AlmsfpWarnDdm Article
        "
	::= { pm1005AlmClientNurg 48 }


pm1005AlmsfpWarnDdmEntry OBJECT-TYPE
	SYNTAX Pm1005AlmsfpWarnDdmEntry
	MAX-ACCESS not-accessible
	STATUS current
	DESCRIPTION
        "
        Row definition for the pm1005AlmsfpWarnDdm 
        table
        "
	INDEX   { pm1005AlmsfpWarnDdmIndex }
	::= { pm1005AlmsfpWarnDdmTable 1 }


Pm1005AlmsfpWarnDdmEntry ::=
	SEQUENCE {
	pm1005AlmsfpWarnDdmIndex
		INTEGER,
	pm1005AlmRxPwrHighWngPortn
		EkiOnOff,
	pm1005AlmRxPwrLowWngPortn
		EkiOnOff,
	pm1005AlmTempHighWngPortn
		EkiOnOff,
	pm1005AlmTempLowWngPortn
		EkiOnOff,
	pm1005AlmVccHighWngPortn
		EkiOnOff,
	pm1005AlmVccLowWngPortn
		EkiOnOff,
	pm1005AlmTxBiasHighWngPortn
		EkiOnOff,
	pm1005AlmTxBiasLowWngPortn
		EkiOnOff,
	pm1005AlmTxPwrHighWngPortn
		EkiOnOff,
	pm1005AlmTxPwLowWngPortn
		EkiOnOff
	}


pm1005AlmsfpWarnDdmIndex OBJECT-TYPE
	SYNTAX  INTEGER(0..128)
	MAX-ACCESS  read-only
	STATUS current
	DESCRIPTION
        "
        Index definition for the pm1005AlmsfpWarnDdm 
        table
        "
	::= { pm1005AlmsfpWarnDdmEntry 1 }


pm1005AlmRxPwrHighWngPortn OBJECT-TYPE
	SYNTAX  EkiOnOff
	MAX-ACCESS read-only
	STATUS current
	DESCRIPTION
        "
        Client SFP Rx Power High Warning 
        :Warning indicating that the SFP 
        input power of port is higher than 
        the threshold value written in
         the SFP EEPROM <Condtype> RX_PWR_HIGH_WNG_1 
        <Probcause> receiveFailure (41) 
        <Alarmtype> equipmentAlarm (5)
         <Polarity> (2) 
        "
	::= { pm1005AlmsfpWarnDdmEntry 17 }


pm1005AlmRxPwrLowWngPortn OBJECT-TYPE
	SYNTAX  EkiOnOff
	MAX-ACCESS read-only
	STATUS current
	DESCRIPTION
        "
        Client SFP Rx Power Low Warning 
        :Warning indicating that the SFP 
        input power of port is lower than 
        the threshold value written in
         the SFP EEPROM <Condtype> RX_PWR_LOW_WNG_1 
        <Probcause> receiveFailure (41) 
        <Alarmtype> equipmentAlarm (5)
         <Polarity> (2) 
        "
	::= { pm1005AlmsfpWarnDdmEntry 16 }


pm1005AlmTempHighWngPortn OBJECT-TYPE
	SYNTAX  EkiOnOff
	MAX-ACCESS read-only
	STATUS current
	DESCRIPTION
        "
        Client SFP Temp High Warning :Warning 
        indicating that the SFP temperature 
        of port is higher than the threshold 
        value written in the SFP EEPROM 
        <Condtype> TEMP_HIGH_WNG_1 <Probcause> 
        temperatureUnacceptable (51) <Alarmtype> 
        equipmentAlarm (5) <Polarity> (2) 
        "
	::= { pm1005AlmsfpWarnDdmEntry 9 }


pm1005AlmTempLowWngPortn OBJECT-TYPE
	SYNTAX  EkiOnOff
	MAX-ACCESS read-only
	STATUS current
	DESCRIPTION
        "
        Client SFP Temp Low Warning :Warning 
        indicating that the SFP temperature 
        of port is lower than the threshold 
        value written in the SFP EEPROM 
        <Condtype> TEMP_LOW_WNG_1 <Probcause> 
        temperatureUnacceptable (51) <Alarmtype> 
        equipmentAlarm (5) <Polarity> (2) 
        "
	::= { pm1005AlmsfpWarnDdmEntry 8 }


pm1005AlmVccHighWngPortn OBJECT-TYPE
	SYNTAX  EkiOnOff
	MAX-ACCESS read-only
	STATUS current
	DESCRIPTION
        "
        Client SFP Power Supply High Warning 
        :Warning indicating that the SFP 
        power supply of port is higher
         than the threshold value written 
        in the SFP EEPROM  <Condtype> VCC_HIGH_WNG_1 
        <Probcause> powerProblem (36) <Alarmtype> 
        equipmentAlarm (5) <Polarity> (2) 
        "
	::= { pm1005AlmsfpWarnDdmEntry 7 }


pm1005AlmVccLowWngPortn OBJECT-TYPE
	SYNTAX  EkiOnOff
	MAX-ACCESS read-only
	STATUS current
	DESCRIPTION
        "
        Client SFP Power Supply Low Warning 
        :Warning indicating that the SFP 
        power supply of port is lower than 
        the threshold value written in
         the SFP EEPROM  <Condtype> VCC_LOW_WNG_1 
        <Probcause> powerProblem (36) <Alarmtype> 
        equipmentAlarm (5) <Polarity> (2) 
        "
	::= { pm1005AlmsfpWarnDdmEntry 6 }


pm1005AlmTxBiasHighWngPortn OBJECT-TYPE
	SYNTAX  EkiOnOff
	MAX-ACCESS read-only
	STATUS current
	DESCRIPTION
        "
        Client SFP Bias High Warning :Warning 
        indicating that the SFP laser bias 
        current of port is higher than
         the threshold value written in 
        the SFP EEPROM <Condtype> TX_BIAS_HIGH_WNG_1 
        <Probcause> transmitterFailure
         (56) <Alarmtype> equipmentAlarm 
        (5) <Polarity> (2) 
        "
	::= { pm1005AlmsfpWarnDdmEntry 5 }


pm1005AlmTxBiasLowWngPortn OBJECT-TYPE
	SYNTAX  EkiOnOff
	MAX-ACCESS read-only
	STATUS current
	DESCRIPTION
        "
        Client SFP Bias Low Warning :Warning 
        indicating that the SFP laser bias 
        current of port is lower than the 
        threshold value written in the
         SFP EEPROM <Condtype> TX_BIAS_LOW_WNG_1 
        <Probcause> transmitterFailure
         (56) <Alarmtype> equipmentAlarm 
        (5) <Polarity> (2) 
        "
	::= { pm1005AlmsfpWarnDdmEntry 4 }


pm1005AlmTxPwrHighWngPortn OBJECT-TYPE
	SYNTAX  EkiOnOff
	MAX-ACCESS read-only
	STATUS current
	DESCRIPTION
        "
        Client SFP Tx Power High Warning 
        :Warning indicating that the SFP 
        output power of port is higher
         than the threshold value written 
        in the SFP EEPROM <Condtype> TX_PWR_HIGH_WNG_1 
        <Probcause> transmitterFailure
         (56) <Alarmtype> equipmentAlarm 
        (5) <Polarity> (2) 
        "
	::= { pm1005AlmsfpWarnDdmEntry 3 }


pm1005AlmTxPwLowWngPortn OBJECT-TYPE
	SYNTAX  EkiOnOff
	MAX-ACCESS read-only
	STATUS current
	DESCRIPTION
        "
        Client SFP Tx Power Low Warning 
        :Warning indicating that the SFP 
        output power of port is lower than 
        the threshold value written in
         the SFP EEPROM <Condtype> TX_PW_LOW_WNG_1 
        <Probcause> transmitterFailure
         (56) <Alarmtype> equipmentAlarm 
        (5) <Polarity> (2) 
        "
	::= { pm1005AlmsfpWarnDdmEntry 2 }


--- *********************************************************
---     TABLE for the pm1005AlmmapperDeAlm articles
--- *********************************************************

pm1005AlmmapperDeAlmTable OBJECT-TYPE
	SYNTAX  SEQUENCE OF Pm1005AlmmapperDeAlmEntry
	MAX-ACCESS not-accessible
	STATUS current
	DESCRIPTION
        "
        List of pm1005AlmmapperDeAlm Article
        "
	::= { pm1005AlmClientCrit 72 }


pm1005AlmmapperDeAlmEntry OBJECT-TYPE
	SYNTAX Pm1005AlmmapperDeAlmEntry
	MAX-ACCESS not-accessible
	STATUS current
	DESCRIPTION
        "
        Row definition for the pm1005AlmmapperDeAlm 
        table
        "
	INDEX   { pm1005AlmmapperDeAlmIndex }
	::= { pm1005AlmmapperDeAlmTable 1 }


Pm1005AlmmapperDeAlmEntry ::=
	SEQUENCE {
	pm1005AlmmapperDeAlmIndex
		INTEGER,
	pm1005AlmDwBufferOvlPortn
		EkiOnOff,
	pm1005AlmDwCsfDetPortn
		EkiOnOff,
	pm1005AlmUpBufferOvlPortn
		EkiOnOff,
	pm1005AlmUpAccOosPortn
		EkiOnOff
	}


pm1005AlmmapperDeAlmIndex OBJECT-TYPE
	SYNTAX  INTEGER(0..128)
	MAX-ACCESS  read-only
	STATUS current
	DESCRIPTION
        "
        Index definition for the pm1005AlmmapperDeAlm 
        table
        "
	::= { pm1005AlmmapperDeAlmEntry 1 }


pm1005AlmDwBufferOvlPortn OBJECT-TYPE
	SYNTAX  EkiOnOff
	MAX-ACCESS read-only
	STATUS current
	DESCRIPTION
        "
        Client Downstream Buffer Overload 
        :This OID indicates that the de-mapper 
        buffer for client port is in overload. 
         <Help>  This alarm indicates if 
        there is a downstream FIFO overload 
        for this client port <Condtype> 
        DW_BUFFER_OVL_1 <Probcause> equipmentMalfunction 
        (16) <Alarmtype> equipmentAlarm 
        (5) <Polarity> (2) 
        "
	::= { pm1005AlmmapperDeAlmEntry 15 }


pm1005AlmDwCsfDetPortn OBJECT-TYPE
	SYNTAX  EkiOnOff
	MAX-ACCESS read-only
	STATUS current
	DESCRIPTION
        "
        Client Signal Fail Detected :This 
        OID indicates that a CSF has been 
        detected on client port in the
         downstream direction   <Help>
          This alarm indicates if a Client 
        Signal Fail has been detected in 
        the incoming line frame for this 
        client port <Condtype> DW_CSF_DET_1 
        <Probcause> receiveFailure (41) 
        <Alarmtype> other (1) <Polarity> 
        (2) 
        "
	::= { pm1005AlmmapperDeAlmEntry 12 }


pm1005AlmUpBufferOvlPortn OBJECT-TYPE
	SYNTAX  EkiOnOff
	MAX-ACCESS read-only
	STATUS current
	DESCRIPTION
        "
        Client Upstream Buffer Overload 
        :This OID indicates that the rate 
        adaptation buffer for client port 
        is in overload.  <Help>  This alarm 
        indicates if there is a upstream 
        FIFO overload for this client port 
        <Condtype> UP_BUFFER_OVL_1 <Probcause> 
        receiveFailure (41) <Alarmtype> 
        integrityViolation (7) <Polarity> 
        (2) 
        "
	::= { pm1005AlmmapperDeAlmEntry 11 }


pm1005AlmUpAccOosPortn OBJECT-TYPE
	SYNTAX  EkiOnOff
	MAX-ACCESS read-only
	STATUS current
	DESCRIPTION
        "
        Client Loss Of 10b/8b Synchro
         :This OID indicates the upstream 
        client input port has lost synchronization 
        on its 10B/8B decoder  <Help> 
         This alarms indicates if the input 
        client signal is correctly synchronized 
        with the 10b/8b decoder <Condtype> 
        UP_ACC_OOS_1 <Probcause> receiveFailure 
        (41) <Alarmtype> integrityViolation 
        (7) <Polarity> (2) 
        "
	::= { pm1005AlmmapperDeAlmEntry 2 }


--- *********************************************************
---     TABLE for the pm1005AlmdfrmAlm articles
--- *********************************************************

pm1005AlmdfrmAlmTable OBJECT-TYPE
	SYNTAX  SEQUENCE OF Pm1005AlmdfrmAlmEntry
	MAX-ACCESS not-accessible
	STATUS current
	DESCRIPTION
        "
        List of pm1005AlmdfrmAlm Article
        "
	::= { pm1005AlmLineCrit 128 }


pm1005AlmdfrmAlmEntry OBJECT-TYPE
	SYNTAX Pm1005AlmdfrmAlmEntry
	MAX-ACCESS not-accessible
	STATUS current
	DESCRIPTION
        "
        Row definition for the pm1005AlmdfrmAlm 
        table
        "
	INDEX   { pm1005AlmdfrmAlmIndex }
	::= { pm1005AlmdfrmAlmTable 1 }


Pm1005AlmdfrmAlmEntry ::=
	SEQUENCE {
	pm1005AlmdfrmAlmIndex
		INTEGER,
	pm1005AlmDwLofPortn
		EkiOnOff,
	pm1005AlmDwOofPortn
		EkiOnOff,
	pm1005AlmDwRdiDetPortn
		EkiOnOff,
	pm1005AlmDwAisDetPortn
		EkiOnOff
	}


pm1005AlmdfrmAlmIndex OBJECT-TYPE
	SYNTAX  INTEGER(0..128)
	MAX-ACCESS  read-only
	STATUS current
	DESCRIPTION
        "
        Index definition for the pm1005AlmdfrmAlm 
        table
        "
	::= { pm1005AlmdfrmAlmEntry 1 }


pm1005AlmDwLofPortn OBJECT-TYPE
	SYNTAX  EkiOnOff
	MAX-ACCESS read-only
	STATUS current
	DESCRIPTION
        "
        SONET/SDH Line Loss Of Frame :This 
        OID indicates that a Loss Of Frame 
        has been detected on incoming 
         OC-48c/STM-16c input signal  <Help> 
         This alarm indicates if there
         is a Loss of Frame is detected 
        on the line input signal <Condtype> 
        DW_LOF_1 <Probcause> receiveFailure 
        (41) <Alarmtype> integrityViolation 
        (7) <Polarity> (2) 
        "
	::= { pm1005AlmdfrmAlmEntry 5 }


pm1005AlmDwOofPortn OBJECT-TYPE
	SYNTAX  EkiOnOff
	MAX-ACCESS read-only
	STATUS current
	DESCRIPTION
        "
        SONET/SDH Line Out Of Frame :This 
        OID indicates that an Out Of Frame 
        has been detected on incoming 
         OC-48c/STM-16c input signal  <Help> 
         This alarm indicates if there
         is a Out of Frame is detected
         on the line input signal <Condtype> 
        DW_OOF_1 <Probcause> receiveFailure 
        (41) <Alarmtype> integrityViolation 
        (7) <Polarity> (2) 
        "
	::= { pm1005AlmdfrmAlmEntry 4 }


pm1005AlmDwRdiDetPortn OBJECT-TYPE
	SYNTAX  EkiOnOff
	MAX-ACCESS read-only
	STATUS current
	DESCRIPTION
        "
        MS-RDI/L-RDI Detected On Line
         Input :This OID indicates that 
        an MS-RDI has been detected on
         incoming  OC-48c/STM-16c input 
        signal  <Help>  This alarm indicates 
        if there is a MS-RDI/L-RDI is detected 
        on the line input signal <Condtype> 
        DW_RDI_DET_1 <Probcause> remoteNodeTransmissionError 
        (43) <Alarmtype> other (1) <Polarity> 
        (2) 
        "
	::= { pm1005AlmdfrmAlmEntry 3 }


pm1005AlmDwAisDetPortn OBJECT-TYPE
	SYNTAX  EkiOnOff
	MAX-ACCESS read-only
	STATUS current
	DESCRIPTION
        "
        MS-AIS/L-AIS Detected On Line
         Input :This OID indicates that 
        an MS-AIS has been detected on
         incoming  OC-48c/STM-16c input 
        signal  <Help>  This alarm indicates 
        if there is a MS-AIS/L-AIS is detected 
        on the line input signal <Condtype> 
        DW_AIS_DET_1 <Probcause> receiveFailure 
        (41) <Alarmtype> operationalViolation 
        (8) <Polarity> (2) 
        "
	::= { pm1005AlmdfrmAlmEntry 2 }


--- *********************************************************
---     TABLE for the pm1005AlmdfrmBer articles
--- *********************************************************

pm1005AlmdfrmBerTable OBJECT-TYPE
	SYNTAX  SEQUENCE OF Pm1005AlmdfrmBerEntry
	MAX-ACCESS not-accessible
	STATUS current
	DESCRIPTION
        "
        List of pm1005AlmdfrmBer Article
        "
	::= { pm1005AlmLineUrg 129 }


pm1005AlmdfrmBerEntry OBJECT-TYPE
	SYNTAX Pm1005AlmdfrmBerEntry
	MAX-ACCESS not-accessible
	STATUS current
	DESCRIPTION
        "
        Row definition for the pm1005AlmdfrmBer 
        table
        "
	INDEX   { pm1005AlmdfrmBerIndex }
	::= { pm1005AlmdfrmBerTable 1 }


Pm1005AlmdfrmBerEntry ::=
	SEQUENCE {
	pm1005AlmdfrmBerIndex
		INTEGER,
	pm1005AlmLineDegradePortn
		EkiOnOff,
	pm1005AlmLineSignalFailPortn
		EkiOnOff,
	pm1005AlmLineSignalDegradePortn
		EkiOnOff
	}


pm1005AlmdfrmBerIndex OBJECT-TYPE
	SYNTAX  INTEGER(0..128)
	MAX-ACCESS  read-only
	STATUS current
	DESCRIPTION
        "
        Index definition for the pm1005AlmdfrmBer 
        table
        "
	::= { pm1005AlmdfrmBerEntry 1 }


pm1005AlmLineDegradePortn OBJECT-TYPE
	SYNTAX  EkiOnOff
	MAX-ACCESS read-only
	STATUS current
	DESCRIPTION
        "
        Fixed Line Signal Degrade :This 
        OID indicates that the line input 
        signal is DEGRADE. The assetion 
        hysteresis is fixed to 10-8 (assertion) 
        and 10-9 (de-assertion) <Condtype> 
        LINE_DEGRADE_1 <Probcause> degradedSignal 
        (13) <Alarmtype> qualityOfServiceAlarm 
        (3) <Polarity> (2) 
        "
	::= { pm1005AlmdfrmBerEntry 6 }


pm1005AlmLineSignalFailPortn OBJECT-TYPE
	SYNTAX  EkiOnOff
	MAX-ACCESS read-only
	STATUS current
	DESCRIPTION
        "
        Custom Line Signal Fail :This
         OID indicates that the line input 
        signal is FAIL. The assertion hysteresis 
        can be customized by the host <Condtype> 
        LINE_SIGNAL_FAIL_1 <Probcause>
         receiveFailure (41) <Alarmtype> 
        integrityViolation (7) <Polarity> 
        (2) 
        "
	::= { pm1005AlmdfrmBerEntry 3 }


pm1005AlmLineSignalDegradePortn OBJECT-TYPE
	SYNTAX  EkiOnOff
	MAX-ACCESS read-only
	STATUS current
	DESCRIPTION
        "
        Custom Line Signal Degrade :This 
        OID indicates that the line input 
        signal is DEGRADE. The assertion 
        hysteresis can customized by the 
        host <Condtype> LINE_SIGNAL_DEGRADE_1 
        <Probcause> degradedSignal (13) 
        <Alarmtype> qualityOfServiceAlarm 
        (3) <Polarity> (2) 
        "
	::= { pm1005AlmdfrmBerEntry 2 }


--- *********************************************************
---     TABLE for the pm1005AlmlineSyncAlarms articles
--- *********************************************************

pm1005AlmlineSyncAlarmsTable OBJECT-TYPE
	SYNTAX  SEQUENCE OF Pm1005AlmlineSyncAlarmsEntry
	MAX-ACCESS not-accessible
	STATUS current
	DESCRIPTION
        "
        List of pm1005AlmlineSyncAlarms 
        Article
        "
	::= { pm1005AlmLineCrit 133 }


pm1005AlmlineSyncAlarmsEntry OBJECT-TYPE
	SYNTAX Pm1005AlmlineSyncAlarmsEntry
	MAX-ACCESS not-accessible
	STATUS current
	DESCRIPTION
        "
        Row definition for the pm1005AlmlineSyncAlarms 
        table
        "
	INDEX   { pm1005AlmlineSyncAlarmsIndex }
	::= { pm1005AlmlineSyncAlarmsTable 1 }


Pm1005AlmlineSyncAlarmsEntry ::=
	SEQUENCE {
	pm1005AlmlineSyncAlarmsIndex
		INTEGER,
	pm1005AlmDwLosPortn
		EkiOnOff,
	pm1005AlmUpLockerrPortn
		EkiOnOff,
	pm1005AlmDwLockerrPortn
		EkiOnOff
	}


pm1005AlmlineSyncAlarmsIndex OBJECT-TYPE
	SYNTAX  INTEGER(0..128)
	MAX-ACCESS  read-only
	STATUS current
	DESCRIPTION
        "
        Index definition for the pm1005AlmlineSyncAlarms 
        table
        "
	::= { pm1005AlmlineSyncAlarmsEntry 1 }


pm1005AlmDwLosPortn OBJECT-TYPE
	SYNTAX  EkiOnOff
	MAX-ACCESS read-only
	STATUS current
	DESCRIPTION
        "
        Line Input Loss Of Signal :This 
        OID indicates a loss of signal
         on the 10 Gb/s input.  <Help>
          This alarm indicates if an optical 
        signal is detected on the line
         transceiver input <Condtype> DW_LOS 
        <Probcause> receiveFailure (41) 
        <Alarmtype> physicalViolation (9) 
        <Polarity> (2) 
        "
	::= { pm1005AlmlineSyncAlarmsEntry 17 }


pm1005AlmUpLockerrPortn OBJECT-TYPE
	SYNTAX  EkiOnOff
	MAX-ACCESS read-only
	STATUS current
	DESCRIPTION
        "
        Upstream Clock Lock Error :This 
        OID indicates that the serializer 
        output 10 Gb/s clock multiplier 
        unit is not locked. <Condtype>
         UP_LOCKERR <Probcause> receiveFailure 
        (41) <Alarmtype> equipmentAlarm 
        (5) <Polarity> (2) 
        "
	::= { pm1005AlmlineSyncAlarmsEntry 14 }


pm1005AlmDwLockerrPortn OBJECT-TYPE
	SYNTAX  EkiOnOff
	MAX-ACCESS read-only
	STATUS current
	DESCRIPTION
        "
        Downstream Clock Lock Error :This 
        OID indicates that the deserializer 
        input 10 Gb/s clock recovery is 
        not locked. <Condtype> DW_LOCKERR 
        <Probcause> receiveFailure (41) 
        <Alarmtype> equipmentAlarm (5)
         <Polarity> (2) 
        "
	::= { pm1005AlmlineSyncAlarmsEntry 13 }


--- *****************************************************
---     LEAF for the modInitFailLevel2 article
--- *****************************************************
pm1005AlmmodInitFailLevel2 OBJECT IDENTIFIER ::= { pm1005AlmOtherUrg 194 }




pm1005AlmSwInitFail OBJECT-TYPE
	  SYNTAX EkiOnOff
	  MAX-ACCESS read-only
	  STATUS current
	  DESCRIPTION
        "
        SW Init Fail :This OID indicates 
        that the SW intialization has caused 
        unknown intial conditions  <Help> 
         This alarm indicates if the SW 
        module is correctly initialized 
        <Condtype> SW_INIT_FAIL <Probcause> 
        softwareError (47) <Alarmtype>
         processingErrorAlarm (4) <Polarity> 
        (2) 
        "
	  ::= { pm1005AlmmodInitFailLevel2 5 }



pm1005AlmResetHwInitFail OBJECT-TYPE
	  SYNTAX EkiOnOff
	  MAX-ACCESS read-only
	  STATUS current
	  DESCRIPTION
        "
        Reset HW Init Fail :This OID indicates 
        that the HW intialization has caused 
        unknown intial conditions  <Help> 
         This alarm indicates if the HW 
        has been correctly initialized
         <Condtype> RESET_HW_INIT_FAIL
         <Probcause> softwareError (47) 
        <Alarmtype> processingErrorAlarm 
        (4) <Polarity> (2) 
        "
	  ::= { pm1005AlmmodInitFailLevel2 4 }



pm1005AlmBootUndone OBJECT-TYPE
	  SYNTAX EkiOnOff
	  MAX-ACCESS read-only
	  STATUS current
	  DESCRIPTION
        "
        Boot Undone :This OID indicates 
        that the boot has not been correctly 
        achieved  <Help>  This alarm indicates 
        if the module has correctly boot 
        <Condtype> BOOT_UNDONE <Probcause> 
        softwareError (47) <Alarmtype>
         processingErrorAlarm (4) <Polarity> 
        (2) 
        "
	  ::= { pm1005AlmmodInitFailLevel2 3 }



pm1005AlmNextColdBootForced OBJECT-TYPE
	  SYNTAX EkiOnOff
	  MAX-ACCESS read-only
	  STATUS current
	  DESCRIPTION
        "
        Next Cold Boot Forced :This OID 
        indicates that the next Reset will 
        be forced Cold  <Help>  This alarm 
        indicates that the next reset of 
        the module will be forced to cold 
        reset <Condtype> NEXT_COLD_BOOT_FORCED 
        <Probcause> informationalStatus(1000) 
        <Alarmtype> other (1) <Polarity> 
        (2) 
        "
	  ::= { pm1005AlmmodInitFailLevel2 2 }



pm1005AlmLedFail OBJECT-TYPE
	  SYNTAX EkiOnOff
	  MAX-ACCESS read-only
	  STATUS current
	  DESCRIPTION
        "
        Led Fail :This OID indicates that 
        Led register has not been correctly 
        initalized  <Help>  This alarm
         indicates if the module LEDs are 
        correctly initialized <Condtype> 
        LED_FAIL <Probcause> softwareError 
        (47) <Alarmtype> processingErrorAlarm 
        (4) <Polarity> (2) 
        "
	  ::= { pm1005AlmmodInitFailLevel2 1 }



--- *****************************************************
---     LEAF for the modInitFailLevel3 article
--- *****************************************************
pm1005AlmmodInitFailLevel3 OBJECT IDENTIFIER ::= { pm1005AlmOtherUrg 195 }




pm1005AlmClient8InitFail OBJECT-TYPE
	  SYNTAX EkiOnOff
	  MAX-ACCESS read-only
	  STATUS current
	  DESCRIPTION
        "
        Client8 Init Fail :This OID indicates 
        that Client 8 registers subset
         has not been correctly initialized 
         <Help>  This alarm indicates if 
        the client port 8 is correctly
         initialized <Condtype> CLIENT8_INIT_FAIL 
        <Probcause> softwareError (47)
         <Alarmtype> processingErrorAlarm 
        (4) <Polarity> (2) 
        "
	  ::= { pm1005AlmmodInitFailLevel3 16 }



pm1005AlmClient7InitFail OBJECT-TYPE
	  SYNTAX EkiOnOff
	  MAX-ACCESS read-only
	  STATUS current
	  DESCRIPTION
        "
        Client7 Init Fail :This OID indicates 
        that Client 7 registers subset
         has not been correctly initialized 
         <Help>  This alarm indicates if 
        the client port 7 is correctly
         initialized <Condtype> CLIENT7_INIT_FAIL 
        <Probcause> softwareError (47)
         <Alarmtype> processingErrorAlarm 
        (4) <Polarity> (2) 
        "
	  ::= { pm1005AlmmodInitFailLevel3 15 }



pm1005AlmClient6InitFail OBJECT-TYPE
	  SYNTAX EkiOnOff
	  MAX-ACCESS read-only
	  STATUS current
	  DESCRIPTION
        "
        Client6 Init Fail :This OID indicates 
        that Client 6 registers subset
         has not been correctly initialized 
         <Help>  This alarm indicates if 
        the client port 6 is correctly
         initialized <Condtype> CLIENT6_INIT_FAIL 
        <Probcause> softwareError (47)
         <Alarmtype> processingErrorAlarm 
        (4) <Polarity> (2) 
        "
	  ::= { pm1005AlmmodInitFailLevel3 14 }



pm1005AlmClient5InitFail OBJECT-TYPE
	  SYNTAX EkiOnOff
	  MAX-ACCESS read-only
	  STATUS current
	  DESCRIPTION
        "
        Client5 Init Fail :This OID indicates 
        that Client 5 registers subset
         has not been correctly initialized 
         <Help>  This alarm indicates if 
        the client port 5 is correctly
         initialized <Condtype> CLIENT5_INIT_FAIL 
        <Probcause> softwareError (47)
         <Alarmtype> processingErrorAlarm 
        (4) <Polarity> (2) 
        "
	  ::= { pm1005AlmmodInitFailLevel3 13 }



pm1005AlmClient4InitFail OBJECT-TYPE
	  SYNTAX EkiOnOff
	  MAX-ACCESS read-only
	  STATUS current
	  DESCRIPTION
        "
        Client4 Init Fail :This OID indicates 
        that Client 4 registers subset
         has not been correctly initialized 
         <Help>  This alarm indicates if 
        the client port 4 is correctly
         initialized <Condtype> CLIENT4_INIT_FAIL 
        <Probcause> softwareError (47)
         <Alarmtype> processingErrorAlarm 
        (4) <Polarity> (2) 
        "
	  ::= { pm1005AlmmodInitFailLevel3 12 }



pm1005AlmClient3InitFail OBJECT-TYPE
	  SYNTAX EkiOnOff
	  MAX-ACCESS read-only
	  STATUS current
	  DESCRIPTION
        "
        Client3 Init Fail :This OID indicates 
        that Client 3 registers subset
         has not been correctly initialized 
         <Help>  This alarm indicates if 
        the client port 3 is correctly
         initialized <Condtype> CLIENT3_INIT_FAIL 
        <Probcause> softwareError (47)
         <Alarmtype> processingErrorAlarm 
        (4) <Polarity> (2) 
        "
	  ::= { pm1005AlmmodInitFailLevel3 11 }



pm1005AlmClient2InitFail OBJECT-TYPE
	  SYNTAX EkiOnOff
	  MAX-ACCESS read-only
	  STATUS current
	  DESCRIPTION
        "
        Client2 Init Fail :This OID indicates 
        that Client 2 registers subset
         has not been correctly initialized 
         <Help>  This alarm indicates if 
        the client port 2 is correctly
         initialized <Condtype> CLIENT2_INIT_FAIL 
        <Probcause> softwareError (47)
         <Alarmtype> processingErrorAlarm 
        (4) <Polarity> (2) 
        "
	  ::= { pm1005AlmmodInitFailLevel3 10 }



pm1005AlmClient1InitFail OBJECT-TYPE
	  SYNTAX EkiOnOff
	  MAX-ACCESS read-only
	  STATUS current
	  DESCRIPTION
        "
        Client1 Init Fail :This OID indicates 
        that Client 1 registers subset
         has not been correctly initialized 
         <Help>  This alarm indicates if 
        the client port 1 is correctly
         initialized <Condtype> CLIENT1_INIT_FAIL 
        <Probcause> softwareError (47)
         <Alarmtype> processingErrorAlarm 
        (4) <Polarity> (2) 
        "
	  ::= { pm1005AlmmodInitFailLevel3 9 }



pm1005AlmLine2InitFail OBJECT-TYPE
	  SYNTAX EkiOnOff
	  MAX-ACCESS read-only
	  STATUS current
	  DESCRIPTION
        "
        Line2 Init Fail :This OID indicates 
        that the Line register subset has 
        not been correctly initialized
          <Help>  This alarm indicates
         if the line port 2 is correctly 
        initialized <Condtype> LINE2_INIT_FAIL 
        <Probcause> softwareError (47)
         <Alarmtype> processingErrorAlarm 
        (4) <Polarity> (2) 
        "
	  ::= { pm1005AlmmodInitFailLevel3 8 }



pm1005AlmLine1InitFail OBJECT-TYPE
	  SYNTAX EkiOnOff
	  MAX-ACCESS read-only
	  STATUS current
	  DESCRIPTION
        "
        Line1 Init Fail :This OID indicates 
        that the Line registersvsubset
         has not been correctly initialized 
         <Help>  This alarm indicates if 
        the line port 1 is correctly initialized 
        <Condtype> LINE1_INIT_FAIL <Probcause> 
        softwareError (47) <Alarmtype>
         processingErrorAlarm (4) <Polarity> 
        (2) 
        "
	  ::= { pm1005AlmmodInitFailLevel3 7 }



pm1005AlmXfp2InitFail OBJECT-TYPE
	  SYNTAX EkiOnOff
	  MAX-ACCESS read-only
	  STATUS current
	  DESCRIPTION
        "
        XFP2 Init Fail :This OID indicates 
        that the XFP has not been correctly 
        initialized  <Help>  This alarm 
        indicates if the line transceiver 
        2 is correctly initialized <Condtype> 
        XFP2_INIT_FAIL <Probcause> softwareError 
        (47) <Alarmtype> processingErrorAlarm 
        (4) <Polarity> (2) 
        "
	  ::= { pm1005AlmmodInitFailLevel3 6 }



pm1005AlmXfp1InitFail OBJECT-TYPE
	  SYNTAX EkiOnOff
	  MAX-ACCESS read-only
	  STATUS current
	  DESCRIPTION
        "
        XFP1 Init Fail :This OID indicates 
        that the XFP has not been correctly 
        initialized  <Help>  This alarm 
        indicates if the line transceiver 
        1 is correctly initialized <Condtype> 
        XFP1_INIT_FAIL <Probcause> softwareError 
        (47) <Alarmtype> processingErrorAlarm 
        (4) <Polarity> (2) 
        "
	  ::= { pm1005AlmmodInitFailLevel3 5 }



pm1005AlmInitModuleFail OBJECT-TYPE
	  SYNTAX EkiOnOff
	  MAX-ACCESS read-only
	  STATUS current
	  DESCRIPTION
        "
        Init Module Fail :This OID indicates 
        that the Module has not been correctly 
        initialized  <Help>  This alarm 
        indicates if the SW module is correctly 
        initialized <Condtype> INIT_MODULE_FAIL 
        <Probcause> softwareError (47)
         <Alarmtype> processingErrorAlarm 
        (4) <Polarity> (2) 
        "
	  ::= { pm1005AlmmodInitFailLevel3 3 }



pm1005AlmObmTypeReadFail OBJECT-TYPE
	  SYNTAX EkiOnOff
	  MAX-ACCESS read-only
	  STATUS current
	  DESCRIPTION
        "
        OBM Type Read Fail :This OID indicates 
        that OBM type has not been recognized 
         <Help>  This alarm indicates if 
        the OBM board has been correctly 
        identified <Condtype> OBM_TYPE_READ_FAIL 
        <Probcause> softwareError (47)
         <Alarmtype> processingErrorAlarm 
        (4) <Polarity> (2) 
        "
	  ::= { pm1005AlmmodInitFailLevel3 2 }



pm1005AlmGwIdentFail OBJECT-TYPE
	  SYNTAX EkiOnOff
	  MAX-ACCESS read-only
	  STATUS current
	  DESCRIPTION
        "
        GW Ident Fail :This OID indicates 
        that GW identification has not
         been read  <Help>  This alarm
         indicates if the GW has been correctly 
        identified <Condtype> GW_IDENT_FAIL 
        <Probcause> softwareError (47)
         <Alarmtype> processingErrorAlarm 
        (4) <Polarity> (2) 
        "
	  ::= { pm1005AlmmodInitFailLevel3 1 }



--- *********************************************************
---     TABLE for the pm1005AlmlineXfp1Alarm articles
--- *********************************************************

pm1005AlmlineXfp1AlarmTable OBJECT-TYPE
	SYNTAX  SEQUENCE OF Pm1005AlmlineXfp1AlarmEntry
	MAX-ACCESS not-accessible
	STATUS current
	DESCRIPTION
        "
        List of pm1005AlmlineXfp1Alarm 
        Article
        "
	::= { pm1005AlmLineUrg 208 }


pm1005AlmlineXfp1AlarmEntry OBJECT-TYPE
	SYNTAX Pm1005AlmlineXfp1AlarmEntry
	MAX-ACCESS not-accessible
	STATUS current
	DESCRIPTION
        "
        Row definition for the pm1005AlmlineXfp1Alarm 
        table
        "
	INDEX   { pm1005AlmlineXfp1AlarmIndex }
	::= { pm1005AlmlineXfp1AlarmTable 1 }


Pm1005AlmlineXfp1AlarmEntry ::=
	SEQUENCE {
	pm1005AlmlineXfp1AlarmIndex
		INTEGER,
	pm1005AlmRxPowerHighAlarmPortn
		EkiOnOff,
	pm1005AlmRxPowerLowAlarmPortn
		EkiOnOff,
	pm1005AlmTempHighAlarmPortn
		EkiOnOff,
	pm1005AlmTempLowAlarmPortn
		EkiOnOff,
	pm1005AlmTxBiasHighAlarmPortn
		EkiOnOff,
	pm1005AlmTxBiasLowAlarmPortn
		EkiOnOff,
	pm1005AlmTxPowerHighAlarmPortn
		EkiOnOff,
	pm1005AlmTxPowerLowAlarmPortn
		EkiOnOff
	}


pm1005AlmlineXfp1AlarmIndex OBJECT-TYPE
	SYNTAX  INTEGER(0..128)
	MAX-ACCESS  read-only
	STATUS current
	DESCRIPTION
        "
        Index definition for the pm1005AlmlineXfp1Alarm 
        table
        "
	::= { pm1005AlmlineXfp1AlarmEntry 1 }


pm1005AlmRxPowerHighAlarmPortn OBJECT-TYPE
	SYNTAX  EkiOnOff
	MAX-ACCESS read-only
	STATUS current
	DESCRIPTION
        "
        Line Optical Rx Power High :Alarm 
        indicating that the XFP received 
        optical power is higher than the 
        threshold value written in the
         XFP EEPROM <Condtype> RX_POWER_HIGH_ALARM_1 
        <Probcause> receiveFailure (41) 
        <Alarmtype> equipmentAlarm (5)
         <Polarity> (2) 
        "
	::= { pm1005AlmlineXfp1AlarmEntry 17 }


pm1005AlmRxPowerLowAlarmPortn OBJECT-TYPE
	SYNTAX  EkiOnOff
	MAX-ACCESS read-only
	STATUS current
	DESCRIPTION
        "
        Line Optical Rx Power Low :Alarm 
        indicating that the XFP received 
        optical power is lower than the 
        threshold value written in the
         XFP EEPROM  <Condtype> RX_POWER_LOW_ALARM_1 
        <Probcause> receiveFailure (41) 
        <Alarmtype> equipmentAlarm (5)
         <Polarity> (2) 
        "
	::= { pm1005AlmlineXfp1AlarmEntry 16 }


pm1005AlmTempHighAlarmPortn OBJECT-TYPE
	SYNTAX  EkiOnOff
	MAX-ACCESS read-only
	STATUS current
	DESCRIPTION
        "
        Line Transceiver Temp High :Alarm 
        indicating that the XFP/OTX temperature 
        is higher than the threshold value 
        written in the XFP EEPROM <Condtype> 
        TEMP_HIGH_ALARM_1 <Probcause> temperatureUnacceptable 
        (51) <Alarmtype> equipmentAlarm 
        (5) <Polarity> (2) 
        "
	::= { pm1005AlmlineXfp1AlarmEntry 9 }


pm1005AlmTempLowAlarmPortn OBJECT-TYPE
	SYNTAX  EkiOnOff
	MAX-ACCESS read-only
	STATUS current
	DESCRIPTION
        "
        Line Transceiver Temp Low :Alarm 
        indicating that the XFP/OTX temperature 
        is lower than the threshold value 
        written in the XFP/OTX EEPROM <Condtype> 
        TEMP_LOW_ALARM_1 <Probcause> temperatureUnacceptable 
        (51) <Alarmtype> equipmentAlarm 
        (5) <Polarity> (2) 
        "
	::= { pm1005AlmlineXfp1AlarmEntry 8 }


pm1005AlmTxBiasHighAlarmPortn OBJECT-TYPE
	SYNTAX  EkiOnOff
	MAX-ACCESS read-only
	STATUS current
	DESCRIPTION
        "
        Line Transceiver Bias High :Alarm 
        indicating that the XFP/OTX transmitter 
        laser bias current is higher than 
        the threshold value written in
         the XFP EEPROM <Condtype> TX_BIAS_HIGH_ALARM_1 
        <Probcause> transmitterFailure
         (56) <Alarmtype> equipmentAlarm 
        (5) <Polarity> (2) 
        "
	::= { pm1005AlmlineXfp1AlarmEntry 5 }


pm1005AlmTxBiasLowAlarmPortn OBJECT-TYPE
	SYNTAX  EkiOnOff
	MAX-ACCESS read-only
	STATUS current
	DESCRIPTION
        "
        Line Transceiver Bias Low :Alarm 
        indicating that the XFP/OTX transmitter 
        laser bias current is lower than 
        the threshold value written in
         the XFP/OTX EEPROM <Condtype>
         TX_BIAS_LOW_ALARM_1 <Probcause> 
        transmitterFailure (56) <Alarmtype> 
        equipmentAlarm (5) <Polarity> (2) 
        "
	::= { pm1005AlmlineXfp1AlarmEntry 4 }


pm1005AlmTxPowerHighAlarmPortn OBJECT-TYPE
	SYNTAX  EkiOnOff
	MAX-ACCESS read-only
	STATUS current
	DESCRIPTION
        "
        Line Optical Tx Power High :Alarm 
        indicating that the XFP/OTX transmitter 
        transmitter output power is higher 
        than the threshold value written 
        in the XFP EEPROM <Condtype> TX_POWER_HIGH_ALARM_1 
        <Probcause> transmitterFailure
         (56) <Alarmtype> equipmentAlarm 
        (5) <Polarity> (2) 
        "
	::= { pm1005AlmlineXfp1AlarmEntry 3 }


pm1005AlmTxPowerLowAlarmPortn OBJECT-TYPE
	SYNTAX  EkiOnOff
	MAX-ACCESS read-only
	STATUS current
	DESCRIPTION
        "
        Line Optical Tx Power Low :Alarm 
        indicating that the XFP/OTX transmitter 
        transmitter output power is lower 
        than the threshold value written 
        in the XFP/OTX EEPROM <Condtype> 
        TX_POWER_LOW_ALARM_1 <Probcause> 
        transmitterFailure (56) <Alarmtype> 
        equipmentAlarm (5) <Polarity> (2) 
        "
	::= { pm1005AlmlineXfp1AlarmEntry 2 }


--- *********************************************************
---     TABLE for the pm1005AlmlineXfp1Warnings articles
--- *********************************************************

pm1005AlmlineXfp1WarningsTable OBJECT-TYPE
	SYNTAX  SEQUENCE OF Pm1005AlmlineXfp1WarningsEntry
	MAX-ACCESS not-accessible
	STATUS current
	DESCRIPTION
        "
        List of pm1005AlmlineXfp1Warnings 
        Article
        "
	::= { pm1005AlmLineNurg 209 }


pm1005AlmlineXfp1WarningsEntry OBJECT-TYPE
	SYNTAX Pm1005AlmlineXfp1WarningsEntry
	MAX-ACCESS not-accessible
	STATUS current
	DESCRIPTION
        "
        Row definition for the pm1005AlmlineXfp1Warnings 
        table
        "
	INDEX   { pm1005AlmlineXfp1WarningsIndex }
	::= { pm1005AlmlineXfp1WarningsTable 1 }


Pm1005AlmlineXfp1WarningsEntry ::=
	SEQUENCE {
	pm1005AlmlineXfp1WarningsIndex
		INTEGER,
	pm1005AlmRxPowerHighWarningPortn
		EkiOnOff,
	pm1005AlmRxPowerLowWarningPortn
		EkiOnOff,
	pm1005AlmTempHighWarningPortn
		EkiOnOff,
	pm1005AlmTempLowWarningPortn
		EkiOnOff,
	pm1005AlmTxBiasHighWarningPortn
		EkiOnOff,
	pm1005AlmTxBiasLowWarningPortn
		EkiOnOff,
	pm1005AlmTxPowerHighWarningPortn
		EkiOnOff,
	pm1005AlmTxPowerLowWarningPortn
		EkiOnOff
	}


pm1005AlmlineXfp1WarningsIndex OBJECT-TYPE
	SYNTAX  INTEGER(0..128)
	MAX-ACCESS  read-only
	STATUS current
	DESCRIPTION
        "
        Index definition for the pm1005AlmlineXfp1Warnings 
        table
        "
	::= { pm1005AlmlineXfp1WarningsEntry 1 }


pm1005AlmRxPowerHighWarningPortn OBJECT-TYPE
	SYNTAX  EkiOnOff
	MAX-ACCESS read-only
	STATUS current
	DESCRIPTION
        "
        Line Optical Rx Power High Warning 
        :Warning indicating that the XFP 
        received optical power is higher 
        than the threshold value written 
        in the XFP EEPROM <Condtype> RX_POWER_HIGH_WARNING_1 
        <Probcause> receiveFailure (41) 
        <Alarmtype> equipmentAlarm (5)
         <Polarity> (2) 
        "
	::= { pm1005AlmlineXfp1WarningsEntry 17 }


pm1005AlmRxPowerLowWarningPortn OBJECT-TYPE
	SYNTAX  EkiOnOff
	MAX-ACCESS read-only
	STATUS current
	DESCRIPTION
        "
        Line Optical Rx Power Low Warning 
        :Warning indicating that the XFP 
        received optical power is lower 
        than the threshold value written 
        in the XFP EEPROM  <Condtype> RX_POWER_LOW_WARNING_1 
        <Probcause> receiveFailure (41) 
        <Alarmtype> equipmentAlarm (5)
         <Polarity> (2) 
        "
	::= { pm1005AlmlineXfp1WarningsEntry 16 }


pm1005AlmTempHighWarningPortn OBJECT-TYPE
	SYNTAX  EkiOnOff
	MAX-ACCESS read-only
	STATUS current
	DESCRIPTION
        "
        Line Transceiver Temp High Warning 
        :Warning indicating that the XFP/OTX 
        temperature is higher than the
         threshold value written in the 
        XFP EEPROM <Condtype> TEMP_HIGH_WARNING_1 
        <Probcause> temperatureUnacceptable 
        (51) <Alarmtype> equipmentAlarm 
        (5) <Polarity> (2) 
        "
	::= { pm1005AlmlineXfp1WarningsEntry 9 }


pm1005AlmTempLowWarningPortn OBJECT-TYPE
	SYNTAX  EkiOnOff
	MAX-ACCESS read-only
	STATUS current
	DESCRIPTION
        "
        Line Transceiver Temp Low Warning 
        :Warning indicating that the XFP/OTX 
        temperature is lower than the threshold 
        value written in the XFP/OTX EEPROM 
        <Condtype> TEMP_LOW_WARNING_1 <Probcause> 
        temperatureUnacceptable (51) <Alarmtype> 
        equipmentAlarm (5) <Polarity> (2) 
        "
	::= { pm1005AlmlineXfp1WarningsEntry 8 }


pm1005AlmTxBiasHighWarningPortn OBJECT-TYPE
	SYNTAX  EkiOnOff
	MAX-ACCESS read-only
	STATUS current
	DESCRIPTION
        "
        Line Transceiver Bias High Warning 
        :Warning indicating that the XFP/OTX 
        transmitter laser bias current
         is higher than the threshold value 
        written in the XFP EEPROM <Condtype> 
        TX_BIAS_HIGH_WARNING_1 <Probcause> 
        transmitterFailure (56) <Alarmtype> 
        equipmentAlarm (5) <Polarity> (2) 
        "
	::= { pm1005AlmlineXfp1WarningsEntry 5 }


pm1005AlmTxBiasLowWarningPortn OBJECT-TYPE
	SYNTAX  EkiOnOff
	MAX-ACCESS read-only
	STATUS current
	DESCRIPTION
        "
        Line Transceiver Bias Low Warning 
        :Warning indicating that the XFP/OTX 
        transmitter laser bias current
         is lower than the threshold value 
        written in the XFP/OTX EEPROM <Condtype> 
        TX_BIAS_LOW_WARNING_1 <Probcause> 
        transmitterFailure (56) <Alarmtype> 
        equipmentAlarm (5) <Polarity> (2) 
        "
	::= { pm1005AlmlineXfp1WarningsEntry 4 }


pm1005AlmTxPowerHighWarningPortn OBJECT-TYPE
	SYNTAX  EkiOnOff
	MAX-ACCESS read-only
	STATUS current
	DESCRIPTION
        "
        Line Optical Tx Power High Warning 
        :Warning indicating that the XFP/OTX 
        transmitter transmitter output
         power is higher than the threshold 
        value written in the XFP EEPROM 
        <Condtype> TX_POWER_HIGH_WARNING_1 
        <Probcause> transmitterFailure
         (56) <Alarmtype> equipmentAlarm 
        (5) <Polarity> (2) 
        "
	::= { pm1005AlmlineXfp1WarningsEntry 3 }


pm1005AlmTxPowerLowWarningPortn OBJECT-TYPE
	SYNTAX  EkiOnOff
	MAX-ACCESS read-only
	STATUS current
	DESCRIPTION
        "
        Line Optical Tx Power Low Warning 
        :Warning indicating that the XFP/OTX 
        transmitter transmitter output
         power is lower than the threshold 
        value written in the XFP/OTX EEPROM 
        <Condtype> TX_POWER_LOW_WARNING_1 
        <Probcause> transmitterFailure
         (56) <Alarmtype> equipmentAlarm 
        (5) <Polarity> (2) 
        "
	::= { pm1005AlmlineXfp1WarningsEntry 2 }


--- *********************************************************
---     TABLE for the pm1005AlmlineXfp1Alarms articles
--- *********************************************************

pm1005AlmlineXfp1AlarmsTable OBJECT-TYPE
	SYNTAX  SEQUENCE OF Pm1005AlmlineXfp1AlarmsEntry
	MAX-ACCESS not-accessible
	STATUS current
	DESCRIPTION
        "
        List of pm1005AlmlineXfp1Alarms 
        Article
        "
	::= { pm1005AlmLineCrit 211 }


pm1005AlmlineXfp1AlarmsEntry OBJECT-TYPE
	SYNTAX Pm1005AlmlineXfp1AlarmsEntry
	MAX-ACCESS not-accessible
	STATUS current
	DESCRIPTION
        "
        Row definition for the pm1005AlmlineXfp1Alarms 
        table
        "
	INDEX   { pm1005AlmlineXfp1AlarmsIndex }
	::= { pm1005AlmlineXfp1AlarmsTable 1 }


Pm1005AlmlineXfp1AlarmsEntry ::=
	SEQUENCE {
	pm1005AlmlineXfp1AlarmsIndex
		INTEGER,
	pm1005AlmApdSupplyFaultPortn
		EkiOnOff,
	pm1005AlmTecFaultPortn
		EkiOnOff,
	pm1005AlmWavelengthUnlockedPortn
		EkiOnOff,
	pm1005AlmTxNrPortn
		EkiOnOff,
	pm1005AlmTxFaultPortn
		EkiOnOff,
	pm1005AlmTxCdrNotLockedPortn
		EkiOnOff,
	pm1005AlmRxNrPortn
		EkiOnOff,
	pm1005AlmRxCdrNotLockedPortn
		EkiOnOff,
	pm1005AlmModNrPortn
		EkiOnOff
	}


pm1005AlmlineXfp1AlarmsIndex OBJECT-TYPE
	SYNTAX  INTEGER(0..128)
	MAX-ACCESS  read-only
	STATUS current
	DESCRIPTION
        "
        Index definition for the pm1005AlmlineXfp1Alarms 
        table
        "
	::= { pm1005AlmlineXfp1AlarmsEntry 1 }


pm1005AlmApdSupplyFaultPortn OBJECT-TYPE
	SYNTAX  EkiOnOff
	MAX-ACCESS read-only
	STATUS current
	DESCRIPTION
        "
        Line Rx Photodiode Power Failed 
        :This OID indicates a failure on 
        the APD power supply  <Help>  This 
        alarm indicates if the APD power 
        supply is in fail condition <Condtype> 
        APD_SUPPLY_FAULT_1 <Probcause>
         receiverFailure (42) <Alarmtype> 
        equipmentAlarm (5) <Polarity> (2) 
        "
	::= { pm1005AlmlineXfp1AlarmsEntry 17 }


pm1005AlmTecFaultPortn OBJECT-TYPE
	SYNTAX  EkiOnOff
	MAX-ACCESS read-only
	STATUS current
	DESCRIPTION
        "
        Line Optical Tx Temp Regul Failed 
        :This OID indicates a failure on 
        the TEC module  <Help>  This alarm 
        indicates if the TEC of the line 
        transceiver is in fail condition 
        <Condtype> TEC_FAULT_1 <Probcause> 
        transmitterFailure (56) <Alarmtype> 
        equipmentAlarm (5) <Polarity> (2) 
        "
	::= { pm1005AlmlineXfp1AlarmsEntry 16 }


pm1005AlmWavelengthUnlockedPortn OBJECT-TYPE
	SYNTAX  EkiOnOff
	MAX-ACCESS read-only
	STATUS current
	DESCRIPTION
        "
        Line Optical Tx Wavelength Unlocked 
        :This OID indicates that the wavelength 
        error is exceeding the manufacturer 
        tolerance  <Help>  This alarm indicates 
        if the wavelenght of the line transceiver 
        is locked <Condtype> WAVELENGTH_UNLOCKED_1 
        <Probcause> transmitterFailure
         (56) <Alarmtype> equipmentAlarm 
        (5) <Polarity> (2) 
        "
	::= { pm1005AlmlineXfp1AlarmsEntry 15 }


pm1005AlmTxNrPortn OBJECT-TYPE
	SYNTAX  EkiOnOff
	MAX-ACCESS read-only
	STATUS current
	DESCRIPTION
        "
        Line Optical Tx Not Ready :This 
        OID indicates a condition has arisen 
        leading to invalid data on the
         transmitting side  <Help>  This 
        alarm indicates if the Tx part
         of the line transceiver is ready 
        <Condtype> TX_NR_1 <Probcause>
         transmitterFailure (56) <Alarmtype> 
        equipmentAlarm (5) <Polarity> (2) 
        "
	::= { pm1005AlmlineXfp1AlarmsEntry 9 }


pm1005AlmTxFaultPortn OBJECT-TYPE
	SYNTAX  EkiOnOff
	MAX-ACCESS read-only
	STATUS current
	DESCRIPTION
        "
        Line Optical Tx Failure :This
         OID indicates a fault condition 
        on the laser detected by the safety 
        syste  <Help>  This alarm indicates 
        if the laser of the line transceiver 
        is in fail condition <Condtype> 
        TX_FAULT_1 <Probcause> transmitterFailure 
        (56) <Alarmtype> equipmentAlarm 
        (5) <Polarity> (2) 
        "
	::= { pm1005AlmlineXfp1AlarmsEntry 8 }


pm1005AlmTxCdrNotLockedPortn OBJECT-TYPE
	SYNTAX  EkiOnOff
	MAX-ACCESS read-only
	STATUS current
	DESCRIPTION
        "
        Line Optical Tx CDR Unlocked :This 
        OID indicates a loss of lock on 
        the transmitting side CDR has been 
        detected.  <Help>  This alarm indicates 
        if the Tx CDR is locked in the
         line transceiver <Condtype> TX_CDR_NOT_LOCKED1_1 
        <Probcause> transmitterFailure
         (56) <Alarmtype> equipmentAlarm 
        (5) <Polarity> (2) 
        "
	::= { pm1005AlmlineXfp1AlarmsEntry 7 }


pm1005AlmRxNrPortn OBJECT-TYPE
	SYNTAX  EkiOnOff
	MAX-ACCESS read-only
	STATUS current
	DESCRIPTION
        "
        Line Optical Rx Not Ready :This 
        OID indicates that a condition
         has arisen leading to invalid
         data on the receiving side.  <Help> 
         This alarm indicates if the Rx 
        part of the line transceiver is 
        ready <Condtype> RX_NR_1 <Probcause> 
        receiveFailure (41) <Alarmtype> 
        equipmentAlarm (5) <Polarity> (2) 
        "
	::= { pm1005AlmlineXfp1AlarmsEntry 6 }


pm1005AlmRxCdrNotLockedPortn OBJECT-TYPE
	SYNTAX  EkiOnOff
	MAX-ACCESS read-only
	STATUS current
	DESCRIPTION
        "
        Line Optical Rx CDR Unlocked :This 
        OID indicates that a loss of lock 
        on the receiving side CDR has been 
        detected  <Help>  This alarm indicates 
        if the Rx CDR is locked in the
         line transceiver <Condtype> RX_CDR_NOT_LOCKED1_1 
        <Probcause> receiveFailure (41) 
        <Alarmtype> equipmentAlarm (5)
         <Polarity> (2) 
        "
	::= { pm1005AlmlineXfp1AlarmsEntry 4 }


pm1005AlmModNrPortn OBJECT-TYPE
	SYNTAX  EkiOnOff
	MAX-ACCESS read-only
	STATUS current
	DESCRIPTION
        "
        Line Optical Module Not Ready
         :This OID indicates that the module 
        is unable to determine correct
         data.  <Help>  This alarm indicates 
        if the line transceiver is ready 
        <Condtype> MOD_NR_1 <Probcause> 
        receiveFailure (41) <Alarmtype> 
        equipmentAlarm (5) <Polarity> (2) 
        "
	::= { pm1005AlmlineXfp1AlarmsEntry 3 }


--- *********************************************************
---     TABLE for the pm1005AlmlineXfp1SupplyAlarm articles
--- *********************************************************

pm1005AlmlineXfp1SupplyAlarmTable OBJECT-TYPE
	SYNTAX  SEQUENCE OF Pm1005AlmlineXfp1SupplyAlarmEntry
	MAX-ACCESS not-accessible
	STATUS current
	DESCRIPTION
        "
        List of pm1005AlmlineXfp1SupplyAlarm 
        Article
        "
	::= { pm1005AlmLineUrg 212 }


pm1005AlmlineXfp1SupplyAlarmEntry OBJECT-TYPE
	SYNTAX Pm1005AlmlineXfp1SupplyAlarmEntry
	MAX-ACCESS not-accessible
	STATUS current
	DESCRIPTION
        "
        Row definition for the pm1005AlmlineXfp1SupplyAlarm 
        table
        "
	INDEX   { pm1005AlmlineXfp1SupplyAlarmIndex }
	::= { pm1005AlmlineXfp1SupplyAlarmTable 1 }


Pm1005AlmlineXfp1SupplyAlarmEntry ::=
	SEQUENCE {
	pm1005AlmlineXfp1SupplyAlarmIndex
		INTEGER,
	pm1005AlmVcc5HighWarningPortn
		EkiOnOff,
	pm1005AlmVcc5LowWarningPortn
		EkiOnOff,
	pm1005AlmVcc3HighWarningPortn
		EkiOnOff,
	pm1005AlmVcc3LowWarningPortn
		EkiOnOff,
	pm1005AlmVcc2HighWarningPortn
		EkiOnOff,
	pm1005AlmVcc2LowWarningPortn
		EkiOnOff,
	pm1005AlmVee5HighWarningPortn
		EkiOnOff,
	pm1005AlmVee5LowWarningPortn
		EkiOnOff,
	pm1005AlmVcc5HighAlarmPortn
		EkiOnOff,
	pm1005AlmVcc5LowAlarmPortn
		EkiOnOff,
	pm1005AlmVcc3HighAlarmPortn
		EkiOnOff,
	pm1005AlmVcc3LowAlarmPortn
		EkiOnOff,
	pm1005AlmVcc2HighAlarmPortn
		EkiOnOff,
	pm1005AlmVcc2LowAlarmPortn
		EkiOnOff,
	pm1005AlmVee5HighAlarmPortn
		EkiOnOff,
	pm1005AlmVee5LowAlarmPortn
		EkiOnOff
	}


pm1005AlmlineXfp1SupplyAlarmIndex OBJECT-TYPE
	SYNTAX  INTEGER(0..128)
	MAX-ACCESS  read-only
	STATUS current
	DESCRIPTION
        "
        Index definition for the pm1005AlmlineXfp1SupplyAlarm 
        table
        "
	::= { pm1005AlmlineXfp1SupplyAlarmEntry 1 }


pm1005AlmVcc5HighWarningPortn OBJECT-TYPE
	SYNTAX  EkiOnOff
	MAX-ACCESS read-only
	STATUS current
	DESCRIPTION
        "
        VCC5 Power Supply High Warning 
        :Warning indicating the XFP/OTX 
        VCC5 power supply is higher than 
        the threshold written in the EEPROM 
        <Condtype> VCC5_HIGH_WARNING_1
         <Probcause> powerProblem (36)
         <Alarmtype> equipmentAlarm (5) 
        <Polarity> (2) 
        "
	::= { pm1005AlmlineXfp1SupplyAlarmEntry 17 }


pm1005AlmVcc5LowWarningPortn OBJECT-TYPE
	SYNTAX  EkiOnOff
	MAX-ACCESS read-only
	STATUS current
	DESCRIPTION
        "
        VCC5 Power Supply Low Warning
         :Warning indicating the XFP/OTX 
        VCC5 power supply is lower than 
        the threshold written in the EEPROM 
        <Condtype> VCC5_LOW_WARNING_1 <Probcause> 
        powerProblem (36) <Alarmtype> equipmentAlarm 
        (5) <Polarity> (2) 
        "
	::= { pm1005AlmlineXfp1SupplyAlarmEntry 16 }


pm1005AlmVcc3HighWarningPortn OBJECT-TYPE
	SYNTAX  EkiOnOff
	MAX-ACCESS read-only
	STATUS current
	DESCRIPTION
        "
        VCC3 Power Supply High Warning 
        :Warning indicating the XFP/OTX 
        VCC3 power supply is higher than 
        the threshold written in the EEPROM 
        <Condtype> VCC3_HIGH_WARNING_1
         <Probcause> powerProblem (36)
         <Alarmtype> equipmentAlarm (5) 
        <Polarity> (2) 
        "
	::= { pm1005AlmlineXfp1SupplyAlarmEntry 15 }


pm1005AlmVcc3LowWarningPortn OBJECT-TYPE
	SYNTAX  EkiOnOff
	MAX-ACCESS read-only
	STATUS current
	DESCRIPTION
        "
        VCC3 Power Supply Low Warning
         :Warning indicating the XFP/OTX 
        VCC3 power supply is lower than 
        the threshold written in the EEPROM 
        <Condtype> VCC3_LOW_WARNING_1 <Probcause> 
        powerProblem (36) <Alarmtype> equipmentAlarm 
        (5) <Polarity> (2) 
        "
	::= { pm1005AlmlineXfp1SupplyAlarmEntry 14 }


pm1005AlmVcc2HighWarningPortn OBJECT-TYPE
	SYNTAX  EkiOnOff
	MAX-ACCESS read-only
	STATUS current
	DESCRIPTION
        "
        VCC2 Power Supply High Warning 
        :Warning indicating the XFP/OTX 
        VCC2 power supply is higher than 
        the threshold written in the EEPROM 
        <Condtype> VCC2_HIGH_WARNING_1
         <Probcause> powerProblem (36)
         <Alarmtype> equipmentAlarm (5) 
        <Polarity> (2) 
        "
	::= { pm1005AlmlineXfp1SupplyAlarmEntry 13 }


pm1005AlmVcc2LowWarningPortn OBJECT-TYPE
	SYNTAX  EkiOnOff
	MAX-ACCESS read-only
	STATUS current
	DESCRIPTION
        "
        VCC2 Power Supply Low Warning
         :Warning indicating the XFP/OTX 
        VCC2 power supply is lower than 
        the threshold written in the EEPROM 
        <Condtype> VCC2_LOW_WARNING_1 <Probcause> 
        powerProblem (36) <Alarmtype> equipmentAlarm 
        (5) <Polarity> (2) 
        "
	::= { pm1005AlmlineXfp1SupplyAlarmEntry 12 }


pm1005AlmVee5HighWarningPortn OBJECT-TYPE
	SYNTAX  EkiOnOff
	MAX-ACCESS read-only
	STATUS current
	DESCRIPTION
        "
        VEE5 Power Supply High Warning 
        :Warning indicating the XFP/OTX 
        VEE5 power supply is higher than 
        the threshold written in the EEPROM 
        <Condtype> VEE5_HIGH_WARNING_1
         <Probcause> powerProblem (36)
         <Alarmtype> equipmentAlarm (5) 
        <Polarity> (2) 
        "
	::= { pm1005AlmlineXfp1SupplyAlarmEntry 11 }


pm1005AlmVee5LowWarningPortn OBJECT-TYPE
	SYNTAX  EkiOnOff
	MAX-ACCESS read-only
	STATUS current
	DESCRIPTION
        "
        VEE5 Power Supply Low Warning
         :Warning indicating the XFP/OTX 
        VEE5 power supply is lower than 
        the threshold written in the EEPROM 
        <Condtype> VEE5_LOW_WARNING_1 <Probcause> 
        powerProblem (36) <Alarmtype> equipmentAlarm 
        (5) <Polarity> (2) 
        "
	::= { pm1005AlmlineXfp1SupplyAlarmEntry 10 }


pm1005AlmVcc5HighAlarmPortn OBJECT-TYPE
	SYNTAX  EkiOnOff
	MAX-ACCESS read-only
	STATUS current
	DESCRIPTION
        "
        VCC5 Power Supply High :Alarm
         indicating the XFP/OTX VCC5 power 
        supply is higher than the threshold 
        written in the EEPROM <Condtype> 
        VCC5_HIGH_ALARM_1 <Probcause> powerProblem 
        (36) <Alarmtype> equipmentAlarm 
        (5) <Polarity> (2) 
        "
	::= { pm1005AlmlineXfp1SupplyAlarmEntry 9 }


pm1005AlmVcc5LowAlarmPortn OBJECT-TYPE
	SYNTAX  EkiOnOff
	MAX-ACCESS read-only
	STATUS current
	DESCRIPTION
        "
        VCC5 Power Supply Low :Alarm indicating 
        the XFP/OTX VCC5 power supply is 
        lower than the threshold written 
        in the EEPROM <Condtype> VCC5_LOW_ALARM_1 
        <Probcause> powerProblem (36) <Alarmtype> 
        equipmentAlarm (5) <Polarity> (2) 
        "
	::= { pm1005AlmlineXfp1SupplyAlarmEntry 8 }


pm1005AlmVcc3HighAlarmPortn OBJECT-TYPE
	SYNTAX  EkiOnOff
	MAX-ACCESS read-only
	STATUS current
	DESCRIPTION
        "
        VCC3 Power Supply High :Alarm
         indicating the XFP/OTX VCC3 power 
        supply is higher than the threshold 
        written in the EEPROM <Condtype> 
        VCC3_HIGH_ALARM_1 <Probcause> powerProblem 
        (36) <Alarmtype> equipmentAlarm 
        (5) <Polarity> (2) 
        "
	::= { pm1005AlmlineXfp1SupplyAlarmEntry 7 }


pm1005AlmVcc3LowAlarmPortn OBJECT-TYPE
	SYNTAX  EkiOnOff
	MAX-ACCESS read-only
	STATUS current
	DESCRIPTION
        "
        VCC3 Power Supply Low :Alarm indicating 
        the XFP/OTX VCC3 power supply is 
        lower than the threshold written 
        in the EEPROM <Condtype> VCC3_LOW_ALARM_1 
        <Probcause> powerProblem (36) <Alarmtype> 
        equipmentAlarm (5) <Polarity> (2) 
        "
	::= { pm1005AlmlineXfp1SupplyAlarmEntry 6 }


pm1005AlmVcc2HighAlarmPortn OBJECT-TYPE
	SYNTAX  EkiOnOff
	MAX-ACCESS read-only
	STATUS current
	DESCRIPTION
        "
        VCC2 Power Supply High :Alarm
         indicating the XFP/OTX VCC2 power 
        supply is higher than the threshold 
        written in the EEPROM <Condtype> 
        VCC2_HIGH_ALARM_1 <Probcause> powerProblem 
        (36) <Alarmtype> equipmentAlarm 
        (5) <Polarity> (2) 
        "
	::= { pm1005AlmlineXfp1SupplyAlarmEntry 5 }


pm1005AlmVcc2LowAlarmPortn OBJECT-TYPE
	SYNTAX  EkiOnOff
	MAX-ACCESS read-only
	STATUS current
	DESCRIPTION
        "
        VCC2 Power Supply Low :Alarm indicating 
        the XFP/OTX VCC2 power supply is 
        lower than the threshold written 
        in the EEPROM <Condtype> VCC2_LOW_ALARM_1 
        <Probcause> powerProblem (36) <Alarmtype> 
        equipmentAlarm (5) <Polarity> (2) 
        "
	::= { pm1005AlmlineXfp1SupplyAlarmEntry 4 }


pm1005AlmVee5HighAlarmPortn OBJECT-TYPE
	SYNTAX  EkiOnOff
	MAX-ACCESS read-only
	STATUS current
	DESCRIPTION
        "
        VEE5 Power Supply High :Alarm
         indicating the XFP/OTX VEE5 power 
        supply is higher than the threshold 
        written in the EEPROM <Condtype> 
        VEE5_HIGH_ALARM_1 <Probcause> powerProblem 
        (36) <Alarmtype> equipmentAlarm 
        (5) <Polarity> (2) 
        "
	::= { pm1005AlmlineXfp1SupplyAlarmEntry 3 }


pm1005AlmVee5LowAlarmPortn OBJECT-TYPE
	SYNTAX  EkiOnOff
	MAX-ACCESS read-only
	STATUS current
	DESCRIPTION
        "
        VEE5 Power Supply Low :Alarm indicating 
        the XFP/OTX VEE5 power supply is 
        lower than the threshold written 
        in the EEPROM <Condtype> VEE5_LOW_ALARM_1 
        <Probcause> powerProblem (36) <Alarmtype> 
        equipmentAlarm (5) <Polarity> (2) 
        "
	::= { pm1005AlmlineXfp1SupplyAlarmEntry 2 }


--- *********************************************************
---     TABLE for the pm1005AlmlineOtx1TlhAlarms articles
--- *********************************************************

pm1005AlmlineOtx1TlhAlarmsTable OBJECT-TYPE
	SYNTAX  SEQUENCE OF Pm1005AlmlineOtx1TlhAlarmsEntry
	MAX-ACCESS not-accessible
	STATUS current
	DESCRIPTION
        "
        List of pm1005AlmlineOtx1TlhAlarms 
        Article
        "
	::= { pm1005AlmLineUrg 224 }


pm1005AlmlineOtx1TlhAlarmsEntry OBJECT-TYPE
	SYNTAX Pm1005AlmlineOtx1TlhAlarmsEntry
	MAX-ACCESS not-accessible
	STATUS current
	DESCRIPTION
        "
        Row definition for the pm1005AlmlineOtx1TlhAlarms 
        table
        "
	INDEX   { pm1005AlmlineOtx1TlhAlarmsIndex }
	::= { pm1005AlmlineOtx1TlhAlarmsTable 1 }


Pm1005AlmlineOtx1TlhAlarmsEntry ::=
	SEQUENCE {
	pm1005AlmlineOtx1TlhAlarmsIndex
		INTEGER,
	pm1005AlmLineLaserTempHighAlaPortn
		EkiOnOff,
	pm1005AlmLineFreqDevHighAlaPortn
		EkiOnOff,
	pm1005AlmLineAgingHighAlaPortn
		EkiOnOff,
	pm1005AlmLineModulatorAgingHighAlaPortn
		EkiOnOff
	}


pm1005AlmlineOtx1TlhAlarmsIndex OBJECT-TYPE
	SYNTAX  INTEGER(0..128)
	MAX-ACCESS  read-only
	STATUS current
	DESCRIPTION
        "
        Index definition for the pm1005AlmlineOtx1TlhAlarms 
        table
        "
	::= { pm1005AlmlineOtx1TlhAlarmsEntry 1 }


pm1005AlmLineLaserTempHighAlaPortn OBJECT-TYPE
	SYNTAX  EkiOnOff
	MAX-ACCESS read-only
	STATUS current
	DESCRIPTION
        "
        Line Laser Temp. High Alarm :Alarm 
        indicating the Line OTX TLH laser 
        temperature is higher than the
         threshold written in the EEPROM 
        <Condtype> LINE_LASER_TEMP_HIGH_ALA_1 
        <Probcause> temperatureUnacceptable 
        (51) <Alarmtype> equipmentAlarm 
        (5) <Polarity> (2) 
        "
	::= { pm1005AlmlineOtx1TlhAlarmsEntry 15 }


pm1005AlmLineFreqDevHighAlaPortn OBJECT-TYPE
	SYNTAX  EkiOnOff
	MAX-ACCESS read-only
	STATUS current
	DESCRIPTION
        "
        Line Freq. Deviation High Alarm 
        :Alarm indicating the Line OTX
         TLH frequency deviation is higher 
        than the threshold written in the 
        EEPROM <Condtype> LINE_FREQ_DEV_HIGH_ALA_1 
        <Probcause> transmitterFailure
         (56) <Alarmtype> equipmentAlarm 
        (5) <Polarity> (2) 
        "
	::= { pm1005AlmlineOtx1TlhAlarmsEntry 13 }


pm1005AlmLineAgingHighAlaPortn OBJECT-TYPE
	SYNTAX  EkiOnOff
	MAX-ACCESS read-only
	STATUS current
	DESCRIPTION
        "
        Line OTX TLH Aging High Alarm
         :Alarm indicating the Line OTX 
        TLH aging is higher than the threshold 
        written in the EEPROM <Condtype> 
        LINE_AGING_HIGH_ALA_1 <Probcause> 
        transmitterFailure (56) <Alarmtype> 
        equipmentAlarm (5) <Polarity> (2) 
        "
	::= { pm1005AlmlineOtx1TlhAlarmsEntry 7 }


pm1005AlmLineModulatorAgingHighAlaPortn OBJECT-TYPE
	SYNTAX  EkiOnOff
	MAX-ACCESS read-only
	STATUS current
	DESCRIPTION
        "
        Line Modulator Aging High Alarm 
        :Alarm indicating the Line OTX
         TLH modulator aging is higher
         than the threshold written in
         the EEPROM <Condtype> LINE_MODULATOR_AGING_HIGH_ALA_1 
        <Probcause> transmitterFailure
         (56) <Alarmtype> equipmentAlarm 
        (5) <Polarity> (2) 
        "
	::= { pm1005AlmlineOtx1TlhAlarmsEntry 6 }


--- *********************************************************
---     TABLE for the pm1005AlmlineOtx1TlhWarnings articles
--- *********************************************************

pm1005AlmlineOtx1TlhWarningsTable OBJECT-TYPE
	SYNTAX  SEQUENCE OF Pm1005AlmlineOtx1TlhWarningsEntry
	MAX-ACCESS not-accessible
	STATUS current
	DESCRIPTION
        "
        List of pm1005AlmlineOtx1TlhWarnings 
        Article
        "
	::= { pm1005AlmLineNurg 225 }


pm1005AlmlineOtx1TlhWarningsEntry OBJECT-TYPE
	SYNTAX Pm1005AlmlineOtx1TlhWarningsEntry
	MAX-ACCESS not-accessible
	STATUS current
	DESCRIPTION
        "
        Row definition for the pm1005AlmlineOtx1TlhWarnings 
        table
        "
	INDEX   { pm1005AlmlineOtx1TlhWarningsIndex }
	::= { pm1005AlmlineOtx1TlhWarningsTable 1 }


Pm1005AlmlineOtx1TlhWarningsEntry ::=
	SEQUENCE {
	pm1005AlmlineOtx1TlhWarningsIndex
		INTEGER,
	pm1005AlmLineLaserTempHighWarningPortn
		EkiOnOff,
	pm1005AlmLineFreqDevHighWarningPortn
		EkiOnOff,
	pm1005AlmLineAgingHighWarningPortn
		EkiOnOff,
	pm1005AlmLineModulatorAgingHighWarningPortn
		EkiOnOff
	}


pm1005AlmlineOtx1TlhWarningsIndex OBJECT-TYPE
	SYNTAX  INTEGER(0..128)
	MAX-ACCESS  read-only
	STATUS current
	DESCRIPTION
        "
        Index definition for the pm1005AlmlineOtx1TlhWarnings 
        table
        "
	::= { pm1005AlmlineOtx1TlhWarningsEntry 1 }


pm1005AlmLineLaserTempHighWarningPortn OBJECT-TYPE
	SYNTAX  EkiOnOff
	MAX-ACCESS read-only
	STATUS current
	DESCRIPTION
        "
        Line Laser Temp. High Warning
         :Warning indicating the Line OTX 
        TLH laser temperature is higher 
        than the threshold written in the 
        EEPROM <Condtype> LINE_LASER_TEMP_HIGH_WARNING_1 
        <Probcause> temperatureUnacceptable 
        (51) <Alarmtype> equipmentAlarm 
        (5) <Polarity> (2) 
        "
	::= { pm1005AlmlineOtx1TlhWarningsEntry 15 }


pm1005AlmLineFreqDevHighWarningPortn OBJECT-TYPE
	SYNTAX  EkiOnOff
	MAX-ACCESS read-only
	STATUS current
	DESCRIPTION
        "
        Line Freq. Deviation High Warning 
        :Warning indicating the Line OTX 
        TLH frequency deviation is higher 
        than the threshold written in the 
        EEPROM <Condtype> LINE_FREQ_DEV_HIGH_WARNING_1 
        <Probcause> transmitterFailure
         (56) <Alarmtype> equipmentAlarm 
        (5) <Polarity> (2) 
        "
	::= { pm1005AlmlineOtx1TlhWarningsEntry 13 }


pm1005AlmLineAgingHighWarningPortn OBJECT-TYPE
	SYNTAX  EkiOnOff
	MAX-ACCESS read-only
	STATUS current
	DESCRIPTION
        "
        Line OTX TLH Aging High Warning 
        :Warning indicating the Line OTX 
        TLH aging is higher than the threshold 
        written in the EEPROM <Condtype> 
        LINE_AGING_HIGH_WARNING_1 <Probcause> 
        transmitterFailure (56) <Alarmtype> 
        equipmentAlarm (5) <Polarity> (2) 
        "
	::= { pm1005AlmlineOtx1TlhWarningsEntry 7 }


pm1005AlmLineModulatorAgingHighWarningPortn OBJECT-TYPE
	SYNTAX  EkiOnOff
	MAX-ACCESS read-only
	STATUS current
	DESCRIPTION
        "
        Line Modulator Aging High Warning 
        :Warning indicating the Line OTX 
        TLH modulator aging is higher than 
        the threshold written in the EEPROM 
        <Condtype> LINE_MODULATOR_AGING_HIGH_WARNING_1 
        <Probcause> transmitterFailure
         (56) <Alarmtype> equipmentAlarm 
        (5) <Polarity> (2) 
        "
	::= { pm1005AlmlineOtx1TlhWarningsEntry 6 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm1005CtrlconfMgnt1 OBJECT IDENTIFIER ::= { pm1005CtrlOther 1 }




pm1005CtrlConf2Clear1 OBJECT-TYPE
	  SYNTAX EkiOnOff
	  MAX-ACCESS read-write
	  STATUS current
	  DESCRIPTION
        "
        Clear Configuration Tables :This 
        OID clears the configuration tables 
        from configuration2 in the flash. 
         <Help>  This control restores
         the default configuration of the 
        module
        "
	  ::= { pm1005CtrlconfMgnt1 14 }



pm1005CtrlConf2Flash1 OBJECT-TYPE
	  SYNTAX EkiOnOff
	  MAX-ACCESS read-write
	  STATUS current
	  DESCRIPTION
        "
        Write Configuration Tables :This 
        OID saves the current configuration 
        of the PM as configuration2 in
         the flash.  <Help>  This control 
        saves the customer configuration 
        on the module
        "
	  ::= { pm1005CtrlconfMgnt1 10 }



pm1005CtrlConf2Load1 OBJECT-TYPE
	  SYNTAX EkiOnOff
	  MAX-ACCESS read-write
	  STATUS current
	  DESCRIPTION
        "
        Load Configuration Tables Set
         Nb 2 :When set this OID enables 
        loading from flash configuration2 
        into the PM.
        "
	  ::= { pm1005CtrlconfMgnt1 2 }



pm1005CtrlConf1Load1 OBJECT-TYPE
	  SYNTAX EkiOnOff
	  MAX-ACCESS read-write
	  STATUS current
	  DESCRIPTION
        "
        Load Configuration Tables Set
         Nb 1 :When set this OID enables 
        loading from flash configuration1 
        into the PM.
        "
	  ::= { pm1005CtrlconfMgnt1 1 }



--- *****************************************************
---     LEAF for the synth4 article
--- *****************************************************
pm1005Ctrlsynth4 OBJECT IDENTIFIER ::= { pm1005CtrlOther 4 }




pm1005CtrlCorrelatOff OBJECT-TYPE
	  SYNTAX EkiOnOff
	  MAX-ACCESS read-write
	  STATUS current
	  DESCRIPTION
        "
        Disable Alarm Correlation :This 
        OID disables the alarm correlation 
        in the PM.
        "
	  ::= { pm1005Ctrlsynth4 2 }



pm1005CtrlCorrelatOn OBJECT-TYPE
	  SYNTAX EkiOnOff
	  MAX-ACCESS read-write
	  STATUS current
	  DESCRIPTION
        "
        Enable Alarm Correlation :This 
        OID enables the alarm correlation 
        in the PM.
        "
	  ::= { pm1005Ctrlsynth4 1 }



--- *****************************************************
---     LEAF for the swMgnt article
--- *****************************************************
pm1005CtrlswMgnt OBJECT IDENTIFIER ::= { pm1005CtrlOther 5 }




pm1005CtrlLoadSwBank2 OBJECT-TYPE
	  SYNTAX EkiOnOff
	  MAX-ACCESS read-write
	  STATUS current
	  DESCRIPTION
        "
        Set Software Nb 2 As Active :This 
        OID, when set, loads the SW from 
        bank2 into the PM. It must be followed 
        by a reset.  <Help>  This controls 
        selects the second SW bank as the 
        active bank for the next module 
        reset
        "
	  ::= { pm1005CtrlswMgnt 6 }



pm1005CtrlLoadSwBank1 OBJECT-TYPE
	  SYNTAX EkiOnOff
	  MAX-ACCESS read-write
	  STATUS current
	  DESCRIPTION
        "
        Set Software Nb 1 As Active :This 
        OID, when set, loads the SW from 
        bank1 into the PM. It must be followed 
        by a reset.  <Help>  This controls 
        selects the first SW bank as the 
        active bank for the next module 
        reset
        "
	  ::= { pm1005CtrlswMgnt 5 }



pm1005CtrlWarmReset OBJECT-TYPE
	  SYNTAX EkiOnOff
	  MAX-ACCESS read-write
	  STATUS current
	  DESCRIPTION
        "
        PM Warm Reset :This OID, when
         set, causes a warm reset of the 
        PM. This reset is not traffic affecting, 
        and the configuration of PM remains 
        unchanged.  <Help>  This control 
        initiates a warm reset of the module. 
        "
	  ::= { pm1005CtrlswMgnt 3 }



pm1005CtrlColdReset OBJECT-TYPE
	  SYNTAX EkiOnOff
	  MAX-ACCESS read-write
	  STATUS current
	  DESCRIPTION
        "
        PM Cold Reset :This OID, when
         set, causes a cold reset of the 
        PM. This reset is traffic affecting, 
        and the configuration of PM is
         reloaded on start-up.  <Help>
          This control initiates a cold 
        reset of the module. 
        "
	  ::= { pm1005CtrlswMgnt 2 }



--- *****************************************************
---     LEAF for the gwMgnt article
--- *****************************************************
pm1005CtrlgwMgnt OBJECT IDENTIFIER ::= { pm1005CtrlOther 6 }




pm1005CtrlLoadGwBank4 OBJECT-TYPE
	  SYNTAX EkiOnOff
	  MAX-ACCESS read-write
	  STATUS current
	  DESCRIPTION
        "
        Set Gateware Nb 4 As Active :This 
        OID, when set, loads the GW from 
        bank4 (Flash) into the PM. It is 
        followed by an automatic gateware 
        cold reset.
        "
	  ::= { pm1005CtrlgwMgnt 8 }



pm1005CtrlLoadGwBank3 OBJECT-TYPE
	  SYNTAX EkiOnOff
	  MAX-ACCESS read-write
	  STATUS current
	  DESCRIPTION
        "
        Set Gateware Nb 3 As Active :This 
        OID, when set, loads the GW from 
        bank3 (Flash) into the PM. It is 
        followed by an automatic gateware 
        cold reset.  <Help>  This controls 
        initiates a cold reset of the module 
        and select the third GW bank as 
        the active bank
        "
	  ::= { pm1005CtrlgwMgnt 7 }



pm1005CtrlLoadGwBank2 OBJECT-TYPE
	  SYNTAX EkiOnOff
	  MAX-ACCESS read-write
	  STATUS current
	  DESCRIPTION
        "
        Set Gateware Nb 2 As Active :This 
        OID, when set, loads the GW from 
        bank2 (Flash) into the PM. It is 
        followed by an automatic gateware 
        cold reset.
        "
	  ::= { pm1005CtrlgwMgnt 6 }



pm1005CtrlLoadGwBank1 OBJECT-TYPE
	  SYNTAX EkiOnOff
	  MAX-ACCESS read-write
	  STATUS current
	  DESCRIPTION
        "
        Set Gateware Nb 1 As Active :This 
        OID, when set, loads the GW from 
        bank1 (Flash) into the PM. It is 
        followed by an automatic gateware 
        cold reset.  <Help>  This controls 
        initiates a cold reset of the module 
        and select the first GW bank as 
        the active bank
        "
	  ::= { pm1005CtrlgwMgnt 5 }



pm1005CtrlCurrentGwReset OBJECT-TYPE
	  SYNTAX EkiOnOff
	  MAX-ACCESS read-write
	  STATUS current
	  DESCRIPTION
        "
        Active Gateware Reset :This OID, 
        when set, resets the active gateware. 
        It is traffic affecting.
        "
	  ::= { pm1005CtrlgwMgnt 1 }



--- *********************************************************
---     TABLE for the pm1005CtrlaccessLoop articles
--- *********************************************************

pm1005CtrlaccessLoopTable OBJECT-TYPE
	SYNTAX  SEQUENCE OF Pm1005CtrlaccessLoopEntry
	MAX-ACCESS not-accessible
	STATUS current
	DESCRIPTION
        "
        List of pm1005CtrlaccessLoop Article
        "
	::= { pm1005CtrlClient 16 }


pm1005CtrlaccessLoopEntry OBJECT-TYPE
	SYNTAX Pm1005CtrlaccessLoopEntry
	MAX-ACCESS not-accessible
	STATUS current
	DESCRIPTION
        "
        Row definition for the pm1005CtrlaccessLoop 
        table
        "
	INDEX   { pm1005CtrlaccessLoopIndex }
	::= { pm1005CtrlaccessLoopTable 1 }


Pm1005CtrlaccessLoopEntry ::=
	SEQUENCE {
	pm1005CtrlaccessLoopIndex
		INTEGER,
	pm1005CtrlaccessLoopPortn
		EkiState
	}


pm1005CtrlaccessLoopIndex OBJECT-TYPE
	SYNTAX  INTEGER(0..128)
	MAX-ACCESS  read-only
	STATUS current
	DESCRIPTION
        "
        Index definition for the pm1005CtrlaccessLoop 
        table
        "
	::= { pm1005CtrlaccessLoopEntry 1 }


pm1005CtrlaccessLoopPortn OBJECT-TYPE
	SYNTAX  EkiState
	MAX-ACCESS read-write
	STATUS current
	DESCRIPTION
        "
        Client Facility Loopback :This 
        OID operates a Client Facility
         Loopback, looping client input 
        signal on the client output port. 
        The loop is located on the client 
        transceiver  <Help> This maintenance 
        parameter operates a Client Facility 
        Loopback, looping client input
         signal on the client output port. 
        The loop is located on the client 
        transceiver
        "
	::= { pm1005CtrlaccessLoopEntry 2 }


--- *********************************************************
---     TABLE for the pm1005CtrlportOosMode articles
--- *********************************************************

pm1005CtrlportOosModeTable OBJECT-TYPE
	SYNTAX  SEQUENCE OF Pm1005CtrlportOosModeEntry
	MAX-ACCESS not-accessible
	STATUS current
	DESCRIPTION
        "
        List of pm1005CtrlportOosMode
         Article
        "
	::= { pm1005CtrlClient 18 }


pm1005CtrlportOosModeEntry OBJECT-TYPE
	SYNTAX Pm1005CtrlportOosModeEntry
	MAX-ACCESS not-accessible
	STATUS current
	DESCRIPTION
        "
        Row definition for the pm1005CtrlportOosMode 
        table
        "
	INDEX   { pm1005CtrlportOosModeIndex }
	::= { pm1005CtrlportOosModeTable 1 }


Pm1005CtrlportOosModeEntry ::=
	SEQUENCE {
	pm1005CtrlportOosModeIndex
		INTEGER,
	pm1005CtrlportOosModePortn
		EkiState
	}


pm1005CtrlportOosModeIndex OBJECT-TYPE
	SYNTAX  INTEGER(0..128)
	MAX-ACCESS  read-only
	STATUS current
	DESCRIPTION
        "
        Index definition for the pm1005CtrlportOosMode 
        table
        "
	::= { pm1005CtrlportOosModeEntry 1 }


pm1005CtrlportOosModePortn OBJECT-TYPE
	SYNTAX  EkiState
	MAX-ACCESS read-write
	STATUS current
	DESCRIPTION
        "
        Client Port Out Of Service :This 
        OID sets the client port Out Of 
        Service  <Help>  This controls
         defines the service state of the 
        client port
        "
	::= { pm1005CtrlportOosModeEntry 2 }


--- *********************************************************
---     TABLE for the pm1005CtrlsfpOnCtrl articles
--- *********************************************************

pm1005CtrlsfpOnCtrlTable OBJECT-TYPE
	SYNTAX  SEQUENCE OF Pm1005CtrlsfpOnCtrlEntry
	MAX-ACCESS not-accessible
	STATUS current
	DESCRIPTION
        "
        List of pm1005CtrlsfpOnCtrl Article
        "
	::= { pm1005CtrlClient 19 }


pm1005CtrlsfpOnCtrlEntry OBJECT-TYPE
	SYNTAX Pm1005CtrlsfpOnCtrlEntry
	MAX-ACCESS not-accessible
	STATUS current
	DESCRIPTION
        "
        Row definition for the pm1005CtrlsfpOnCtrl 
        table
        "
	INDEX   { pm1005CtrlsfpOnCtrlIndex }
	::= { pm1005CtrlsfpOnCtrlTable 1 }


Pm1005CtrlsfpOnCtrlEntry ::=
	SEQUENCE {
	pm1005CtrlsfpOnCtrlIndex
		INTEGER,
	pm1005CtrlsfpOnCtrlPortn
		EkiState
	}


pm1005CtrlsfpOnCtrlIndex OBJECT-TYPE
	SYNTAX  INTEGER(0..128)
	MAX-ACCESS  read-only
	STATUS current
	DESCRIPTION
        "
        Index definition for the pm1005CtrlsfpOnCtrl 
        table
        "
	::= { pm1005CtrlsfpOnCtrlEntry 1 }


pm1005CtrlsfpOnCtrlPortn OBJECT-TYPE
	SYNTAX  EkiState
	MAX-ACCESS read-write
	STATUS current
	DESCRIPTION
        "
        Client SFP Optical Laser ON :This 
        OID switches on the SFP.
        "
	::= { pm1005CtrlsfpOnCtrlEntry 2 }


--- *********************************************************
---     TABLE for the pm1005CtrlsfpOffCtrl articles
--- *********************************************************

pm1005CtrlsfpOffCtrlTable OBJECT-TYPE
	SYNTAX  SEQUENCE OF Pm1005CtrlsfpOffCtrlEntry
	MAX-ACCESS not-accessible
	STATUS current
	DESCRIPTION
        "
        List of pm1005CtrlsfpOffCtrl Article
        "
	::= { pm1005CtrlClient 20 }


pm1005CtrlsfpOffCtrlEntry OBJECT-TYPE
	SYNTAX Pm1005CtrlsfpOffCtrlEntry
	MAX-ACCESS not-accessible
	STATUS current
	DESCRIPTION
        "
        Row definition for the pm1005CtrlsfpOffCtrl 
        table
        "
	INDEX   { pm1005CtrlsfpOffCtrlIndex }
	::= { pm1005CtrlsfpOffCtrlTable 1 }


Pm1005CtrlsfpOffCtrlEntry ::=
	SEQUENCE {
	pm1005CtrlsfpOffCtrlIndex
		INTEGER,
	pm1005CtrlsfpOffCtrlPortn
		EkiState
	}


pm1005CtrlsfpOffCtrlIndex OBJECT-TYPE
	SYNTAX  INTEGER(0..128)
	MAX-ACCESS  read-only
	STATUS current
	DESCRIPTION
        "
        Index definition for the pm1005CtrlsfpOffCtrl 
        table
        "
	::= { pm1005CtrlsfpOffCtrlEntry 1 }


pm1005CtrlsfpOffCtrlPortn OBJECT-TYPE
	SYNTAX  EkiState
	MAX-ACCESS read-write
	STATUS current
	DESCRIPTION
        "
        Client SFP Laser Shutdown :This 
        OID switches off the SFP.  <Help> 
         This control defines the laser 
        state of the client transceiver
        "
	::= { pm1005CtrlsfpOffCtrlEntry 2 }


--- *********************************************************
---     TABLE for the pm1005CtrlcsfUpIns articles
--- *********************************************************

pm1005CtrlcsfUpInsTable OBJECT-TYPE
	SYNTAX  SEQUENCE OF Pm1005CtrlcsfUpInsEntry
	MAX-ACCESS not-accessible
	STATUS current
	DESCRIPTION
        "
        List of pm1005CtrlcsfUpIns Article
        "
	::= { pm1005CtrlClient 21 }


pm1005CtrlcsfUpInsEntry OBJECT-TYPE
	SYNTAX Pm1005CtrlcsfUpInsEntry
	MAX-ACCESS not-accessible
	STATUS current
	DESCRIPTION
        "
        Row definition for the pm1005CtrlcsfUpIns 
        table
        "
	INDEX   { pm1005CtrlcsfUpInsIndex }
	::= { pm1005CtrlcsfUpInsTable 1 }


Pm1005CtrlcsfUpInsEntry ::=
	SEQUENCE {
	pm1005CtrlcsfUpInsIndex
		INTEGER,
	pm1005CtrlcsfUpInsPortn
		EkiState
	}


pm1005CtrlcsfUpInsIndex OBJECT-TYPE
	SYNTAX  INTEGER(0..128)
	MAX-ACCESS  read-only
	STATUS current
	DESCRIPTION
        "
        Index definition for the pm1005CtrlcsfUpIns 
        table
        "
	::= { pm1005CtrlcsfUpInsEntry 1 }


pm1005CtrlcsfUpInsPortn OBJECT-TYPE
	SYNTAX  EkiState
	MAX-ACCESS read-write
	STATUS current
	DESCRIPTION
        "
        Client Signal Fail Insertion :This 
        OID, when set, inserts  a client 
        signal fail in the upstream client 
        Port.  <Help>  This control inserts 
        a Client Signal Fail for the client 
        port
        "
	::= { pm1005CtrlcsfUpInsEntry 2 }


--- *********************************************************
---     TABLE for the pm1005CtrlcaisDwIns articles
--- *********************************************************

pm1005CtrlcaisDwInsTable OBJECT-TYPE
	SYNTAX  SEQUENCE OF Pm1005CtrlcaisDwInsEntry
	MAX-ACCESS not-accessible
	STATUS current
	DESCRIPTION
        "
        List of pm1005CtrlcaisDwIns Article
        "
	::= { pm1005CtrlClient 22 }


pm1005CtrlcaisDwInsEntry OBJECT-TYPE
	SYNTAX Pm1005CtrlcaisDwInsEntry
	MAX-ACCESS not-accessible
	STATUS current
	DESCRIPTION
        "
        Row definition for the pm1005CtrlcaisDwIns 
        table
        "
	INDEX   { pm1005CtrlcaisDwInsIndex }
	::= { pm1005CtrlcaisDwInsTable 1 }


Pm1005CtrlcaisDwInsEntry ::=
	SEQUENCE {
	pm1005CtrlcaisDwInsIndex
		INTEGER,
	pm1005CtrlcaisDwInsPortn
		EkiState
	}


pm1005CtrlcaisDwInsIndex OBJECT-TYPE
	SYNTAX  INTEGER(0..128)
	MAX-ACCESS  read-only
	STATUS current
	DESCRIPTION
        "
        Index definition for the pm1005CtrlcaisDwIns 
        table
        "
	::= { pm1005CtrlcaisDwInsEntry 1 }


pm1005CtrlcaisDwInsPortn OBJECT-TYPE
	SYNTAX  EkiState
	MAX-ACCESS read-write
	STATUS current
	DESCRIPTION
        "
        Client AIS Insertion :This OID, 
        when set, inserts a client AIS
         on the downstream client Port. 
         <Help>  This control inserts a 
        Client AIS for the client port
        "
	::= { pm1005CtrlcaisDwInsEntry 2 }


--- *********************************************************
---     TABLE for the pm1005CtrlclientAccessTermLoop articles
--- *********************************************************

pm1005CtrlclientAccessTermLoopTable OBJECT-TYPE
	SYNTAX  SEQUENCE OF Pm1005CtrlclientAccessTermLoopEntry
	MAX-ACCESS not-accessible
	STATUS current
	DESCRIPTION
        "
        List of pm1005CtrlclientAccessTermLoop 
        Article
        "
	::= { pm1005CtrlClient 26 }


pm1005CtrlclientAccessTermLoopEntry OBJECT-TYPE
	SYNTAX Pm1005CtrlclientAccessTermLoopEntry
	MAX-ACCESS not-accessible
	STATUS current
	DESCRIPTION
        "
        Row definition for the pm1005CtrlclientAccessTermLoop 
        table
        "
	INDEX   { pm1005CtrlclientAccessTermLoopIndex }
	::= { pm1005CtrlclientAccessTermLoopTable 1 }


Pm1005CtrlclientAccessTermLoopEntry ::=
	SEQUENCE {
	pm1005CtrlclientAccessTermLoopIndex
		INTEGER,
	pm1005CtrlclientAccessTermLoopPortn
		EkiState
	}


pm1005CtrlclientAccessTermLoopIndex OBJECT-TYPE
	SYNTAX  INTEGER(0..128)
	MAX-ACCESS  read-only
	STATUS current
	DESCRIPTION
        "
        Index definition for the pm1005CtrlclientAccessTermLoop 
        table
        "
	::= { pm1005CtrlclientAccessTermLoopEntry 1 }


pm1005CtrlclientAccessTermLoopPortn OBJECT-TYPE
	SYNTAX  EkiState
	MAX-ACCESS read-write
	STATUS current
	DESCRIPTION
        "
        Client Terminal Loopback :This 
        OID operates a Client Terminal
         Loopback, looping client input 
        signal on the client output port. 
        The loop is located on the line 
        transceiver  <Help> This maintenance 
        parameter operates a Client Terminal 
        Loopback, looping client input
         signal on the client output port. 
        The loop is located on the line 
        transceiver
        "
	::= { pm1005CtrlclientAccessTermLoopEntry 2 }


--- *********************************************************
---     TABLE for the pm1005Ctrlprotocol articles
--- *********************************************************

pm1005CtrlprotocolTable OBJECT-TYPE
	SYNTAX  SEQUENCE OF Pm1005CtrlprotocolEntry
	MAX-ACCESS not-accessible
	STATUS current
	DESCRIPTION
        "
        List of pm1005Ctrlprotocol Article
        "
	::= { pm1005CtrlClient 48 }


pm1005CtrlprotocolEntry OBJECT-TYPE
	SYNTAX Pm1005CtrlprotocolEntry
	MAX-ACCESS not-accessible
	STATUS current
	DESCRIPTION
        "
        Row definition for the pm1005Ctrlprotocol 
        table
        "
	INDEX   { pm1005CtrlprotocolIndex }
	::= { pm1005CtrlprotocolTable 1 }


Pm1005CtrlprotocolEntry ::=
	SEQUENCE {
	pm1005CtrlprotocolIndex
		INTEGER,
	pm1005CtrlprotocolPortn
		EkiProtocol
	}


pm1005CtrlprotocolIndex OBJECT-TYPE
	SYNTAX  INTEGER(0..128)
	MAX-ACCESS  read-only
	STATUS current
	DESCRIPTION
        "
        Index definition for the pm1005Ctrlprotocol 
        table
        "
	::= { pm1005CtrlprotocolEntry 1 }


pm1005CtrlprotocolPortn OBJECT-TYPE
	SYNTAX  EkiProtocol
	MAX-ACCESS read-write
	STATUS current
	DESCRIPTION
        "
        Client Protocol: This OID sets 
        the protocol of the Client port.
        "
	::= { pm1005CtrlprotocolEntry 2 }


--- *****************************************************
---     LEAF for the commAccessLoop article
--- *****************************************************
pm1005CtrlcommAccessLoop OBJECT IDENTIFIER ::= { pm1005CtrlLine 64 }




pm1005CtrlCommAccessloop OBJECT-TYPE
	  SYNTAX EkiOnOff
	  MAX-ACCESS read-write
	  STATUS deprecated
	  DESCRIPTION
        "
        PM Full Access Loop Mode :This 
        OID, when set, puts the module
         in common access loop back, looping 
        the 10 Gb/s output signal on the 
        10 Gb/s input.
        "
	  ::= { pm1005CtrlcommAccessLoop 1 }



--- *****************************************************
---     LEAF for the lineLoop article
--- *****************************************************
pm1005CtrllineLoop OBJECT IDENTIFIER ::= { pm1005CtrlLine 66 }




pm1005CtrlLineLoop OBJECT-TYPE
	  SYNTAX EkiOnOff
	  MAX-ACCESS read-write
	  STATUS deprecated
	  DESCRIPTION
        "
        PM Line Loop Mode :This OID, when 
        set at '1' puts the module in line 
        loopback mode, looping the received 
        10 Gb/s signal on the transmit
         10 Gb/s output. The Upstream part 
        of the module is timed on the 10 
        Gb/s recovered clock in that case.
        "
	  ::= { pm1005CtrllineLoop 1 }



--- *****************************************************
---     LEAF for the msAis article
--- *****************************************************
pm1005CtrlmsAis OBJECT IDENTIFIER ::= { pm1005CtrlLine 67 }




pm1005CtrlMsAis OBJECT-TYPE
	  SYNTAX EkiOnOff
	  MAX-ACCESS read-write
	  STATUS current
	  DESCRIPTION
        "
        Insert MS-AIS/L-AIS On Line Output 
        :This OID, when set, inserts an 
        MS-AIS/L-AIS in the outgoing STM-64/OC-192 
        signal.
        "
	  ::= { pm1005CtrlmsAis 1 }



--- *********************************************************
---     TABLE for the pm1005CtrlfecDisable articles
--- *********************************************************

pm1005CtrlfecDisableTable OBJECT-TYPE
	SYNTAX  SEQUENCE OF Pm1005CtrlfecDisableEntry
	MAX-ACCESS not-accessible
	STATUS current
	DESCRIPTION
        "
        List of pm1005CtrlfecDisable Article
        "
	::= { pm1005CtrlLine 69 }


pm1005CtrlfecDisableEntry OBJECT-TYPE
	SYNTAX Pm1005CtrlfecDisableEntry
	MAX-ACCESS not-accessible
	STATUS current
	DESCRIPTION
        "
        Row definition for the pm1005CtrlfecDisable 
        table
        "
	INDEX   { pm1005CtrlfecDisableIndex }
	::= { pm1005CtrlfecDisableTable 1 }


Pm1005CtrlfecDisableEntry ::=
	SEQUENCE {
	pm1005CtrlfecDisableIndex
		INTEGER,
	pm1005CtrlfecDisablePortn
		EkiState
	}


pm1005CtrlfecDisableIndex OBJECT-TYPE
	SYNTAX  INTEGER(0..128)
	MAX-ACCESS  read-only
	STATUS current
	DESCRIPTION
        "
        Index definition for the pm1005CtrlfecDisable 
        table
        "
	::= { pm1005CtrlfecDisableEntry 1 }


pm1005CtrlfecDisablePortn OBJECT-TYPE
	SYNTAX  EkiState
	MAX-ACCESS read-write
	STATUS current
	DESCRIPTION
        "
        Forward Error Correction Inhibition 
        :This OID, when set, inhibits the 
        Forward Error Correction feature 
        on the line input  <Help>  This 
        control enables/disables the Forward 
        Error Correction on the line interface
        "
	::= { pm1005CtrlfecDisableEntry 2 }


--- *****************************************************
---     LEAF for the protMgnt article
--- *****************************************************
pm1005CtrlProtMgnt OBJECT IDENTIFIER ::= { pm1005CtrlLine 73 }




pm1005CtrlLineNumber OBJECT-TYPE
	  SYNTAX Unsigned32 (0..3)
	  MAX-ACCESS read-write
	  STATUS current
	  DESCRIPTION
        "
        Active Line Number : This OID
         sets the active line number
        "
	  ::= { pm1005CtrlProtMgnt 1 }



pm1005CtrlProtMode OBJECT-TYPE
	  SYNTAX EkiMode
	  MAX-ACCESS read-write
	  STATUS current
	  DESCRIPTION
        "
        Line Switch Mode (Auto Or Manual) 
        :This bit selects the manual (1) 
        or automatic (0) switch method
          <Help>  This control defines
         the protection switch mode on
         the line interface
        "
	  ::= { pm1005CtrlProtMgnt 2 }



--- *********************************************************
---     TABLE for the pm1005CtrllineOosMode articles
--- *********************************************************

pm1005CtrllineOosModeTable OBJECT-TYPE
	SYNTAX  SEQUENCE OF Pm1005CtrllineOosModeEntry
	MAX-ACCESS not-accessible
	STATUS current
	DESCRIPTION
        "
        List of pm1005CtrllineOosMode
         Article
        "
	::= { pm1005CtrlLine 74 }


pm1005CtrllineOosModeEntry OBJECT-TYPE
	SYNTAX Pm1005CtrllineOosModeEntry
	MAX-ACCESS not-accessible
	STATUS current
	DESCRIPTION
        "
        Row definition for the pm1005CtrllineOosMode 
        table
        "
	INDEX   { pm1005CtrllineOosModeIndex }
	::= { pm1005CtrllineOosModeTable 1 }


Pm1005CtrllineOosModeEntry ::=
	SEQUENCE {
	pm1005CtrllineOosModeIndex
		INTEGER,
	pm1005CtrllineOosModePortn
		EkiState
	}


pm1005CtrllineOosModeIndex OBJECT-TYPE
	SYNTAX  INTEGER(0..128)
	MAX-ACCESS  read-only
	STATUS current
	DESCRIPTION
        "
        Index definition for the pm1005CtrllineOosMode 
        table
        "
	::= { pm1005CtrllineOosModeEntry 1 }


pm1005CtrllineOosModePortn OBJECT-TYPE
	SYNTAX  EkiState
	MAX-ACCESS read-write
	STATUS current
	DESCRIPTION
        "
        Line Port Out Of Service :This 
        OID sets the line port Out Of Service 
         <Help>  This control defines the 
        service state of the line port
        "
	::= { pm1005CtrllineOosModeEntry 2 }


--- *****************************************************
---     LEAF for the maintenanceMode article
--- *****************************************************
pm1005CtrlmaintenanceMode OBJECT IDENTIFIER ::= { pm1005CtrlOther 197 }




pm1005CtrlMaintenanceMode OBJECT-TYPE
	  SYNTAX EkiOnOff
	  MAX-ACCESS read-write
	  STATUS current
	  DESCRIPTION
        "
        Module Maintenance Mode :This
         OID enables the maintenance mode 
        on the PM.  <Help>   This control 
        enables the maintenance mode on 
        the PM.
        "
	  ::= { pm1005CtrlmaintenanceMode 1 }



--- *****************************************************
---     LEAF for the dccEnable article
--- *****************************************************
pm1005CtrldccEnable OBJECT IDENTIFIER ::= { pm1005CtrlOther 198 }




pm1005CtrlDccEnable OBJECT-TYPE
	  SYNTAX EkiOnOff
	  MAX-ACCESS read-write
	  STATUS current
	  DESCRIPTION
        "
        DCC Enable :This OID enables the 
        DCC mode on the PM   <Help>   This 
        control enables the DCC mode on 
        the PM
        "
	  ::= { pm1005CtrldccEnable 1 }



--- *****************************************************
---     LEAF for the ledTest article
--- *****************************************************
pm1005CtrlledTest OBJECT IDENTIFIER ::= { pm1005CtrlOther 192 }




pm1005CtrlLedOff OBJECT-TYPE
	  SYNTAX EkiOnOff
	  MAX-ACCESS read-write
	  STATUS current
	  DESCRIPTION
        "
        Leds Off :This OID switches off 
        all the Leds as a test feature. 
         <Help>  This control initiates 
        a test leds turning all the LEDs 
        to OFF
        "
	  ::= { pm1005CtrlledTest 3 }



pm1005CtrlRedLed OBJECT-TYPE
	  SYNTAX EkiOnOff
	  MAX-ACCESS read-write
	  STATUS current
	  DESCRIPTION
        "
        Red Leds Test :This OID switches 
        on all the red Leds as a test feature. 
         <Help>  This control initiates 
        a test leds turning all the LEDs 
        to red
        "
	  ::= { pm1005CtrlledTest 2 }



pm1005CtrlGreenLed OBJECT-TYPE
	  SYNTAX EkiOnOff
	  MAX-ACCESS read-write
	  STATUS current
	  DESCRIPTION
        "
        Green Leds Test :This OID switches 
        on all the green Leds as a test 
        feature.  <Help>  This control
         initiates a test leds turning
         all the LEDs to green
        "
	  ::= { pm1005CtrlledTest 1 }



--- *****************************************************
---     LEAF for the moduleOosMode article
--- *****************************************************
pm1005CtrlmoduleOosMode OBJECT IDENTIFIER ::= { pm1005CtrlOther 193 }




pm1005CtrlModuleOosMode OBJECT-TYPE
	  SYNTAX EkiOnOff
	  MAX-ACCESS read-write
	  STATUS current
	  DESCRIPTION
        "
        PM Out Of Service :This OID sets 
        the PM Out Of Service  <Help> 
         This control defines the service 
        state of the complete module
        "
	  ::= { pm1005CtrlmoduleOosMode 1 }



--- *********************************************************
---     TABLE for the pm1005CtrlxfpOnoff articles
--- *********************************************************

pm1005CtrlxfpOnoffTable OBJECT-TYPE
	SYNTAX  SEQUENCE OF Pm1005CtrlxfpOnoffEntry
	MAX-ACCESS not-accessible
	STATUS current
	DESCRIPTION
        "
        List of pm1005CtrlxfpOnoff Article
        "
	::= { pm1005CtrlLine 208 }


pm1005CtrlxfpOnoffEntry OBJECT-TYPE
	SYNTAX Pm1005CtrlxfpOnoffEntry
	MAX-ACCESS not-accessible
	STATUS current
	DESCRIPTION
        "
        Row definition for the pm1005CtrlxfpOnoff 
        table
        "
	INDEX   { pm1005CtrlxfpOnoffIndex }
	::= { pm1005CtrlxfpOnoffTable 1 }


Pm1005CtrlxfpOnoffEntry ::=
	SEQUENCE {
	pm1005CtrlxfpOnoffIndex
		INTEGER,
	pm1005CtrlxfpOnoffPortn
		EkiState
	}


pm1005CtrlxfpOnoffIndex OBJECT-TYPE
	SYNTAX  INTEGER(0..128)
	MAX-ACCESS  read-only
	STATUS current
	DESCRIPTION
        "
        Index definition for the pm1005CtrlxfpOnoff 
        table
        "
	::= { pm1005CtrlxfpOnoffEntry 1 }


pm1005CtrlxfpOnoffPortn OBJECT-TYPE
	SYNTAX  EkiState
	MAX-ACCESS read-write
	STATUS current
	DESCRIPTION
        "
        Line Optical Laser Shutdown :This 
        OID switches off the XFP or the 
        OTX  <Help>  This control defines 
        the laser state of the line transceiver
        "
	::= { pm1005CtrlxfpOnoffEntry 2 }


--- *********************************************************
---     TABLE for the pm1005CtrlxfpLineLoop articles
--- *********************************************************

pm1005CtrlxfpLineLoopTable OBJECT-TYPE
	SYNTAX  SEQUENCE OF Pm1005CtrlxfpLineLoopEntry
	MAX-ACCESS not-accessible
	STATUS current
	DESCRIPTION
        "
        List of pm1005CtrlxfpLineLoop
         Article
        "
	::= { pm1005CtrlLine 209 }


pm1005CtrlxfpLineLoopEntry OBJECT-TYPE
	SYNTAX Pm1005CtrlxfpLineLoopEntry
	MAX-ACCESS not-accessible
	STATUS current
	DESCRIPTION
        "
        Row definition for the pm1005CtrlxfpLineLoop 
        table
        "
	INDEX   { pm1005CtrlxfpLineLoopIndex }
	::= { pm1005CtrlxfpLineLoopTable 1 }


Pm1005CtrlxfpLineLoopEntry ::=
	SEQUENCE {
	pm1005CtrlxfpLineLoopIndex
		INTEGER,
	pm1005CtrlxfpLineLoopPortn
		EkiState
	}


pm1005CtrlxfpLineLoopIndex OBJECT-TYPE
	SYNTAX  INTEGER(0..128)
	MAX-ACCESS  read-only
	STATUS current
	DESCRIPTION
        "
        Index definition for the pm1005CtrlxfpLineLoop 
        table
        "
	::= { pm1005CtrlxfpLineLoopEntry 1 }


pm1005CtrlxfpLineLoopPortn OBJECT-TYPE
	SYNTAX  EkiState
	MAX-ACCESS read-write
	STATUS current
	DESCRIPTION
        "
        Line Facility Loopback :This OID 
        operates a Line Facility Loopback, 
        looping line input signal on the 
        line output port. The loop is located 
        on the line transceiver. If the 
        Line signal carries DCC, the management 
        network is impacted  <Help> This 
        maintenance parameter operates
         a Line Facility Loopback, looping 
        line input signal on the line output 
        port. The loop is located on the 
        line transceiver. If the Line signal 
        carries DCC, the management network 
        is impacted
        "
	::= { pm1005CtrlxfpLineLoopEntry 2 }


--- *********************************************************
---     TABLE for the pm1005CtrlxfpXfiLoop articles
--- *********************************************************

pm1005CtrlxfpXfiLoopTable OBJECT-TYPE
	SYNTAX  SEQUENCE OF Pm1005CtrlxfpXfiLoopEntry
	MAX-ACCESS not-accessible
	STATUS current
	DESCRIPTION
        "
        List of pm1005CtrlxfpXfiLoop Article
        "
	::= { pm1005CtrlLine 210 }


pm1005CtrlxfpXfiLoopEntry OBJECT-TYPE
	SYNTAX Pm1005CtrlxfpXfiLoopEntry
	MAX-ACCESS not-accessible
	STATUS current
	DESCRIPTION
        "
        Row definition for the pm1005CtrlxfpXfiLoop 
        table
        "
	INDEX   { pm1005CtrlxfpXfiLoopIndex }
	::= { pm1005CtrlxfpXfiLoopTable 1 }


Pm1005CtrlxfpXfiLoopEntry ::=
	SEQUENCE {
	pm1005CtrlxfpXfiLoopIndex
		INTEGER,
	pm1005CtrlxfpXfiLoopPortn
		EkiState
	}


pm1005CtrlxfpXfiLoopIndex OBJECT-TYPE
	SYNTAX  INTEGER(0..128)
	MAX-ACCESS  read-only
	STATUS current
	DESCRIPTION
        "
        Index definition for the pm1005CtrlxfpXfiLoop 
        table
        "
	::= { pm1005CtrlxfpXfiLoopEntry 1 }


pm1005CtrlxfpXfiLoopPortn OBJECT-TYPE
	SYNTAX  EkiState
	MAX-ACCESS read-write
	STATUS current
	DESCRIPTION
        "
        Line Terminal Loopback :This OID 
        operates a Line Terminal Loopback, 
        looping line input signal on the 
        line output port. The loop is located 
        on all client transceivers  <Help> 
        This maintenance parameter operates 
        a Line Terminal Loopback, looping 
        line input signal on the line output 
        port. The loop is located on all 
        client transceivers.
        "
	::= { pm1005CtrlxfpXfiLoopEntry 2 }


--- *********************************************************
---     TABLE for the pm1005CtrllineTunableChannel articles
--- *********************************************************

pm1005CtrllineTunableChannelTable OBJECT-TYPE
	SYNTAX  SEQUENCE OF Pm1005CtrllineTunableChannelEntry
	MAX-ACCESS not-accessible
	STATUS current
	DESCRIPTION
        "
        List of pm1005CtrllineTunableChannel 
        Article
        "
	::= { pm1005CtrlLine 212 }


pm1005CtrllineTunableChannelEntry OBJECT-TYPE
	SYNTAX Pm1005CtrllineTunableChannelEntry
	MAX-ACCESS not-accessible
	STATUS current
	DESCRIPTION
        "
        Row definition for the pm1005CtrllineTunableChannel 
        table
        "
	INDEX   { pm1005CtrllineTunableChannelIndex }
	::= { pm1005CtrllineTunableChannelTable 1 }


Pm1005CtrllineTunableChannelEntry ::=
	SEQUENCE {
	pm1005CtrllineTunableChannelIndex
		INTEGER,
	pm1005CtrllineTunableChannelPortn
		Pm1005OtxChannel
	}


pm1005CtrllineTunableChannelIndex OBJECT-TYPE
	SYNTAX  INTEGER(0..128)
	MAX-ACCESS  read-only
	STATUS current
	DESCRIPTION
        "
        Index definition for the pm1005CtrllineTunableChannel 
        table
        "
	::= { pm1005CtrllineTunableChannelEntry 1 }


pm1005CtrllineTunableChannelPortn OBJECT-TYPE
	SYNTAX  Pm1005OtxChannel
	MAX-ACCESS read-write
	STATUS current
	DESCRIPTION
        "
        ITU Channel :This OID selects
         the ITU channel of the Line OTX 
        TLH Laser  <Help>   This control 
        defines the ITU channel of the
         Line OTX TLH Laser
        "
	::= { pm1005CtrllineTunableChannelEntry 2 }


--- *********************************************************
---     TABLE for the pm1005CtrllinePhotodiodeMode articles
--- *********************************************************

pm1005CtrllinePhotodiodeModeTable OBJECT-TYPE
	SYNTAX  SEQUENCE OF Pm1005CtrllinePhotodiodeModeEntry
	MAX-ACCESS not-accessible
	STATUS current
	DESCRIPTION
        "
        List of pm1005CtrllinePhotodiodeMode 
        Article
        "
	::= { pm1005CtrlLine 213 }


pm1005CtrllinePhotodiodeModeEntry OBJECT-TYPE
	SYNTAX Pm1005CtrllinePhotodiodeModeEntry
	MAX-ACCESS not-accessible
	STATUS current
	DESCRIPTION
        "
        Row definition for the pm1005CtrllinePhotodiodeMode 
        table
        "
	INDEX   { pm1005CtrllinePhotodiodeModeIndex }
	::= { pm1005CtrllinePhotodiodeModeTable 1 }


Pm1005CtrllinePhotodiodeModeEntry ::=
	SEQUENCE {
	pm1005CtrllinePhotodiodeModeIndex
		INTEGER,
	pm1005CtrllinePhotodiodeModePortn
		Pm1005OtxMode
	}


pm1005CtrllinePhotodiodeModeIndex OBJECT-TYPE
	SYNTAX  INTEGER(0..128)
	MAX-ACCESS  read-only
	STATUS current
	DESCRIPTION
        "
        Index definition for the pm1005CtrllinePhotodiodeMode 
        table
        "
	::= { pm1005CtrllinePhotodiodeModeEntry 1 }


pm1005CtrllinePhotodiodeModePortn OBJECT-TYPE
	SYNTAX  Pm1005OtxMode
	MAX-ACCESS read-write
	STATUS current
	DESCRIPTION
        "
        OTX TLH Rx Sens. Mode :This OID 
        defines the Rx sensiblity mode
         of the Line OTX TLH  <Help>  
         This control defines the receiver 
        sensibility mode of the Line OTX 
        TLH Laser (OTX60, OTX80 or Custom)
        "
	::= { pm1005CtrllinePhotodiodeModeEntry 2 }


--- *********************************************************
---     TABLE for the pm1005CtrllinePhotodiodeValue articles
--- *********************************************************

pm1005CtrllinePhotodiodeValueTable OBJECT-TYPE
	SYNTAX  SEQUENCE OF Pm1005CtrllinePhotodiodeValueEntry
	MAX-ACCESS not-accessible
	STATUS current
	DESCRIPTION
        "
        List of pm1005CtrllinePhotodiodeValue 
        Article
        "
	::= { pm1005CtrlLine 214 }


pm1005CtrllinePhotodiodeValueEntry OBJECT-TYPE
	SYNTAX Pm1005CtrllinePhotodiodeValueEntry
	MAX-ACCESS not-accessible
	STATUS current
	DESCRIPTION
        "
        Row definition for the pm1005CtrllinePhotodiodeValue 
        table
        "
	INDEX   { pm1005CtrllinePhotodiodeValueIndex }
	::= { pm1005CtrllinePhotodiodeValueTable 1 }


Pm1005CtrllinePhotodiodeValueEntry ::=
	SEQUENCE {
	pm1005CtrllinePhotodiodeValueIndex
		INTEGER,
	pm1005CtrllinePhotodiodeValuePortn
		Pm1005AdjustValue
	}


pm1005CtrllinePhotodiodeValueIndex OBJECT-TYPE
	SYNTAX  INTEGER(0..128)
	MAX-ACCESS  read-only
	STATUS current
	DESCRIPTION
        "
        Index definition for the pm1005CtrllinePhotodiodeValue 
        table
        "
	::= { pm1005CtrllinePhotodiodeValueEntry 1 }


pm1005CtrllinePhotodiodeValuePortn OBJECT-TYPE
	SYNTAX  Pm1005AdjustValue
	MAX-ACCESS read-write
	STATUS current
	DESCRIPTION
        "
        OTX TLH Rx Sensibility :This OID 
        sets the Rx sensibility of the
         Line OTX TLH (custom mode only) 
         <Help>   This control defines
         the receiver sensibility value 
        (only in Custom mode) of the Line 
        OTX TLH Laser
        "
	::= { pm1005CtrllinePhotodiodeValueEntry 2 }


--- *********************************************************
---     TABLE for the pm1005CtrllinePowerLaser articles
--- *********************************************************

pm1005CtrllinePowerLaserTable OBJECT-TYPE
	SYNTAX  SEQUENCE OF Pm1005CtrllinePowerLaserEntry
	MAX-ACCESS not-accessible
	STATUS current
	DESCRIPTION
        "
        List of pm1005CtrllinePowerLaser 
        Article
        "
	::= { pm1005CtrlLine 215 }


pm1005CtrllinePowerLaserEntry OBJECT-TYPE
	SYNTAX Pm1005CtrllinePowerLaserEntry
	MAX-ACCESS not-accessible
	STATUS current
	DESCRIPTION
        "
        Row definition for the pm1005CtrllinePowerLaser 
        table
        "
	INDEX   { pm1005CtrllinePowerLaserIndex }
	::= { pm1005CtrllinePowerLaserTable 1 }


Pm1005CtrllinePowerLaserEntry ::=
	SEQUENCE {
	pm1005CtrllinePowerLaserIndex
		INTEGER,
	pm1005CtrllinePowerLaserPortn
		INTEGER 
	}


pm1005CtrllinePowerLaserIndex OBJECT-TYPE
	SYNTAX  INTEGER(0..128)
	MAX-ACCESS  read-only
	STATUS current
	DESCRIPTION
        "
        Index definition for the pm1005CtrllinePowerLaser 
        table
        "
	::= { pm1005CtrllinePowerLaserEntry 1 }


pm1005CtrllinePowerLaserPortn OBJECT-TYPE
	SYNTAX  INTEGER (0..255)
	MAX-ACCESS read-write
	STATUS current
	DESCRIPTION
        "
        Line Laser Output Power [3-5]
         :This OID sets the output power 
        value on the laser of the Line
         OTX TLH  (AV=Power*10+158) (Unit 
        = dBm)  <Help>   This control defines 
        the start-up output power of the 
        Line OTX TLH
        "
	::= { pm1005CtrllinePowerLaserEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm1005CntupRaRemCnt articles
--- *********************************************************

pm1005CntupRaRemCntTable OBJECT-TYPE
	SYNTAX  SEQUENCE OF Pm1005CntupRaRemCntEntry
	MAX-ACCESS not-accessible
	STATUS current
	DESCRIPTION
        "
        List of pm1005CntupRaRemCnt Article
        "
	::= { pm1005CntClient 16 }


pm1005CntupRaRemCntEntry OBJECT-TYPE
	SYNTAX Pm1005CntupRaRemCntEntry
	MAX-ACCESS not-accessible
	STATUS current
	DESCRIPTION
        "
        Row definition for the pm1005CntupRaRemCnt 
        table
        "
	INDEX   { pm1005CntupRaRemCntIndex }
	::= { pm1005CntupRaRemCntTable 1 }


Pm1005CntupRaRemCntEntry ::=
	SEQUENCE {
	pm1005CntupRaRemCntIndex
		INTEGER,
	pm1005CntupRaRemCntValuePortn
		Counter32,
	pm1005CntupRaRemCntErrorPortn
		EkiOnOff,
	pm1005CntupRaRemCntOverloadPortn
		EkiOnOff
	}


pm1005CntupRaRemCntIndex OBJECT-TYPE
	SYNTAX  INTEGER(0..128)
	MAX-ACCESS  read-only
	STATUS current
	DESCRIPTION
        "
        Index definition for the pm1005CntupRaRemCnt 
        table
        "
	::= { pm1005CntupRaRemCntEntry 1 }


pm1005CntupRaRemCntValuePortn OBJECT-TYPE
	SYNTAX  Counter32
	MAX-ACCESS read-only
	STATUS current
	DESCRIPTION
        "
        Client Rate Adapt. Words Removal 
        :This counter is incremented each 
        time a rate adaptation 10B word 
        is removed from the Client input 
        stream
        "
	::= { pm1005CntupRaRemCntEntry 2 }


pm1005CntupRaRemCntErrorPortn OBJECT-TYPE
	SYNTAX  EkiOnOff
	MAX-ACCESS read-only
	STATUS current
	DESCRIPTION
        "
        Client Counter Error :This OID 
        when set indicates the rate adaptation 
        removal counter value is invalid 
        on Port
        "
	::= { pm1005CntupRaRemCntEntry 3 }


pm1005CntupRaRemCntOverloadPortn OBJECT-TYPE
	SYNTAX  EkiOnOff
	MAX-ACCESS read-only
	STATUS current
	DESCRIPTION
        "
        Client Counter Overload :This
         OID when set indicates a rate
         adaptation removal counter overload 
        on Port
        "
	::= { pm1005CntupRaRemCntEntry 4 }


--- *********************************************************
---     TABLE for the pm1005CntupRaInsCnt articles
--- *********************************************************

pm1005CntupRaInsCntTable OBJECT-TYPE
	SYNTAX  SEQUENCE OF Pm1005CntupRaInsCntEntry
	MAX-ACCESS not-accessible
	STATUS current
	DESCRIPTION
        "
        List of pm1005CntupRaInsCnt Article
        "
	::= { pm1005CntClient 24 }


pm1005CntupRaInsCntEntry OBJECT-TYPE
	SYNTAX Pm1005CntupRaInsCntEntry
	MAX-ACCESS not-accessible
	STATUS current
	DESCRIPTION
        "
        Row definition for the pm1005CntupRaInsCnt 
        table
        "
	INDEX   { pm1005CntupRaInsCntIndex }
	::= { pm1005CntupRaInsCntTable 1 }


Pm1005CntupRaInsCntEntry ::=
	SEQUENCE {
	pm1005CntupRaInsCntIndex
		INTEGER,
	pm1005CntupRaInsCntValuePortn
		Counter32,
	pm1005CntupRaInsCntErrorPortn
		EkiOnOff,
	pm1005CntupRaInsCntOverloadPortn
		EkiOnOff
	}


pm1005CntupRaInsCntIndex OBJECT-TYPE
	SYNTAX  INTEGER(0..128)
	MAX-ACCESS  read-only
	STATUS current
	DESCRIPTION
        "
        Index definition for the pm1005CntupRaInsCnt 
        table
        "
	::= { pm1005CntupRaInsCntEntry 1 }


pm1005CntupRaInsCntValuePortn OBJECT-TYPE
	SYNTAX  Counter32
	MAX-ACCESS read-only
	STATUS current
	DESCRIPTION
        "
        Client Rate Adapt. Words Insertion 
        :This counter is incremented each 
        time a rate adaptation 10B word 
        is inserted in the Client input 
        stream
        "
	::= { pm1005CntupRaInsCntEntry 2 }


pm1005CntupRaInsCntErrorPortn OBJECT-TYPE
	SYNTAX  EkiOnOff
	MAX-ACCESS read-only
	STATUS current
	DESCRIPTION
        "
        Client Counter Error :This OID 
        when set indicates the rate adaptation 
        insertion counter value is invalid 
        on Port
        "
	::= { pm1005CntupRaInsCntEntry 3 }


pm1005CntupRaInsCntOverloadPortn OBJECT-TYPE
	SYNTAX  EkiOnOff
	MAX-ACCESS read-only
	STATUS current
	DESCRIPTION
        "
        Client Counter Overload :This
         OID when set indicates a rate
         adaptation insertion counter overload 
        on Port
        "
	::= { pm1005CntupRaInsCntEntry 4 }


--- *********************************************************
---     TABLE for the pm1005CntupRdErrCnt articles
--- *********************************************************

pm1005CntupRdErrCntTable OBJECT-TYPE
	SYNTAX  SEQUENCE OF Pm1005CntupRdErrCntEntry
	MAX-ACCESS not-accessible
	STATUS current
	DESCRIPTION
        "
        List of pm1005CntupRdErrCnt Article
        "
	::= { pm1005CntClient 32 }


pm1005CntupRdErrCntEntry OBJECT-TYPE
	SYNTAX Pm1005CntupRdErrCntEntry
	MAX-ACCESS not-accessible
	STATUS current
	DESCRIPTION
        "
        Row definition for the pm1005CntupRdErrCnt 
        table
        "
	INDEX   { pm1005CntupRdErrCntIndex }
	::= { pm1005CntupRdErrCntTable 1 }


Pm1005CntupRdErrCntEntry ::=
	SEQUENCE {
	pm1005CntupRdErrCntIndex
		INTEGER,
	pm1005CntupRdErrCntValuePortn
		Counter32,
	pm1005CntupRdErrCntErrorPortn
		EkiOnOff,
	pm1005CntupRdErrCntOverloadPortn
		EkiOnOff
	}


pm1005CntupRdErrCntIndex OBJECT-TYPE
	SYNTAX  INTEGER(0..128)
	MAX-ACCESS  read-only
	STATUS current
	DESCRIPTION
        "
        Index definition for the pm1005CntupRdErrCnt 
        table
        "
	::= { pm1005CntupRdErrCntEntry 1 }


pm1005CntupRdErrCntValuePortn OBJECT-TYPE
	SYNTAX  Counter32
	MAX-ACCESS read-only
	STATUS current
	DESCRIPTION
        "
        Client Input Errors :This counter 
        is increased each time a 10b/8b 
        running disparity error is detected 
        on the Client input stream  <Help> 
         This counter gives the number
         of 10b/8b running disparity errors 
        on the client port
        "
	::= { pm1005CntupRdErrCntEntry 2 }


pm1005CntupRdErrCntErrorPortn OBJECT-TYPE
	SYNTAX  EkiOnOff
	MAX-ACCESS read-only
	STATUS current
	DESCRIPTION
        "
        Client Counter Error :This OID 
        when set indicates the client error 
        counter value is invalid on Port
        "
	::= { pm1005CntupRdErrCntEntry 3 }


pm1005CntupRdErrCntOverloadPortn OBJECT-TYPE
	SYNTAX  EkiOnOff
	MAX-ACCESS read-only
	STATUS current
	DESCRIPTION
        "
        Client Counter Overload :This
         OID when set indicates a client 
        input error counter overload on 
        Port
        "
	::= { pm1005CntupRdErrCntEntry 4 }


--- *********************************************************
---     TABLE for the pm1005CntupTimCnt articles
--- *********************************************************

pm1005CntupTimCntTable OBJECT-TYPE
	SYNTAX  SEQUENCE OF Pm1005CntupTimCntEntry
	MAX-ACCESS not-accessible
	STATUS current
	DESCRIPTION
        "
        List of pm1005CntupTimCnt Article
        "
	::= { pm1005CntClient 40 }


pm1005CntupTimCntEntry OBJECT-TYPE
	SYNTAX Pm1005CntupTimCntEntry
	MAX-ACCESS not-accessible
	STATUS current
	DESCRIPTION
        "
        Row definition for the pm1005CntupTimCnt 
        table
        "
	INDEX   { pm1005CntupTimCntIndex }
	::= { pm1005CntupTimCntTable 1 }


Pm1005CntupTimCntEntry ::=
	SEQUENCE {
	pm1005CntupTimCntIndex
		INTEGER,
	pm1005CntupTimCntValuePortn
		Counter32,
	pm1005CntupTimCntErrorPortn
		EkiOnOff,
	pm1005CntupTimCntOverloadPortn
		EkiOnOff
	}


pm1005CntupTimCntIndex OBJECT-TYPE
	SYNTAX  INTEGER(0..128)
	MAX-ACCESS  read-only
	STATUS current
	DESCRIPTION
        "
        Index definition for the pm1005CntupTimCnt 
        table
        "
	::= { pm1005CntupTimCntEntry 1 }


pm1005CntupTimCntValuePortn OBJECT-TYPE
	SYNTAX  Counter32
	MAX-ACCESS read-only
	STATUS current
	DESCRIPTION
        "
        Client Upstream Timer Counter
         :This is the timing counter dedicated 
        to the upstream access counters. 
        It is incremented every 125 us.
        "
	::= { pm1005CntupTimCntEntry 2 }


pm1005CntupTimCntErrorPortn OBJECT-TYPE
	SYNTAX  EkiOnOff
	MAX-ACCESS read-only
	STATUS current
	DESCRIPTION
        "
        Client Counter Error :This OID 
        when set indicates the upstream 
        timing counter value is invalid 
        on Port
        "
	::= { pm1005CntupTimCntEntry 3 }


pm1005CntupTimCntOverloadPortn OBJECT-TYPE
	SYNTAX  EkiOnOff
	MAX-ACCESS read-only
	STATUS current
	DESCRIPTION
        "
        Client Counter Overload :This
         OID when set indicates a upstream 
        timing counter overload on Port
        "
	::= { pm1005CntupTimCntEntry 4 }


--- *********************************************************
---     TABLE for the pm1005CntupCvErrCnt articles
--- *********************************************************

pm1005CntupCvErrCntTable OBJECT-TYPE
	SYNTAX  SEQUENCE OF Pm1005CntupCvErrCntEntry
	MAX-ACCESS not-accessible
	STATUS current
	DESCRIPTION
        "
        List of pm1005CntupCvErrCnt Article
        "
	::= { pm1005CntClient 48 }


pm1005CntupCvErrCntEntry OBJECT-TYPE
	SYNTAX Pm1005CntupCvErrCntEntry
	MAX-ACCESS not-accessible
	STATUS current
	DESCRIPTION
        "
        Row definition for the pm1005CntupCvErrCnt 
        table
        "
	INDEX   { pm1005CntupCvErrCntIndex }
	::= { pm1005CntupCvErrCntTable 1 }


Pm1005CntupCvErrCntEntry ::=
	SEQUENCE {
	pm1005CntupCvErrCntIndex
		INTEGER,
	pm1005CntupCvErrCntValuePortn
		Counter32,
	pm1005CntupCvErrCntErrorPortn
		EkiOnOff,
	pm1005CntupCvErrCntOverloadPortn
		EkiOnOff
	}


pm1005CntupCvErrCntIndex OBJECT-TYPE
	SYNTAX  INTEGER(0..128)
	MAX-ACCESS  read-only
	STATUS current
	DESCRIPTION
        "
        Index definition for the pm1005CntupCvErrCnt 
        table
        "
	::= { pm1005CntupCvErrCntEntry 1 }


pm1005CntupCvErrCntValuePortn OBJECT-TYPE
	SYNTAX  Counter32
	MAX-ACCESS read-only
	STATUS current
	DESCRIPTION
        "
        Client Coding Violation Counter 
        :This counter is increased each 
        time a 10b/8b coding violation
         is detected on the Client input 
        stream
        "
	::= { pm1005CntupCvErrCntEntry 2 }


pm1005CntupCvErrCntErrorPortn OBJECT-TYPE
	SYNTAX  EkiOnOff
	MAX-ACCESS read-only
	STATUS current
	DESCRIPTION
        "
        Client Counter Error :This OID 
        when set indicates the coding violation 
        counter value is invalid on Port
        "
	::= { pm1005CntupCvErrCntEntry 3 }


pm1005CntupCvErrCntOverloadPortn OBJECT-TYPE
	SYNTAX  EkiOnOff
	MAX-ACCESS read-only
	STATUS current
	DESCRIPTION
        "
        Client Counter Overload :This
         OID when set indicates a coding 
        violation counter overload on Port
        "
	::= { pm1005CntupCvErrCntEntry 4 }


--- *********************************************************
---     TABLE for the pm1005CntdwCbipCnt articles
--- *********************************************************

pm1005CntdwCbipCntTable OBJECT-TYPE
	SYNTAX  SEQUENCE OF Pm1005CntdwCbipCntEntry
	MAX-ACCESS not-accessible
	STATUS current
	DESCRIPTION
        "
        List of pm1005CntdwCbipCnt Article
        "
	::= { pm1005CntClient 64 }


pm1005CntdwCbipCntEntry OBJECT-TYPE
	SYNTAX Pm1005CntdwCbipCntEntry
	MAX-ACCESS not-accessible
	STATUS current
	DESCRIPTION
        "
        Row definition for the pm1005CntdwCbipCnt 
        table
        "
	INDEX   { pm1005CntdwCbipCntIndex }
	::= { pm1005CntdwCbipCntTable 1 }


Pm1005CntdwCbipCntEntry ::=
	SEQUENCE {
	pm1005CntdwCbipCntIndex
		INTEGER,
	pm1005CntdwCbipCntValuePortn
		Counter32,
	pm1005CntdwCbipCntErrorPortn
		EkiOnOff,
	pm1005CntdwCbipCntOverloadPortn
		EkiOnOff
	}


pm1005CntdwCbipCntIndex OBJECT-TYPE
	SYNTAX  INTEGER(0..128)
	MAX-ACCESS  read-only
	STATUS current
	DESCRIPTION
        "
        Index definition for the pm1005CntdwCbipCnt 
        table
        "
	::= { pm1005CntdwCbipCntEntry 1 }


pm1005CntdwCbipCntValuePortn OBJECT-TYPE
	SYNTAX  Counter32
	MAX-ACCESS read-only
	STATUS current
	DESCRIPTION
        "
        Client Output Errors :This counter 
        is incremented each time a CBIP 
        parity error is detected on the 
        Client output stream  <Help>  This 
        counter gives the number of CBIP 
        errors on the client port
        "
	::= { pm1005CntdwCbipCntEntry 2 }


pm1005CntdwCbipCntErrorPortn OBJECT-TYPE
	SYNTAX  EkiOnOff
	MAX-ACCESS read-only
	STATUS current
	DESCRIPTION
        "
        Client Counter Error :This OID 
        when set indicates the CBIP error 
        counter value is invalid on Port
        "
	::= { pm1005CntdwCbipCntEntry 3 }


pm1005CntdwCbipCntOverloadPortn OBJECT-TYPE
	SYNTAX  EkiOnOff
	MAX-ACCESS read-only
	STATUS current
	DESCRIPTION
        "
        Client CBIP Counter Overload :This 
        OID when set indicates a CBIP error 
        counter overload on Port
        "
	::= { pm1005CntdwCbipCntEntry 4 }


--- *********************************************************
---     TABLE for the pm1005CntdwTimCnt articles
--- *********************************************************

pm1005CntdwTimCntTable OBJECT-TYPE
	SYNTAX  SEQUENCE OF Pm1005CntdwTimCntEntry
	MAX-ACCESS not-accessible
	STATUS current
	DESCRIPTION
        "
        List of pm1005CntdwTimCnt Article
        "
	::= { pm1005CntClient 72 }


pm1005CntdwTimCntEntry OBJECT-TYPE
	SYNTAX Pm1005CntdwTimCntEntry
	MAX-ACCESS not-accessible
	STATUS current
	DESCRIPTION
        "
        Row definition for the pm1005CntdwTimCnt 
        table
        "
	INDEX   { pm1005CntdwTimCntIndex }
	::= { pm1005CntdwTimCntTable 1 }


Pm1005CntdwTimCntEntry ::=
	SEQUENCE {
	pm1005CntdwTimCntIndex
		INTEGER,
	pm1005CntdwTimCntValuePortn
		Counter32,
	pm1005CntdwTimCntErrorPortn
		EkiOnOff,
	pm1005CntdwTimCntOverloadPortn
		EkiOnOff
	}


pm1005CntdwTimCntIndex OBJECT-TYPE
	SYNTAX  INTEGER(0..128)
	MAX-ACCESS  read-only
	STATUS current
	DESCRIPTION
        "
        Index definition for the pm1005CntdwTimCnt 
        table
        "
	::= { pm1005CntdwTimCntEntry 1 }


pm1005CntdwTimCntValuePortn OBJECT-TYPE
	SYNTAX  Counter32
	MAX-ACCESS read-only
	STATUS current
	DESCRIPTION
        "
        Client Downstream Timer Counter 
        :This is the timing counter dedicated 
        to the downstream access counters. 
        It is incremented every 125 us.
        "
	::= { pm1005CntdwTimCntEntry 2 }


pm1005CntdwTimCntErrorPortn OBJECT-TYPE
	SYNTAX  EkiOnOff
	MAX-ACCESS read-only
	STATUS current
	DESCRIPTION
        "
        Client Counter Error :This OID 
        when set indicates the downstream 
        timer counter value is invalid
         on Port
        "
	::= { pm1005CntdwTimCntEntry 3 }


pm1005CntdwTimCntOverloadPortn OBJECT-TYPE
	SYNTAX  EkiOnOff
	MAX-ACCESS read-only
	STATUS current
	DESCRIPTION
        "
        Client Counter Overload :This
         OID when set indicates a downstream 
        timer counter overload on Port
        "
	::= { pm1005CntdwTimCntEntry 4 }


--- *********************************************************
---     TABLE for the pm1005CntdfrmB1ErrCnt articles
--- *********************************************************

pm1005CntdfrmB1ErrCntTable OBJECT-TYPE
	SYNTAX  SEQUENCE OF Pm1005CntdfrmB1ErrCntEntry
	MAX-ACCESS not-accessible
	STATUS current
	DESCRIPTION
        "
        List of pm1005CntdfrmB1ErrCnt
         Article
        "
	::= { pm1005CntLine 152 }


pm1005CntdfrmB1ErrCntEntry OBJECT-TYPE
	SYNTAX Pm1005CntdfrmB1ErrCntEntry
	MAX-ACCESS not-accessible
	STATUS current
	DESCRIPTION
        "
        Row definition for the pm1005CntdfrmB1ErrCnt 
        table
        "
	INDEX   { pm1005CntdfrmB1ErrCntIndex }
	::= { pm1005CntdfrmB1ErrCntTable 1 }


Pm1005CntdfrmB1ErrCntEntry ::=
	SEQUENCE {
	pm1005CntdfrmB1ErrCntIndex
		INTEGER,
	pm1005CntdfrmB1ErrCntValuePortn
		Counter32,
	pm1005CntdfrmB1ErrCntErrorPortn
		EkiOnOff,
	pm1005CntdfrmB1ErrCntOverloadPortn
		EkiOnOff
	}


pm1005CntdfrmB1ErrCntIndex OBJECT-TYPE
	SYNTAX  INTEGER(0..128)
	MAX-ACCESS  read-only
	STATUS current
	DESCRIPTION
        "
        Index definition for the pm1005CntdfrmB1ErrCnt 
        table
        "
	::= { pm1005CntdfrmB1ErrCntEntry 1 }


pm1005CntdfrmB1ErrCntValuePortn OBJECT-TYPE
	SYNTAX  Counter32
	MAX-ACCESS read-only
	STATUS current
	DESCRIPTION
        "
        Line Input B1 Errors :This counter 
        is incremented each time a B1 error 
        is detected on the Deframer input 
        stream.  <Help>  This counter gives 
        the number of B1 errors on the
         line port
        "
	::= { pm1005CntdfrmB1ErrCntEntry 2 }


pm1005CntdfrmB1ErrCntErrorPortn OBJECT-TYPE
	SYNTAX  EkiOnOff
	MAX-ACCESS read-only
	STATUS current
	DESCRIPTION
        "
        Line Counter Error :This OID when 
        set indicates the B1 error counter 
        value is invalid on Port
        "
	::= { pm1005CntdfrmB1ErrCntEntry 3 }


pm1005CntdfrmB1ErrCntOverloadPortn OBJECT-TYPE
	SYNTAX  EkiOnOff
	MAX-ACCESS read-only
	STATUS current
	DESCRIPTION
        "
        Line Counter Overload :This OID 
        when set indicates a B1 error counter 
        overload on Port
        "
	::= { pm1005CntdfrmB1ErrCntEntry 4 }


--- *********************************************************
---     TABLE for the pm1005CntdfrmTimCnt articles
--- *********************************************************

pm1005CntdfrmTimCntTable OBJECT-TYPE
	SYNTAX  SEQUENCE OF Pm1005CntdfrmTimCntEntry
	MAX-ACCESS not-accessible
	STATUS current
	DESCRIPTION
        "
        List of pm1005CntdfrmTimCnt Article
        "
	::= { pm1005CntLine 153 }


pm1005CntdfrmTimCntEntry OBJECT-TYPE
	SYNTAX Pm1005CntdfrmTimCntEntry
	MAX-ACCESS not-accessible
	STATUS current
	DESCRIPTION
        "
        Row definition for the pm1005CntdfrmTimCnt 
        table
        "
	INDEX   { pm1005CntdfrmTimCntIndex }
	::= { pm1005CntdfrmTimCntTable 1 }


Pm1005CntdfrmTimCntEntry ::=
	SEQUENCE {
	pm1005CntdfrmTimCntIndex
		INTEGER,
	pm1005CntdfrmTimCntValuePortn
		Counter32,
	pm1005CntdfrmTimCntErrorPortn
		EkiOnOff,
	pm1005CntdfrmTimCntOverloadPortn
		EkiOnOff
	}


pm1005CntdfrmTimCntIndex OBJECT-TYPE
	SYNTAX  INTEGER(0..128)
	MAX-ACCESS  read-only
	STATUS current
	DESCRIPTION
        "
        Index definition for the pm1005CntdfrmTimCnt 
        table
        "
	::= { pm1005CntdfrmTimCntEntry 1 }


pm1005CntdfrmTimCntValuePortn OBJECT-TYPE
	SYNTAX  Counter32
	MAX-ACCESS read-only
	STATUS current
	DESCRIPTION
        "
        Line Timer Counter :This is the 
        timing counter dedicated to the 
        downstream deframer counters. It 
        is incremented every 125 us.
        "
	::= { pm1005CntdfrmTimCntEntry 2 }


pm1005CntdfrmTimCntErrorPortn OBJECT-TYPE
	SYNTAX  EkiOnOff
	MAX-ACCESS read-only
	STATUS current
	DESCRIPTION
        "
        Line Counter Error :This OID when 
        set indicates the deframer timer 
        counter value is invalid on Port
        "
	::= { pm1005CntdfrmTimCntEntry 3 }


pm1005CntdfrmTimCntOverloadPortn OBJECT-TYPE
	SYNTAX  EkiOnOff
	MAX-ACCESS read-only
	STATUS current
	DESCRIPTION
        "
        Line Counter Overload :This OID 
        when set indicates a deframer timer 
        counter overload on Port
        "
	::= { pm1005CntdfrmTimCntEntry 4 }


--- *********************************************************
---     TABLE for the pm1005CntdfrmPrimLineErrCnt articles
--- *********************************************************

pm1005CntdfrmPrimLineErrCntTable OBJECT-TYPE
	SYNTAX  SEQUENCE OF Pm1005CntdfrmPrimLineErrCntEntry
	MAX-ACCESS not-accessible
	STATUS current
	DESCRIPTION
        "
        List of pm1005CntdfrmPrimLineErrCnt 
        Article
        "
	::= { pm1005CntLine 154 }


pm1005CntdfrmPrimLineErrCntEntry OBJECT-TYPE
	SYNTAX Pm1005CntdfrmPrimLineErrCntEntry
	MAX-ACCESS not-accessible
	STATUS current
	DESCRIPTION
        "
        Row definition for the pm1005CntdfrmPrimLineErrCnt 
        table
        "
	INDEX   { pm1005CntdfrmPrimLineErrCntIndex }
	::= { pm1005CntdfrmPrimLineErrCntTable 1 }


Pm1005CntdfrmPrimLineErrCntEntry ::=
	SEQUENCE {
	pm1005CntdfrmPrimLineErrCntIndex
		INTEGER,
	pm1005CntdfrmPrimLineErrCntValuePortn
		Counter32,
	pm1005CntdfrmPrimLineErrCntErrorPortn
		EkiOnOff,
	pm1005CntdfrmPrimLineErrCntOverloadPortn
		EkiOnOff
	}


pm1005CntdfrmPrimLineErrCntIndex OBJECT-TYPE
	SYNTAX  INTEGER(0..128)
	MAX-ACCESS  read-only
	STATUS current
	DESCRIPTION
        "
        Index definition for the pm1005CntdfrmPrimLineErrCnt 
        table
        "
	::= { pm1005CntdfrmPrimLineErrCntEntry 1 }


pm1005CntdfrmPrimLineErrCntValuePortn OBJECT-TYPE
	SYNTAX  Counter32
	MAX-ACCESS read-only
	STATUS current
	DESCRIPTION
        "
        Line Input FEC Corrected Errors 
        :This counter is incremented each 
        time the FEC is correcting an error 
        on the line input stream.  <Help> 
         This counter gives the number
         of errors corrected by the FEC 
        on the line port
        "
	::= { pm1005CntdfrmPrimLineErrCntEntry 2 }


pm1005CntdfrmPrimLineErrCntErrorPortn OBJECT-TYPE
	SYNTAX  EkiOnOff
	MAX-ACCESS read-only
	STATUS current
	DESCRIPTION
        "
        FEC Counter Error :This bit when 
        set indicates the FEC corrected 
        errors counter value is invalid 
        on Line
        "
	::= { pm1005CntdfrmPrimLineErrCntEntry 3 }


pm1005CntdfrmPrimLineErrCntOverloadPortn OBJECT-TYPE
	SYNTAX  EkiOnOff
	MAX-ACCESS read-only
	STATUS current
	DESCRIPTION
        "
        FEC Counter Overload :This bit 
        when set indicates a FEC corrected 
        errors counter overload on Line
        "
	::= { pm1005CntdfrmPrimLineErrCntEntry 4 }


pm1005CntCountersReset  OBJECT-TYPE
	SYNTAX EkiOnOff
	MAX-ACCESS read-write
	STATUS current
	DESCRIPTION
	"Counters Reset:This OID resets and restarts all the counters"
	::= { pm1005counters  259 }

pm1005CntCountersStop  OBJECT-TYPE
	SYNTAX EkiOnOff
	MAX-ACCESS read-write
	STATUS current
	DESCRIPTION
	"Counters stop:This OID stops all the counters"
	::= { pm1005counters 260 }






--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pm1005MonupRmonByteCnt articles
--- *********************************************************

pm1005MonupRmonByteCntTable OBJECT-TYPE
	SYNTAX  SEQUENCE OF Pm1005MonupRmonByteCntEntry
	MAX-ACCESS not-accessible
	STATUS current
	DESCRIPTION
        "
        List of pm1005MonupRmonByteCnt 
        Article
        "
	::= { pm1005MonClientRmonCounter 16 }


pm1005MonupRmonByteCntEntry OBJECT-TYPE
	SYNTAX Pm1005MonupRmonByteCntEntry
	MAX-ACCESS not-accessible
	STATUS current
	DESCRIPTION
        "
        Row definition for the pm1005MonupRmonByteCnt 
        table
        "
	INDEX   { pm1005MonupRmonByteCntIndex }
	::= { pm1005MonupRmonByteCntTable 1 }


Pm1005MonupRmonByteCntEntry ::=
	SEQUENCE {
	pm1005MonupRmonByteCntIndex
		INTEGER,
	pm1005MonupRmonByteCntValuePortn
		Counter64,
	pm1005MonupRmonByteCntErrorPortn
		EkiOnOff,
	pm1005MonupRmonByteCntOverloadPortn
		EkiOnOff
	}


pm1005MonupRmonByteCntIndex OBJECT-TYPE
	SYNTAX  INTEGER(0..128)
	MAX-ACCESS  read-only
	STATUS current
	DESCRIPTION
        "
        Index definition for the pm1005MonupRmonByteCnt 
        table
        "
	::= { pm1005MonupRmonByteCntEntry 1 }


pm1005MonupRmonByteCntValuePortn OBJECT-TYPE
	SYNTAX  Counter64
	MAX-ACCESS read-only
	STATUS current
	DESCRIPTION
        "
        Client Input Bytes :This counter 
        is increased each time a data byte 
        is received on the client port
        "
	::= { pm1005MonupRmonByteCntEntry 2 }


pm1005MonupRmonByteCntErrorPortn OBJECT-TYPE
	SYNTAX  EkiOnOff
	MAX-ACCESS read-only
	STATUS current
	DESCRIPTION
        "
        Bytes Counter Error :This OID
         when set indicates the Bytes counter 
        value is invalid on clinet port
        "
	::= { pm1005MonupRmonByteCntEntry 3 }


pm1005MonupRmonByteCntOverloadPortn OBJECT-TYPE
	SYNTAX  EkiOnOff
	MAX-ACCESS read-only
	STATUS current
	DESCRIPTION
        "
        Bytes Counter Overload :This OID 
        when set indicates a Bytes counter 
        overload on client port
        "
	::= { pm1005MonupRmonByteCntEntry 4 }


--- *********************************************************
---     TABLE for the pm1005MonupRmonCrcErrorCnt articles
--- *********************************************************

pm1005MonupRmonCrcErrorCntTable OBJECT-TYPE
	SYNTAX  SEQUENCE OF Pm1005MonupRmonCrcErrorCntEntry
	MAX-ACCESS not-accessible
	STATUS current
	DESCRIPTION
        "
        List of pm1005MonupRmonCrcErrorCnt 
        Article
        "
	::= { pm1005MonClientRmonCounter 24 }


pm1005MonupRmonCrcErrorCntEntry OBJECT-TYPE
	SYNTAX Pm1005MonupRmonCrcErrorCntEntry
	MAX-ACCESS not-accessible
	STATUS current
	DESCRIPTION
        "
        Row definition for the pm1005MonupRmonCrcErrorCnt 
        table
        "
	INDEX   { pm1005MonupRmonCrcErrorCntIndex }
	::= { pm1005MonupRmonCrcErrorCntTable 1 }


Pm1005MonupRmonCrcErrorCntEntry ::=
	SEQUENCE {
	pm1005MonupRmonCrcErrorCntIndex
		INTEGER,
	pm1005MonupRmonCrcErrorCntValuePortn
		Counter64,
	pm1005MonupRmonCrcErrorCntErrorPortn
		EkiOnOff,
	pm1005MonupRmonCrcErrorCntOverloadPortn
		EkiOnOff
	}


pm1005MonupRmonCrcErrorCntIndex OBJECT-TYPE
	SYNTAX  INTEGER(0..128)
	MAX-ACCESS  read-only
	STATUS current
	DESCRIPTION
        "
        Index definition for the pm1005MonupRmonCrcErrorCnt 
        table
        "
	::= { pm1005MonupRmonCrcErrorCntEntry 1 }


pm1005MonupRmonCrcErrorCntValuePortn OBJECT-TYPE
	SYNTAX  Counter64
	MAX-ACCESS read-only
	STATUS current
	DESCRIPTION
        "
        Client Input CRC Errors :This
         counter is increased each time 
        a CRC error is detected on the
         client port
        "
	::= { pm1005MonupRmonCrcErrorCntEntry 2 }


pm1005MonupRmonCrcErrorCntErrorPortn OBJECT-TYPE
	SYNTAX  EkiOnOff
	MAX-ACCESS read-only
	STATUS current
	DESCRIPTION
        "
        CRC Errors Counter Error :This 
        OID when set indicates the CRC
         Errors counter value is invalid 
        on clinet port
        "
	::= { pm1005MonupRmonCrcErrorCntEntry 3 }


pm1005MonupRmonCrcErrorCntOverloadPortn OBJECT-TYPE
	SYNTAX  EkiOnOff
	MAX-ACCESS read-only
	STATUS current
	DESCRIPTION
        "
        CRC Errors Counter Overload :This 
        OID when set indicates a CRC Errors 
        counter overload on client port
        "
	::= { pm1005MonupRmonCrcErrorCntEntry 4 }


--- *********************************************************
---     TABLE for the pm1005MonupRmonPacketsCnt articles
--- *********************************************************

pm1005MonupRmonPacketsCntTable OBJECT-TYPE
	SYNTAX  SEQUENCE OF Pm1005MonupRmonPacketsCntEntry
	MAX-ACCESS not-accessible
	STATUS current
	DESCRIPTION
        "
        List of pm1005MonupRmonPacketsCnt 
        Article
        "
	::= { pm1005MonClientRmonCounter 32 }


pm1005MonupRmonPacketsCntEntry OBJECT-TYPE
	SYNTAX Pm1005MonupRmonPacketsCntEntry
	MAX-ACCESS not-accessible
	STATUS current
	DESCRIPTION
        "
        Row definition for the pm1005MonupRmonPacketsCnt 
        table
        "
	INDEX   { pm1005MonupRmonPacketsCntIndex }
	::= { pm1005MonupRmonPacketsCntTable 1 }


Pm1005MonupRmonPacketsCntEntry ::=
	SEQUENCE {
	pm1005MonupRmonPacketsCntIndex
		INTEGER,
	pm1005MonupRmonPacketsCntValuePortn
		Counter64,
	pm1005MonupRmonPacketsCntErrorPortn
		EkiOnOff,
	pm1005MonupRmonPacketsCntOverloadPortn
		EkiOnOff
	}


pm1005MonupRmonPacketsCntIndex OBJECT-TYPE
	SYNTAX  INTEGER(0..128)
	MAX-ACCESS  read-only
	STATUS current
	DESCRIPTION
        "
        Index definition for the pm1005MonupRmonPacketsCnt 
        table
        "
	::= { pm1005MonupRmonPacketsCntEntry 1 }


pm1005MonupRmonPacketsCntValuePortn OBJECT-TYPE
	SYNTAX  Counter64
	MAX-ACCESS read-only
	STATUS current
	DESCRIPTION
        "
        Client Input Packets :This counter 
        is increased each time a packet 
        is received on the client port
        "
	::= { pm1005MonupRmonPacketsCntEntry 2 }


pm1005MonupRmonPacketsCntErrorPortn OBJECT-TYPE
	SYNTAX  EkiOnOff
	MAX-ACCESS read-only
	STATUS current
	DESCRIPTION
        "
        Packets Counter Error :This OID 
        when set indicates the Packets
         counter value is invalid on clinet 
        port
        "
	::= { pm1005MonupRmonPacketsCntEntry 3 }


pm1005MonupRmonPacketsCntOverloadPortn OBJECT-TYPE
	SYNTAX  EkiOnOff
	MAX-ACCESS read-only
	STATUS current
	DESCRIPTION
        "
        Packets Counter Overload :This 
        OID when set indicates a Packets 
        counter overload on client port
        "
	::= { pm1005MonupRmonPacketsCntEntry 4 }


--- *********************************************************
---     TABLE for the pm1005MonupRmonBroadcastCnt articles
--- *********************************************************

pm1005MonupRmonBroadcastCntTable OBJECT-TYPE
	SYNTAX  SEQUENCE OF Pm1005MonupRmonBroadcastCntEntry
	MAX-ACCESS not-accessible
	STATUS current
	DESCRIPTION
        "
        List of pm1005MonupRmonBroadcastCnt 
        Article
        "
	::= { pm1005MonClientRmonCounter 40 }


pm1005MonupRmonBroadcastCntEntry OBJECT-TYPE
	SYNTAX Pm1005MonupRmonBroadcastCntEntry
	MAX-ACCESS not-accessible
	STATUS current
	DESCRIPTION
        "
        Row definition for the pm1005MonupRmonBroadcastCnt 
        table
        "
	INDEX   { pm1005MonupRmonBroadcastCntIndex }
	::= { pm1005MonupRmonBroadcastCntTable 1 }


Pm1005MonupRmonBroadcastCntEntry ::=
	SEQUENCE {
	pm1005MonupRmonBroadcastCntIndex
		INTEGER,
	pm1005MonupRmonBroadcastCntValuePortn
		Counter64,
	pm1005MonupRmonBroadcastCntErrorPortn
		EkiOnOff,
	pm1005MonupRmonBroadcastCntOverloadPortn
		EkiOnOff
	}


pm1005MonupRmonBroadcastCntIndex OBJECT-TYPE
	SYNTAX  INTEGER(0..128)
	MAX-ACCESS  read-only
	STATUS current
	DESCRIPTION
        "
        Index definition for the pm1005MonupRmonBroadcastCnt 
        table
        "
	::= { pm1005MonupRmonBroadcastCntEntry 1 }


pm1005MonupRmonBroadcastCntValuePortn OBJECT-TYPE
	SYNTAX  Counter64
	MAX-ACCESS read-only
	STATUS current
	DESCRIPTION
        "
        Client Input Broadcast Packets 
        :This counter is increased each 
        time a broadcast packet is received 
        on the client port
        "
	::= { pm1005MonupRmonBroadcastCntEntry 2 }


pm1005MonupRmonBroadcastCntErrorPortn OBJECT-TYPE
	SYNTAX  EkiOnOff
	MAX-ACCESS read-only
	STATUS current
	DESCRIPTION
        "
        Broadcast Counter Error :This
         OID when set indicates the Broadcast 
        counter value is invalid on clinet 
        port
        "
	::= { pm1005MonupRmonBroadcastCntEntry 3 }


pm1005MonupRmonBroadcastCntOverloadPortn OBJECT-TYPE
	SYNTAX  EkiOnOff
	MAX-ACCESS read-only
	STATUS current
	DESCRIPTION
        "
        Broadcast Counter Overload :This 
        OID when set indicates a Broadcast 
        counter overload on client port
        "
	::= { pm1005MonupRmonBroadcastCntEntry 4 }


--- *********************************************************
---     TABLE for the pm1005MonupRmonMulticastCnt articles
--- *********************************************************

pm1005MonupRmonMulticastCntTable OBJECT-TYPE
	SYNTAX  SEQUENCE OF Pm1005MonupRmonMulticastCntEntry
	MAX-ACCESS not-accessible
	STATUS current
	DESCRIPTION
        "
        List of pm1005MonupRmonMulticastCnt 
        Article
        "
	::= { pm1005MonClientRmonCounter 48 }


pm1005MonupRmonMulticastCntEntry OBJECT-TYPE
	SYNTAX Pm1005MonupRmonMulticastCntEntry
	MAX-ACCESS not-accessible
	STATUS current
	DESCRIPTION
        "
        Row definition for the pm1005MonupRmonMulticastCnt 
        table
        "
	INDEX   { pm1005MonupRmonMulticastCntIndex }
	::= { pm1005MonupRmonMulticastCntTable 1 }


Pm1005MonupRmonMulticastCntEntry ::=
	SEQUENCE {
	pm1005MonupRmonMulticastCntIndex
		INTEGER,
	pm1005MonupRmonMulticastCntValuePortn
		Counter64,
	pm1005MonupRmonMulticastCntErrorPortn
		EkiOnOff,
	pm1005MonupRmonMulticastCntOverloadPortn
		EkiOnOff
	}


pm1005MonupRmonMulticastCntIndex OBJECT-TYPE
	SYNTAX  INTEGER(0..128)
	MAX-ACCESS  read-only
	STATUS current
	DESCRIPTION
        "
        Index definition for the pm1005MonupRmonMulticastCnt 
        table
        "
	::= { pm1005MonupRmonMulticastCntEntry 1 }


pm1005MonupRmonMulticastCntValuePortn OBJECT-TYPE
	SYNTAX  Counter64
	MAX-ACCESS read-only
	STATUS current
	DESCRIPTION
        "
        Client Input Multicast Packets 
        :This counter is increased each 
        time a Multicast packet is received 
        on the client port
        "
	::= { pm1005MonupRmonMulticastCntEntry 2 }


pm1005MonupRmonMulticastCntErrorPortn OBJECT-TYPE
	SYNTAX  EkiOnOff
	MAX-ACCESS read-only
	STATUS current
	DESCRIPTION
        "
        Multicast Counter Error :This
         OID when set indicates the Multicast 
        counter value is invalid on clinet 
        port
        "
	::= { pm1005MonupRmonMulticastCntEntry 3 }


pm1005MonupRmonMulticastCntOverloadPortn OBJECT-TYPE
	SYNTAX  EkiOnOff
	MAX-ACCESS read-only
	STATUS current
	DESCRIPTION
        "
        Multicast Counter Overload :This 
        OID when set indicates a Multicast 
        counter overload on client port
        "
	::= { pm1005MonupRmonMulticastCntEntry 4 }


pm1005MonCountersReset  OBJECT-TYPE
	SYNTAX EkiOnOff
	MAX-ACCESS read-write
	STATUS current
	DESCRIPTION
	"RMON Counters Reset:This OID resets and restarts all the RMON counters"
	::= { pm1005MonRmon   359 }

pm1005MonCountersStop  OBJECT-TYPE
	SYNTAX EkiOnOff
	MAX-ACCESS read-write
	STATUS current
	DESCRIPTION
	"RMON Counters stop:This OID stops all the RMON counters"
	::= { pm1005MonRmon  360 }






--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm1005Mesrsynth0 OBJECT-TYPE
	  SYNTAX EkiMeasureType
	  MAX-ACCESS read-only
	  STATUS deprecated
	  DESCRIPTION
        "
        Not Used :This OID gives the unit 
        used on AUX1 measurement of XFP#1 
         (Unit = )
        "
	  ::= { pm1005MesrOther 0 }



pm1005Mesrsynth1 OBJECT-TYPE
	  SYNTAX EkiMeasureType
	  MAX-ACCESS read-only
	  STATUS deprecated
	  DESCRIPTION
        "
        Not Used :This OID gives the unit 
        used on AUX2 measurement of XFP#1 
         (Unit = )
        "
	  ::= { pm1005MesrOther 1 }



--- *********************************************************
---     TABLE for the pm1005MesrtempMeas articles
--- *********************************************************

pm1005MesrtempMeasTable OBJECT-TYPE
	SYNTAX  SEQUENCE OF Pm1005MesrtempMeasEntry
	MAX-ACCESS not-accessible
	STATUS current
	DESCRIPTION
        "
        List of pm1005MesrtempMeas Article
        "
	::= { pm1005MesrClient 16 }


pm1005MesrtempMeasEntry OBJECT-TYPE
	SYNTAX Pm1005MesrtempMeasEntry
	MAX-ACCESS not-accessible
	STATUS current
	DESCRIPTION
        "
        Row definition for the pm1005MesrtempMeas 
        table
        "
	INDEX   { pm1005MesrtempMeasIndex }
	::= { pm1005MesrtempMeasTable 1 }


Pm1005MesrtempMeasEntry ::=
	SEQUENCE {
	pm1005MesrtempMeasIndex
		INTEGER,
	pm1005MesrtempMeasPortn
		INTEGER 
	}


pm1005MesrtempMeasIndex OBJECT-TYPE
	SYNTAX  INTEGER(0..128)
	MAX-ACCESS  read-only
	STATUS current
	DESCRIPTION
        "
        Index definition for the pm1005MesrtempMeas 
        table
        "
	::= { pm1005MesrtempMeasEntry 1 }


pm1005MesrtempMeasPortn OBJECT-TYPE
	SYNTAX  INTEGER (0..65535)
	MAX-ACCESS read-only
	STATUS current
	DESCRIPTION
        "
        Client SFP Temperature :This OID 
        gives the temperature value of
         the SFP plugged in port, read
         from the DDM (Digital Diagnostic 
        Monitoring) (Temperature = AV/256) 
         (Unit = C)  <Help>  This measure 
        gives the temperature of the client 
        transceiver
        "
	::= { pm1005MesrtempMeasEntry 2 }


--- *********************************************************
---     TABLE for the pm1005MesrvoltMeas articles
--- *********************************************************

pm1005MesrvoltMeasTable OBJECT-TYPE
	SYNTAX  SEQUENCE OF Pm1005MesrvoltMeasEntry
	MAX-ACCESS not-accessible
	STATUS current
	DESCRIPTION
        "
        List of pm1005MesrvoltMeas Article
        "
	::= { pm1005MesrClient 24 }


pm1005MesrvoltMeasEntry OBJECT-TYPE
	SYNTAX Pm1005MesrvoltMeasEntry
	MAX-ACCESS not-accessible
	STATUS current
	DESCRIPTION
        "
        Row definition for the pm1005MesrvoltMeas 
        table
        "
	INDEX   { pm1005MesrvoltMeasIndex }
	::= { pm1005MesrvoltMeasTable 1 }


Pm1005MesrvoltMeasEntry ::=
	SEQUENCE {
	pm1005MesrvoltMeasIndex
		INTEGER,
	pm1005MesrvoltMeasPortn
		INTEGER 
	}


pm1005MesrvoltMeasIndex OBJECT-TYPE
	SYNTAX  INTEGER(0..128)
	MAX-ACCESS  read-only
	STATUS current
	DESCRIPTION
        "
        Index definition for the pm1005MesrvoltMeas 
        table
        "
	::= { pm1005MesrvoltMeasEntry 1 }


pm1005MesrvoltMeasPortn OBJECT-TYPE
	SYNTAX  INTEGER (0..65535)
	MAX-ACCESS read-only
	STATUS current
	DESCRIPTION
        "
        Client SFP Power Supply :This
         OID gives the 3V3 voltage value 
        of the SFP plugged into port, read 
        from the DDM (Digital Diagnostic 
        Monitoring) (Voltage = AV/10000) 
        (Unit = V)  <Help>  This measure 
        gives the 3V3 voltage of the client 
        transceiver
        "
	::= { pm1005MesrvoltMeasEntry 2 }


--- *********************************************************
---     TABLE for the pm1005MesrbiasMeas articles
--- *********************************************************

pm1005MesrbiasMeasTable OBJECT-TYPE
	SYNTAX  SEQUENCE OF Pm1005MesrbiasMeasEntry
	MAX-ACCESS not-accessible
	STATUS current
	DESCRIPTION
        "
        List of pm1005MesrbiasMeas Article
        "
	::= { pm1005MesrClient 32 }


pm1005MesrbiasMeasEntry OBJECT-TYPE
	SYNTAX Pm1005MesrbiasMeasEntry
	MAX-ACCESS not-accessible
	STATUS current
	DESCRIPTION
        "
        Row definition for the pm1005MesrbiasMeas 
        table
        "
	INDEX   { pm1005MesrbiasMeasIndex }
	::= { pm1005MesrbiasMeasTable 1 }


Pm1005MesrbiasMeasEntry ::=
	SEQUENCE {
	pm1005MesrbiasMeasIndex
		INTEGER,
	pm1005MesrbiasMeasPortn
		INTEGER 
	}


pm1005MesrbiasMeasIndex OBJECT-TYPE
	SYNTAX  INTEGER(0..128)
	MAX-ACCESS  read-only
	STATUS current
	DESCRIPTION
        "
        Index definition for the pm1005MesrbiasMeas 
        table
        "
	::= { pm1005MesrbiasMeasEntry 1 }


pm1005MesrbiasMeasPortn OBJECT-TYPE
	SYNTAX  INTEGER (0..65535)
	MAX-ACCESS read-only
	STATUS current
	DESCRIPTION
        "
        Client SFP Laser Bias :This OID 
        gives the bias value of the SFP 
        plugged into port, read from the 
        DDM (Digital Diagnostic Monitoring) 
         (Bias = AV/500) (Unit = mA)  <Help> 
         This measure gives the bias of 
        the client transceiver
        "
	::= { pm1005MesrbiasMeasEntry 2 }


--- *********************************************************
---     TABLE for the pm1005MesrtxpwrMeas articles
--- *********************************************************

pm1005MesrtxpwrMeasTable OBJECT-TYPE
	SYNTAX  SEQUENCE OF Pm1005MesrtxpwrMeasEntry
	MAX-ACCESS not-accessible
	STATUS current
	DESCRIPTION
        "
        List of pm1005MesrtxpwrMeas Article
        "
	::= { pm1005MesrClient 40 }


pm1005MesrtxpwrMeasEntry OBJECT-TYPE
	SYNTAX Pm1005MesrtxpwrMeasEntry
	MAX-ACCESS not-accessible
	STATUS current
	DESCRIPTION
        "
        Row definition for the pm1005MesrtxpwrMeas 
        table
        "
	INDEX   { pm1005MesrtxpwrMeasIndex }
	::= { pm1005MesrtxpwrMeasTable 1 }


Pm1005MesrtxpwrMeasEntry ::=
	SEQUENCE {
	pm1005MesrtxpwrMeasIndex
		INTEGER,
	pm1005MesrtxpwrMeasPortn
		INTEGER 
	}


pm1005MesrtxpwrMeasIndex OBJECT-TYPE
	SYNTAX  INTEGER(0..128)
	MAX-ACCESS  read-only
	STATUS current
	DESCRIPTION
        "
        Index definition for the pm1005MesrtxpwrMeas 
        table
        "
	::= { pm1005MesrtxpwrMeasEntry 1 }


pm1005MesrtxpwrMeasPortn OBJECT-TYPE
	SYNTAX  INTEGER (0..65535)
	MAX-ACCESS read-only
	STATUS current
	DESCRIPTION
        "
        Client SFP Tx Power :This OID
         gives the transmit power value 
        of the SFP plugged into port, read 
        from the DDM (Digital Diagnostic 
        Monitoring) (Power = 10*log(AV)-40) 
        (Unit = dBm)  <Help>  This measure 
        gives the Tx optical power of the 
        client transceiver
        "
	::= { pm1005MesrtxpwrMeasEntry 2 }


--- *********************************************************
---     TABLE for the pm1005MesrrxpwrMeas articles
--- *********************************************************

pm1005MesrrxpwrMeasTable OBJECT-TYPE
	SYNTAX  SEQUENCE OF Pm1005MesrrxpwrMeasEntry
	MAX-ACCESS not-accessible
	STATUS current
	DESCRIPTION
        "
        List of pm1005MesrrxpwrMeas Article
        "
	::= { pm1005MesrClient 48 }


pm1005MesrrxpwrMeasEntry OBJECT-TYPE
	SYNTAX Pm1005MesrrxpwrMeasEntry
	MAX-ACCESS not-accessible
	STATUS current
	DESCRIPTION
        "
        Row definition for the pm1005MesrrxpwrMeas 
        table
        "
	INDEX   { pm1005MesrrxpwrMeasIndex }
	::= { pm1005MesrrxpwrMeasTable 1 }


Pm1005MesrrxpwrMeasEntry ::=
	SEQUENCE {
	pm1005MesrrxpwrMeasIndex
		INTEGER,
	pm1005MesrrxpwrMeasPortn
		INTEGER 
	}


pm1005MesrrxpwrMeasIndex OBJECT-TYPE
	SYNTAX  INTEGER(0..128)
	MAX-ACCESS  read-only
	STATUS current
	DESCRIPTION
        "
        Index definition for the pm1005MesrrxpwrMeas 
        table
        "
	::= { pm1005MesrrxpwrMeasEntry 1 }


pm1005MesrrxpwrMeasPortn OBJECT-TYPE
	SYNTAX  INTEGER (0..65535)
	MAX-ACCESS read-only
	STATUS current
	DESCRIPTION
        "
        Client SFP Rx Power :This OID
         gives the receive power value
         of the SFP plugged into port,
         read in the DDM (Digital Diagnostic 
        Monitoring)  (Power = 10*log(AV)-40) 
        (Unit = dBm)  <Help>  This measure 
        gives the Rx optical power of the 
        client transceiver
        "
	::= { pm1005MesrrxpwrMeasEntry 2 }


--- *********************************************************
---     TABLE for the pm1005Mesrxfp1LxModTempMeas articles
--- *********************************************************

pm1005Mesrxfp1LxModTempMeasTable OBJECT-TYPE
	SYNTAX  SEQUENCE OF Pm1005Mesrxfp1LxModTempMeasEntry
	MAX-ACCESS not-accessible
	STATUS current
	DESCRIPTION
        "
        List of pm1005Mesrxfp1LxModTempMeas 
        Article
        "
	::= { pm1005MesrLine 208 }


pm1005Mesrxfp1LxModTempMeasEntry OBJECT-TYPE
	SYNTAX Pm1005Mesrxfp1LxModTempMeasEntry
	MAX-ACCESS not-accessible
	STATUS current
	DESCRIPTION
        "
        Row definition for the pm1005Mesrxfp1LxModTempMeas 
        table
        "
	INDEX   { pm1005Mesrxfp1LxModTempMeasIndex }
	::= { pm1005Mesrxfp1LxModTempMeasTable 1 }


Pm1005Mesrxfp1LxModTempMeasEntry ::=
	SEQUENCE {
	pm1005Mesrxfp1LxModTempMeasIndex
		INTEGER,
	pm1005Mesrxfp1LxModTempMeasPortn
		INTEGER 
	}


pm1005Mesrxfp1LxModTempMeasIndex OBJECT-TYPE
	SYNTAX  INTEGER(0..128)
	MAX-ACCESS  read-only
	STATUS current
	DESCRIPTION
        "
        Index definition for the pm1005Mesrxfp1LxModTempMeas 
        table
        "
	::= { pm1005Mesrxfp1LxModTempMeasEntry 1 }


pm1005Mesrxfp1LxModTempMeasPortn OBJECT-TYPE
	SYNTAX  INTEGER (0..65535)
	MAX-ACCESS read-only
	STATUS current
	DESCRIPTION
        "
        Line Optical Module Temperature 
        :This OID gives the temperature 
        of the XFP or OTX plugged in line#n, 
        read from the DDM (Digital Diagnostic 
        Monitoring) (Temperature = AV/256) 
        (Unit = C)  <Help>  This measure 
        gives the temperature of the line 
        transceiver
        "
	::= { pm1005Mesrxfp1LxModTempMeasEntry 2 }


--- *********************************************************
---     TABLE for the pm1005Mesrxfp1Reserved articles
--- *********************************************************

pm1005Mesrxfp1ReservedTable OBJECT-TYPE
	SYNTAX  SEQUENCE OF Pm1005Mesrxfp1ReservedEntry
	MAX-ACCESS not-accessible
	STATUS deprecated
	DESCRIPTION
        "
        List of pm1005Mesrxfp1Reserved 
        Article
        "
	::= { pm1005MesrLine 209 }


pm1005Mesrxfp1ReservedEntry OBJECT-TYPE
	SYNTAX Pm1005Mesrxfp1ReservedEntry
	MAX-ACCESS not-accessible
	STATUS deprecated
	DESCRIPTION
        "
        Row definition for the pm1005Mesrxfp1Reserved 
        table
        "
	INDEX   { pm1005Mesrxfp1ReservedIndex }
	::= { pm1005Mesrxfp1ReservedTable 1 }


Pm1005Mesrxfp1ReservedEntry ::=
	SEQUENCE {
	pm1005Mesrxfp1ReservedIndex
		INTEGER,
	pm1005Mesrxfp1ReservedPortn
		INTEGER 
	}


pm1005Mesrxfp1ReservedIndex OBJECT-TYPE
	SYNTAX  INTEGER(0..128)
	MAX-ACCESS  read-only
	STATUS deprecated
	DESCRIPTION
        "
        Index definition for the pm1005Mesrxfp1Reserved 
        table
        "
	::= { pm1005Mesrxfp1ReservedEntry 1 }


pm1005Mesrxfp1ReservedPortn OBJECT-TYPE
	SYNTAX  INTEGER (0..65535)
	MAX-ACCESS read-only
	STATUS deprecated
	DESCRIPTION
        "
        Not Used :Reserved
        "
	::= { pm1005Mesrxfp1ReservedEntry 2 }


--- *********************************************************
---     TABLE for the pm1005Mesrxfp1LoBiasCurrentMeas articles
--- *********************************************************

pm1005Mesrxfp1LoBiasCurrentMeasTable OBJECT-TYPE
	SYNTAX  SEQUENCE OF Pm1005Mesrxfp1LoBiasCurrentMeasEntry
	MAX-ACCESS not-accessible
	STATUS current
	DESCRIPTION
        "
        List of pm1005Mesrxfp1LoBiasCurrentMeas 
        Article
        "
	::= { pm1005MesrLine 210 }


pm1005Mesrxfp1LoBiasCurrentMeasEntry OBJECT-TYPE
	SYNTAX Pm1005Mesrxfp1LoBiasCurrentMeasEntry
	MAX-ACCESS not-accessible
	STATUS current
	DESCRIPTION
        "
        Row definition for the pm1005Mesrxfp1LoBiasCurrentMeas 
        table
        "
	INDEX   { pm1005Mesrxfp1LoBiasCurrentMeasIndex }
	::= { pm1005Mesrxfp1LoBiasCurrentMeasTable 1 }


Pm1005Mesrxfp1LoBiasCurrentMeasEntry ::=
	SEQUENCE {
	pm1005Mesrxfp1LoBiasCurrentMeasIndex
		INTEGER,
	pm1005Mesrxfp1LoBiasCurrentMeasPortn
		INTEGER 
	}


pm1005Mesrxfp1LoBiasCurrentMeasIndex OBJECT-TYPE
	SYNTAX  INTEGER(0..128)
	MAX-ACCESS  read-only
	STATUS current
	DESCRIPTION
        "
        Index definition for the pm1005Mesrxfp1LoBiasCurrentMeas 
        table
        "
	::= { pm1005Mesrxfp1LoBiasCurrentMeasEntry 1 }


pm1005Mesrxfp1LoBiasCurrentMeasPortn OBJECT-TYPE
	SYNTAX  INTEGER (0..65535)
	MAX-ACCESS read-only
	STATUS current
	DESCRIPTION
        "
        Line Optical Module Laser Bias 
        :This OID gives the bias value
         of the XFP or OTX plugged in line 
        #n, read from the DDM (Digital
         Diagnostic Monitoring)  (Bias
         = AV/500)  (Unit = mA)  <Help> 
         This measure gives the bias of 
        the line transceiver
        "
	::= { pm1005Mesrxfp1LoBiasCurrentMeasEntry 2 }


--- *********************************************************
---     TABLE for the pm1005Mesrxfp1LoTxPowerMeas articles
--- *********************************************************

pm1005Mesrxfp1LoTxPowerMeasTable OBJECT-TYPE
	SYNTAX  SEQUENCE OF Pm1005Mesrxfp1LoTxPowerMeasEntry
	MAX-ACCESS not-accessible
	STATUS current
	DESCRIPTION
        "
        List of pm1005Mesrxfp1LoTxPowerMeas 
        Article
        "
	::= { pm1005MesrLine 211 }


pm1005Mesrxfp1LoTxPowerMeasEntry OBJECT-TYPE
	SYNTAX Pm1005Mesrxfp1LoTxPowerMeasEntry
	MAX-ACCESS not-accessible
	STATUS current
	DESCRIPTION
        "
        Row definition for the pm1005Mesrxfp1LoTxPowerMeas 
        table
        "
	INDEX   { pm1005Mesrxfp1LoTxPowerMeasIndex }
	::= { pm1005Mesrxfp1LoTxPowerMeasTable 1 }


Pm1005Mesrxfp1LoTxPowerMeasEntry ::=
	SEQUENCE {
	pm1005Mesrxfp1LoTxPowerMeasIndex
		INTEGER,
	pm1005Mesrxfp1LoTxPowerMeasPortn
		INTEGER 
	}


pm1005Mesrxfp1LoTxPowerMeasIndex OBJECT-TYPE
	SYNTAX  INTEGER(0..128)
	MAX-ACCESS  read-only
	STATUS current
	DESCRIPTION
        "
        Index definition for the pm1005Mesrxfp1LoTxPowerMeas 
        table
        "
	::= { pm1005Mesrxfp1LoTxPowerMeasEntry 1 }


pm1005Mesrxfp1LoTxPowerMeasPortn OBJECT-TYPE
	SYNTAX  INTEGER (0..65535)
	MAX-ACCESS read-only
	STATUS current
	DESCRIPTION
        "
        Line Optical Module Tx Power :This 
        OID gives the transmit power value 
        of the XFP or OTX plugged in line 
        #n, read from the DDM (Digital
           Diagnostic Monitoring) (Power 
        = 10*log(AV)-40)  (Unit = dBm)
          <Help>  This measure gives the 
        Tx optical power of the line transceiver
        "
	::= { pm1005Mesrxfp1LoTxPowerMeasEntry 2 }


--- *********************************************************
---     TABLE for the pm1005Mesrxfp1LiRxPowerMeas articles
--- *********************************************************

pm1005Mesrxfp1LiRxPowerMeasTable OBJECT-TYPE
	SYNTAX  SEQUENCE OF Pm1005Mesrxfp1LiRxPowerMeasEntry
	MAX-ACCESS not-accessible
	STATUS current
	DESCRIPTION
        "
        List of pm1005Mesrxfp1LiRxPowerMeas 
        Article
        "
	::= { pm1005MesrLine 212 }


pm1005Mesrxfp1LiRxPowerMeasEntry OBJECT-TYPE
	SYNTAX Pm1005Mesrxfp1LiRxPowerMeasEntry
	MAX-ACCESS not-accessible
	STATUS current
	DESCRIPTION
        "
        Row definition for the pm1005Mesrxfp1LiRxPowerMeas 
        table
        "
	INDEX   { pm1005Mesrxfp1LiRxPowerMeasIndex }
	::= { pm1005Mesrxfp1LiRxPowerMeasTable 1 }


Pm1005Mesrxfp1LiRxPowerMeasEntry ::=
	SEQUENCE {
	pm1005Mesrxfp1LiRxPowerMeasIndex
		INTEGER,
	pm1005Mesrxfp1LiRxPowerMeasPortn
		INTEGER 
	}


pm1005Mesrxfp1LiRxPowerMeasIndex OBJECT-TYPE
	SYNTAX  INTEGER(0..128)
	MAX-ACCESS  read-only
	STATUS current
	DESCRIPTION
        "
        Index definition for the pm1005Mesrxfp1LiRxPowerMeas 
        table
        "
	::= { pm1005Mesrxfp1LiRxPowerMeasEntry 1 }


pm1005Mesrxfp1LiRxPowerMeasPortn OBJECT-TYPE
	SYNTAX  INTEGER (0..65535)
	MAX-ACCESS read-only
	STATUS current
	DESCRIPTION
        "
        Line Optical Module Rx Power :This 
        OID gives the receive power value 
        of the XFP or OTX plugged in line 
        #n, read from the DDM (Digital
         Diagnostic Monitoring) (Power
         = 10*log(AV)-40) (Unit = dBm)
          <Help>  This measure gives the 
        Rx optical power of the line transceiver
        "
	::= { pm1005Mesrxfp1LiRxPowerMeasEntry 2 }


--- *********************************************************
---     TABLE for the pm1005Mesrxfp1LxAux1Meas articles
--- *********************************************************

pm1005Mesrxfp1LxAux1MeasTable OBJECT-TYPE
	SYNTAX  SEQUENCE OF Pm1005Mesrxfp1LxAux1MeasEntry
	MAX-ACCESS not-accessible
	STATUS deprecated
	DESCRIPTION
        "
        List of pm1005Mesrxfp1LxAux1Meas 
        Article
        "
	::= { pm1005MesrLine 213 }


pm1005Mesrxfp1LxAux1MeasEntry OBJECT-TYPE
	SYNTAX Pm1005Mesrxfp1LxAux1MeasEntry
	MAX-ACCESS not-accessible
	STATUS deprecated
	DESCRIPTION
        "
        Row definition for the pm1005Mesrxfp1LxAux1Meas 
        table
        "
	INDEX   { pm1005Mesrxfp1LxAux1MeasIndex }
	::= { pm1005Mesrxfp1LxAux1MeasTable 1 }


Pm1005Mesrxfp1LxAux1MeasEntry ::=
	SEQUENCE {
	pm1005Mesrxfp1LxAux1MeasIndex
		INTEGER,
	pm1005Mesrxfp1LxAux1MeasPortn
		INTEGER 
	}


pm1005Mesrxfp1LxAux1MeasIndex OBJECT-TYPE
	SYNTAX  INTEGER(0..128)
	MAX-ACCESS  read-only
	STATUS deprecated
	DESCRIPTION
        "
        Index definition for the pm1005Mesrxfp1LxAux1Meas 
        table
        "
	::= { pm1005Mesrxfp1LxAux1MeasEntry 1 }


pm1005Mesrxfp1LxAux1MeasPortn OBJECT-TYPE
	SYNTAX  INTEGER (0..65535)
	MAX-ACCESS read-only
	STATUS deprecated
	DESCRIPTION
        "
        Not Used :This OID gives the receive 
        power value read in the DDM (Digital 
        Diagnostic Monitoring) of the XFP 
        or OTX plugged in line #n (Unit 
        = ?)
        "
	::= { pm1005Mesrxfp1LxAux1MeasEntry 2 }


--- *********************************************************
---     TABLE for the pm1005Mesrxfp1LxAux2Meas articles
--- *********************************************************

pm1005Mesrxfp1LxAux2MeasTable OBJECT-TYPE
	SYNTAX  SEQUENCE OF Pm1005Mesrxfp1LxAux2MeasEntry
	MAX-ACCESS not-accessible
	STATUS deprecated
	DESCRIPTION
        "
        List of pm1005Mesrxfp1LxAux2Meas 
        Article
        "
	::= { pm1005MesrLine 214 }


pm1005Mesrxfp1LxAux2MeasEntry OBJECT-TYPE
	SYNTAX Pm1005Mesrxfp1LxAux2MeasEntry
	MAX-ACCESS not-accessible
	STATUS deprecated
	DESCRIPTION
        "
        Row definition for the pm1005Mesrxfp1LxAux2Meas 
        table
        "
	INDEX   { pm1005Mesrxfp1LxAux2MeasIndex }
	::= { pm1005Mesrxfp1LxAux2MeasTable 1 }


Pm1005Mesrxfp1LxAux2MeasEntry ::=
	SEQUENCE {
	pm1005Mesrxfp1LxAux2MeasIndex
		INTEGER,
	pm1005Mesrxfp1LxAux2MeasPortn
		INTEGER 
	}


pm1005Mesrxfp1LxAux2MeasIndex OBJECT-TYPE
	SYNTAX  INTEGER(0..128)
	MAX-ACCESS  read-only
	STATUS deprecated
	DESCRIPTION
        "
        Index definition for the pm1005Mesrxfp1LxAux2Meas 
        table
        "
	::= { pm1005Mesrxfp1LxAux2MeasEntry 1 }


pm1005Mesrxfp1LxAux2MeasPortn OBJECT-TYPE
	SYNTAX  INTEGER (0..65535)
	MAX-ACCESS read-only
	STATUS deprecated
	DESCRIPTION
        "
        Not Used :This OID gives the receive 
        power value read in the DDM (Digital 
        Diagnostic Monitoring) of the XFP 
        or OTX plugged in line #n (Unit 
        = ?)
        "
	::= { pm1005Mesrxfp1LxAux2MeasEntry 2 }


--- *********************************************************
---     TABLE for the pm1005Mesrotx1Aging articles
--- *********************************************************

pm1005Mesrotx1AgingTable OBJECT-TYPE
	SYNTAX  SEQUENCE OF Pm1005Mesrotx1AgingEntry
	MAX-ACCESS not-accessible
	STATUS current
	DESCRIPTION
        "
        List of pm1005Mesrotx1Aging Article
        "
	::= { pm1005MesrLine 224 }


pm1005Mesrotx1AgingEntry OBJECT-TYPE
	SYNTAX Pm1005Mesrotx1AgingEntry
	MAX-ACCESS not-accessible
	STATUS current
	DESCRIPTION
        "
        Row definition for the pm1005Mesrotx1Aging 
        table
        "
	INDEX   { pm1005Mesrotx1AgingIndex }
	::= { pm1005Mesrotx1AgingTable 1 }


Pm1005Mesrotx1AgingEntry ::=
	SEQUENCE {
	pm1005Mesrotx1AgingIndex
		INTEGER,
	pm1005Mesrotx1AgingPortn
		INTEGER 
	}


pm1005Mesrotx1AgingIndex OBJECT-TYPE
	SYNTAX  INTEGER(0..128)
	MAX-ACCESS  read-only
	STATUS current
	DESCRIPTION
        "
        Index definition for the pm1005Mesrotx1Aging 
        table
        "
	::= { pm1005Mesrotx1AgingEntry 1 }


pm1005Mesrotx1AgingPortn OBJECT-TYPE
	SYNTAX  INTEGER (0..65535)
	MAX-ACCESS read-only
	STATUS current
	DESCRIPTION
        "
        Line OTX TLH Aging :This OID gives 
        the aging of the Line OTX TLH,
         read from the DDM (Digital Diagnostic 
        Monitoring) (Unit = %)  <Help>
          This measure gives the aging
         of the Line OTX TLH
        "
	::= { pm1005Mesrotx1AgingEntry 2 }


--- *********************************************************
---     TABLE for the pm1005Mesrotx1LaserTemperature articles
--- *********************************************************

pm1005Mesrotx1LaserTemperatureTable OBJECT-TYPE
	SYNTAX  SEQUENCE OF Pm1005Mesrotx1LaserTemperatureEntry
	MAX-ACCESS not-accessible
	STATUS deprecated
	DESCRIPTION
        "
        List of pm1005Mesrotx1LaserTemperature 
        Article
        "
	::= { pm1005MesrLine 225 }


pm1005Mesrotx1LaserTemperatureEntry OBJECT-TYPE
	SYNTAX Pm1005Mesrotx1LaserTemperatureEntry
	MAX-ACCESS not-accessible
	STATUS deprecated
	DESCRIPTION
        "
        Row definition for the pm1005Mesrotx1LaserTemperature 
        table
        "
	INDEX   { pm1005Mesrotx1LaserTemperatureIndex }
	::= { pm1005Mesrotx1LaserTemperatureTable 1 }


Pm1005Mesrotx1LaserTemperatureEntry ::=
	SEQUENCE {
	pm1005Mesrotx1LaserTemperatureIndex
		INTEGER,
	pm1005Mesrotx1LaserTemperaturePortn
		INTEGER 
	}


pm1005Mesrotx1LaserTemperatureIndex OBJECT-TYPE
	SYNTAX  INTEGER(0..128)
	MAX-ACCESS  read-only
	STATUS deprecated
	DESCRIPTION
        "
        Index definition for the pm1005Mesrotx1LaserTemperature 
        table
        "
	::= { pm1005Mesrotx1LaserTemperatureEntry 1 }


pm1005Mesrotx1LaserTemperaturePortn OBJECT-TYPE
	SYNTAX  INTEGER (0..65535)
	MAX-ACCESS read-only
	STATUS deprecated
	DESCRIPTION
        "
        Line OTX TLH Laser Temperature 
        :This OID gives the laser temperature 
        of the Line OTX TLH, read from
         the DDM (Digital Diagnostic Monitoring) 
        (Unit = C)  <Help>  This measure 
        gives the laser temperature of
         the Line OTX TLH
        "
	::= { pm1005Mesrotx1LaserTemperatureEntry 2 }


--- *********************************************************
---     TABLE for the pm1005Mesrotx1FreqDeviation articles
--- *********************************************************

pm1005Mesrotx1FreqDeviationTable OBJECT-TYPE
	SYNTAX  SEQUENCE OF Pm1005Mesrotx1FreqDeviationEntry
	MAX-ACCESS not-accessible
	STATUS current
	DESCRIPTION
        "
        List of pm1005Mesrotx1FreqDeviation 
        Article
        "
	::= { pm1005MesrLine 226 }


pm1005Mesrotx1FreqDeviationEntry OBJECT-TYPE
	SYNTAX Pm1005Mesrotx1FreqDeviationEntry
	MAX-ACCESS not-accessible
	STATUS current
	DESCRIPTION
        "
        Row definition for the pm1005Mesrotx1FreqDeviation 
        table
        "
	INDEX   { pm1005Mesrotx1FreqDeviationIndex }
	::= { pm1005Mesrotx1FreqDeviationTable 1 }


Pm1005Mesrotx1FreqDeviationEntry ::=
	SEQUENCE {
	pm1005Mesrotx1FreqDeviationIndex
		INTEGER,
	pm1005Mesrotx1FreqDeviationPortn
		INTEGER 
	}


pm1005Mesrotx1FreqDeviationIndex OBJECT-TYPE
	SYNTAX  INTEGER(0..128)
	MAX-ACCESS  read-only
	STATUS current
	DESCRIPTION
        "
        Index definition for the pm1005Mesrotx1FreqDeviation 
        table
        "
	::= { pm1005Mesrotx1FreqDeviationEntry 1 }


pm1005Mesrotx1FreqDeviationPortn OBJECT-TYPE
	SYNTAX  INTEGER (0..65535)
	MAX-ACCESS read-only
	STATUS current
	DESCRIPTION
        "
        Line OTX TLH Frequency Deviation 
        :This OID gives the frequency deviation 
        of the Line OTX TLH, read from
         the DDM (Digital Diagnostic Monitoring) 
        (Unit = MHz)  <Help>  This measure 
        gives the frequency deviation of 
        the Line OTX TLH
        "
	::= { pm1005Mesrotx1FreqDeviationEntry 2 }


--- *********************************************************
---     TABLE for the pm1005Mesrotx1LaserWvlength articles
--- *********************************************************

pm1005Mesrotx1LaserWvlengthTable OBJECT-TYPE
	SYNTAX  SEQUENCE OF Pm1005Mesrotx1LaserWvlengthEntry
	MAX-ACCESS not-accessible
	STATUS current
	DESCRIPTION
        "
        List of pm1005Mesrotx1LaserWvlength 
        Article
        "
	::= { pm1005MesrLine 227 }


pm1005Mesrotx1LaserWvlengthEntry OBJECT-TYPE
	SYNTAX Pm1005Mesrotx1LaserWvlengthEntry
	MAX-ACCESS not-accessible
	STATUS current
	DESCRIPTION
        "
        Row definition for the pm1005Mesrotx1LaserWvlength 
        table
        "
	INDEX   { pm1005Mesrotx1LaserWvlengthIndex }
	::= { pm1005Mesrotx1LaserWvlengthTable 1 }


Pm1005Mesrotx1LaserWvlengthEntry ::=
	SEQUENCE {
	pm1005Mesrotx1LaserWvlengthIndex
		INTEGER,
	pm1005Mesrotx1LaserWvlengthPortn
		INTEGER 
	}


pm1005Mesrotx1LaserWvlengthIndex OBJECT-TYPE
	SYNTAX  INTEGER(0..128)
	MAX-ACCESS  read-only
	STATUS current
	DESCRIPTION
        "
        Index definition for the pm1005Mesrotx1LaserWvlength 
        table
        "
	::= { pm1005Mesrotx1LaserWvlengthEntry 1 }


pm1005Mesrotx1LaserWvlengthPortn OBJECT-TYPE
	SYNTAX  INTEGER (0..65535)
	MAX-ACCESS read-only
	STATUS current
	DESCRIPTION
        "
        Line Optical Module Wavelength 
        :This OID gives the laser wavelength 
        of the Line OTX TLH, read from
         the DDM (Digital Diagnostic Monitoring) 
        (Unit = nm)  <Help>  This measure 
        gives the laser wavelength of the 
        Line OTX TLH
        "
	::= { pm1005Mesrotx1LaserWvlengthEntry 2 }







--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm1005DwlrestartProcess OBJECT IDENTIFIER ::= { pm1005DwlOther 0 }




pm1005DwlColdRestartProcessed OBJECT-TYPE
	  SYNTAX EkiOnOff
	  MAX-ACCESS read-only
	  STATUS current
	  DESCRIPTION
        "
        Cold Restart :This OID indicates 
        that the module last restart was 
        a Cold RESTART
        "
	  ::= { pm1005DwlrestartProcess 2 }



pm1005DwlWarmRestartProcessed OBJECT-TYPE
	  SYNTAX EkiOnOff
	  MAX-ACCESS read-only
	  STATUS current
	  DESCRIPTION
        "
        Warm Restart :This OID indicates 
        that the module last restart was 
        a Warm RESTART
        "
	  ::= { pm1005DwlrestartProcess 1 }



--- *****************************************************
---     LEAF for the swBanksUsed article
--- *****************************************************
pm1005DwlswBanksUsed OBJECT IDENTIFIER ::= { pm1005DwlOther 1 }




pm1005DwlSwBank2Notempty OBJECT-TYPE
	  SYNTAX EkiOnOff
	  MAX-ACCESS read-only
	  STATUS current
	  DESCRIPTION
        "
        SW bank 2 loaded  :This OID indicates 
        a software is loaded in SW bank 
        2  <Help>  This status indicates 
        if the SW bank 2 contains SW package
        "
	  ::= { pm1005DwlswBanksUsed 6 }



pm1005DwlSwBank1Notempty OBJECT-TYPE
	  SYNTAX EkiOnOff
	  MAX-ACCESS read-only
	  STATUS current
	  DESCRIPTION
        "
        SW bank 1 loaded  :This OID indicates 
        a software is loaded in SW bank 
        1  <Help>  This status indicates 
        if the SW bank 1 contains SW package
        "
	  ::= { pm1005DwlswBanksUsed 5 }



pm1005DwlSwBank2Used OBJECT-TYPE
	  SYNTAX EkiOnOff
	  MAX-ACCESS read-only
	  STATUS current
	  DESCRIPTION
        "
        SW bank 2 active  :This OID indicates 
        the module is working on SW bank 
        2  <Help>  This status indicates 
        if the SW bank 2 is active or standby
        "
	  ::= { pm1005DwlswBanksUsed 2 }



pm1005DwlSwBank1Used OBJECT-TYPE
	  SYNTAX EkiOnOff
	  MAX-ACCESS read-only
	  STATUS current
	  DESCRIPTION
        "
        SW bank 1 active  :This OID indicates 
        the module is working on SW bank 
        1  <Help>  This status indicates 
        if the SW bank 1 is active or standby
        "
	  ::= { pm1005DwlswBanksUsed 1 }



--- *****************************************************
---     LEAF for the gwBanksUsed article
--- *****************************************************
pm1005DwlgwBanksUsed OBJECT IDENTIFIER ::= { pm1005DwlOther 2 }




pm1005DwlGwBank4Notempty OBJECT-TYPE
	  SYNTAX EkiOnOff
	  MAX-ACCESS read-only
	  STATUS current
	  DESCRIPTION
        "
        GW bank 4 loaded  :This OID indicates 
        a gateware is loaded in GW bank 
        4
        "
	  ::= { pm1005DwlgwBanksUsed 8 }



pm1005DwlGwBank3Notempty OBJECT-TYPE
	  SYNTAX EkiOnOff
	  MAX-ACCESS read-only
	  STATUS current
	  DESCRIPTION
        "
        GW bank 3 loaded  :This OID indicates 
        a gateware is loaded in GW bank 
        3  <Help>  This status indicates 
        if the GW bank 3 contains GW package
        "
	  ::= { pm1005DwlgwBanksUsed 7 }



pm1005DwlGwBank2Notempty OBJECT-TYPE
	  SYNTAX EkiOnOff
	  MAX-ACCESS read-only
	  STATUS current
	  DESCRIPTION
        "
        GW bank 2 loaded  :This OID indicates 
        a gateware is loaded in GW bank 
        2
        "
	  ::= { pm1005DwlgwBanksUsed 6 }



pm1005DwlGwBank1Notempty OBJECT-TYPE
	  SYNTAX EkiOnOff
	  MAX-ACCESS read-only
	  STATUS current
	  DESCRIPTION
        "
        GW bank 1 loaded  :This OID indicates 
        a gateware is loaded in GW bank 
        1  <Help>  This status indicates 
        if the GW bank 1 contains GW package
        "
	  ::= { pm1005DwlgwBanksUsed 5 }



pm1005DwlGwBank4Used OBJECT-TYPE
	  SYNTAX EkiOnOff
	  MAX-ACCESS read-only
	  STATUS current
	  DESCRIPTION
        "
        GW bank 4 active  :This OID indicates 
        the module is working on GW bank 
        4
        "
	  ::= { pm1005DwlgwBanksUsed 4 }



pm1005DwlGwBank3Used OBJECT-TYPE
	  SYNTAX EkiOnOff
	  MAX-ACCESS read-only
	  STATUS current
	  DESCRIPTION
        "
        GW bank 3 active  :This OID indicates 
        the module is working on GW bank 
        3  <Help>  This status indicates 
        if the GW bank 3 is active or standby
        "
	  ::= { pm1005DwlgwBanksUsed 3 }



pm1005DwlGwBank2Used OBJECT-TYPE
	  SYNTAX EkiOnOff
	  MAX-ACCESS read-only
	  STATUS current
	  DESCRIPTION
        "
        GW bank 2 active  :This OID indicates 
        the module is working on GW bank 
        2
        "
	  ::= { pm1005DwlgwBanksUsed 2 }



pm1005DwlGwBank1Used OBJECT-TYPE
	  SYNTAX EkiOnOff
	  MAX-ACCESS read-only
	  STATUS current
	  DESCRIPTION
        "
        GW bank 1 active  :This OID indicates 
        the module is working on GW bank 
        1  <Help>  This status indicates 
        if the GW bank 1 is active or standby
        "
	  ::= { pm1005DwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm1005CfgAccessCAisCsf OBJECT IDENTIFIER ::= { pm1005Config 1 }



--- *****************************************************
---     LEAF for the table 0012
--- *****************************************************

pm1005CfgClientcaiscsfTable OBJECT-TYPE
	SYNTAX  SEQUENCE OF Pm1005CfgClientcaiscsfEntry
	MAX-ACCESS not-accessible
	STATUS current
	DESCRIPTION
        "
        List of  Article
        "
	::= { pm1005CfgAccessCAisCsf 1 }


pm1005CfgClientcaiscsfEntry OBJECT-TYPE
	SYNTAX Pm1005CfgClientcaiscsfEntry
	MAX-ACCESS not-accessible
	STATUS current
	DESCRIPTION
        "
        Row definition for the accessCAisCsf 
        table
        "
	INDEX   { pm1005CfgClientcaiscsfIndex }
	::= { pm1005CfgClientcaiscsfTable 1 }


Pm1005CfgClientcaiscsfEntry ::=
	SEQUENCE {
	pm1005CfgClientcaiscsfIndex
		INTEGER,
	pm1005CfgCAisModePortn
		Unsigned32,
	pm1005CfgUpAccessioAlmPortn
		Unsigned32,
	pm1005CfgUpMapperDeAlmPortn
		Unsigned32,
	pm1005CfgDownAccessioAlmPortn
		Unsigned32,
	pm1005CfgDownMapperDeAlmPortn
		Unsigned32,
	pm1005CfgDownDfrmAlmPortn
		Unsigned32,
	pm1005CfgDownLineSyncAlarmsPortn
		Unsigned32
	}


pm1005CfgClientcaiscsfIndex OBJECT-TYPE
	SYNTAX  INTEGER(0..128)
	MAX-ACCESS  read-only
	STATUS current
	DESCRIPTION
        "
        Index definition for the clientcaiscsf 
        table
        "
	::= { pm1005CfgClientcaiscsfEntry 1 }


pm1005CfgCAisModePortn OBJECT-TYPE
	SYNTAX  Unsigned32 (0..65536)
	MAX-ACCESS read-write
	STATUS current
	DESCRIPTION
        "
        CAIS mode  on Client Port :This 
        register enables/disables port
          laser shutdown on CAIS insertion 
        condition
        "
	::= { pm1005CfgClientcaiscsfEntry 3 }


pm1005CfgUpAccessioAlmPortn OBJECT-TYPE
	SYNTAX  Unsigned32 (0..65536)
	MAX-ACCESS read-write
	STATUS current
	DESCRIPTION
        "
        CSF contributors on Client Port 
        :This register configures the contributors 
        to upstream CSF insertion on the 
        port.
        "
	::= { pm1005CfgClientcaiscsfEntry 9 }


pm1005CfgUpMapperDeAlmPortn OBJECT-TYPE
	SYNTAX  Unsigned32 (0..65536)
	MAX-ACCESS read-write
	STATUS current
	DESCRIPTION
        "
        CSF contributors on Client Port 
        :This register configures the contributors 
        to upstream CSF insertion on the 
        port.
        "
	::= { pm1005CfgClientcaiscsfEntry 10 }


pm1005CfgDownAccessioAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pm1005CfgClientcaiscsfEntry 17 }


pm1005CfgDownMapperDeAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pm1005CfgClientcaiscsfEntry 18 }


pm1005CfgDownDfrmAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pm1005CfgClientcaiscsfEntry 19 }


pm1005CfgDownLineSyncAlarmsPortn OBJECT-TYPE
	SYNTAX  Unsigned32 (0..65536)
	MAX-ACCESS read-write
	STATUS deprecated
	DESCRIPTION
        "
        CAIS contributors on Client Port 
        :This register configures the contributors 
        to downstream CAIS insertion on 
         port.
        "
	::= { pm1005CfgClientcaiscsfEntry 20 }


--- *****************************************************
---     LEAF for the table Group startup
--- *****************************************************

pm1005CfgStartup OBJECT IDENTIFIER ::= { pm1005Config 2 }



--- *****************************************************
---     LEAF for the table 2111
--- *****************************************************

pm1005CfgClientStartupTable OBJECT-TYPE
	SYNTAX  SEQUENCE OF Pm1005CfgClientStartupEntry
	MAX-ACCESS not-accessible
	STATUS current
	DESCRIPTION
        "
        List of  Article
        "
	::= { pm1005CfgStartup 1 }


pm1005CfgClientStartupEntry OBJECT-TYPE
	SYNTAX Pm1005CfgClientStartupEntry
	MAX-ACCESS not-accessible
	STATUS current
	DESCRIPTION
        "
        Row definition for the startup 
        table
        "
	INDEX   { pm1005CfgClientStartupIndex }
	::= { pm1005CfgClientStartupTable 1 }


Pm1005CfgClientStartupEntry ::=
	SEQUENCE {
	pm1005CfgClientStartupIndex
		INTEGER,
	pm1005CfgSystConfPortPortn
		Unsigned32,
	pm1005CfgNetConfPortPortn
		Unsigned32
	}


pm1005CfgClientStartupIndex OBJECT-TYPE
	SYNTAX  INTEGER(0..128)
	MAX-ACCESS  read-only
	STATUS current
	DESCRIPTION
        "
        Index definition for the clientStartup 
        table
        "
	::= { pm1005CfgClientStartupEntry 1 }


pm1005CfgSystConfPortPortn OBJECT-TYPE
	SYNTAX  Unsigned32 (0..65536)
	MAX-ACCESS read-write
	STATUS current
	DESCRIPTION
        "
        Default Settings on Client Port 
        :This  register configures the
         default initialisation settings 
        on the port.
        "
	::= { pm1005CfgClientStartupEntry 3 }


pm1005CfgNetConfPortPortn OBJECT-TYPE
	SYNTAX  Unsigned32 (0..65536)
	MAX-ACCESS read-write
	STATUS current
	DESCRIPTION
        "
        Default Protocol on Client Port 
        :This register configures the default 
        initialisation protocol on the
         port.
        "
	::= { pm1005CfgClientStartupEntry 4 }


--- *****************************************************
---     LEAF for the table 2191
--- *****************************************************

pm1005tablelineStartup OBJECT IDENTIFIER ::= { pm1005CfgStartup 2 }



pm1005CfgsystConfLine1 OBJECT-TYPE
	  SYNTAX Unsigned32 (0..65536)
	  MAX-ACCESS read-write
	  STATUS current
	  DESCRIPTION
        "
        Default Settings on Line 1 :This 
        register configures the default 
        initialisation settings on Line 
        port 1.
        "
	  ::= { pm1005tablelineStartup 2 }



pm1005CfglineOptions1 OBJECT-TYPE
	  SYNTAX Unsigned32 (0..65536)
	  MAX-ACCESS read-write
	  STATUS current
	  DESCRIPTION
        "
        Default Options on Active Line 
        Port :This register configures
         the default options on the active 
        line port
        "
	  ::= { pm1005tablelineStartup 5 }



pm1005CfgsystConfLine2 OBJECT-TYPE
	  SYNTAX Unsigned32 (0..65536)
	  MAX-ACCESS read-write
	  STATUS current
	  DESCRIPTION
        "
        Default Settings on Line 2 :This 
        register configures the default 
        initialisation settings on Line 
        port 2.
        "
	  ::= { pm1005tablelineStartup 6 }



pm1005CfglineSelection OBJECT-TYPE
	  SYNTAX Unsigned32 (0..65536)
	  MAX-ACCESS read-write
	  STATUS current
	  DESCRIPTION
        "
        Default Settings of active line 
        :This  register configures the
         start up active line.
        "
	  ::= { pm1005tablelineStartup 7 }



--- *****************************************************
---     LEAF for the table 21AB
--- *****************************************************

pm1005CfgXfpTable OBJECT-TYPE
	SYNTAX  SEQUENCE OF Pm1005CfgXfpEntry
	MAX-ACCESS not-accessible
	STATUS current
	DESCRIPTION
        "
        List of  Article
        "
	::= { pm1005CfgStartup 3 }


pm1005CfgXfpEntry OBJECT-TYPE
	SYNTAX Pm1005CfgXfpEntry
	MAX-ACCESS not-accessible
	STATUS current
	DESCRIPTION
        "
        Row definition for the startup 
        table
        "
	INDEX   { pm1005CfgXfpIndex }
	::= { pm1005CfgXfpTable 1 }


Pm1005CfgXfpEntry ::=
	SEQUENCE {
	pm1005CfgXfpIndex
		INTEGER,
	pm1005CfgSystConfXfpPortn
		Unsigned32,
	pm1005CfgDataRateConfXfpPortn
		Unsigned32
	}


pm1005CfgXfpIndex OBJECT-TYPE
	SYNTAX  INTEGER(0..128)
	MAX-ACCESS  read-only
	STATUS current
	DESCRIPTION
        "
        Index definition for the xfp table
        "
	::= { pm1005CfgXfpEntry 1 }


pm1005CfgSystConfXfpPortn OBJECT-TYPE
	SYNTAX  Unsigned32 (0..65536)
	MAX-ACCESS read-write
	STATUS current
	DESCRIPTION
        "
        Default settings on XFP Port :This 
        register configures the default 
        initialisation settings on XFP
         port.
        "
	::= { pm1005CfgXfpEntry 3 }


pm1005CfgDataRateConfXfpPortn OBJECT-TYPE
	SYNTAX  Unsigned32 (0..65536)
	MAX-ACCESS read-write
	STATUS deprecated
	DESCRIPTION
        "
        :Reserved
        "
	::= { pm1005CfgXfpEntry 4 }


--- *****************************************************
---     LEAF for the table Group labels
--- *****************************************************

pm1005CfgLabels OBJECT IDENTIFIER ::= { pm1005Config 3 }



--- *****************************************************
---     LEAF for the table NO_VALUE
--- *****************************************************

pm1005CfgLabelclientTable OBJECT-TYPE
	SYNTAX  SEQUENCE OF Pm1005CfgLabelclientEntry
	MAX-ACCESS not-accessible
	STATUS current
	DESCRIPTION
        "
        List of  Article
        "
	::= { pm1005CfgLabels 1 }


pm1005CfgLabelclientEntry OBJECT-TYPE
	SYNTAX Pm1005CfgLabelclientEntry
	MAX-ACCESS not-accessible
	STATUS current
	DESCRIPTION
        "
        Row definition for the labels
         table
        "
	INDEX   { pm1005CfgLabelclientIndex }
	::= { pm1005CfgLabelclientTable 1 }


Pm1005CfgLabelclientEntry ::=
	SEQUENCE {
	pm1005CfgLabelclientIndex
		INTEGER,
	pm1005CfgLabelclientPortn
		DisplayString
	}


pm1005CfgLabelclientIndex OBJECT-TYPE
	SYNTAX  INTEGER(0..128)
	MAX-ACCESS  read-only
	STATUS current
	DESCRIPTION
        "
        Index definition for the labelclient 
        table
        "
	::= { pm1005CfgLabelclientEntry 1 }


pm1005CfgLabelclientPortn OBJECT-TYPE
	SYNTAX  DisplayString( SIZE(1..16))
	MAX-ACCESS read-write
	STATUS current
	DESCRIPTION
        "
        Default settings on the label
         of the Ports :These registers
         configures the default initialisation 
        settings of the labels of the ports.
        "
	::= { pm1005CfgLabelclientEntry 3 }


--- *****************************************************
---     LEAF for the table NO_VALUE
--- *****************************************************

pm1005CfgLabellineTable OBJECT-TYPE
	SYNTAX  SEQUENCE OF Pm1005CfgLabellineEntry
	MAX-ACCESS not-accessible
	STATUS current
	DESCRIPTION
        "
        List of  Article
        "
	::= { pm1005CfgLabels 2 }


pm1005CfgLabellineEntry OBJECT-TYPE
	SYNTAX Pm1005CfgLabellineEntry
	MAX-ACCESS not-accessible
	STATUS current
	DESCRIPTION
        "
        Row definition for the labels
         table
        "
	INDEX   { pm1005CfgLabellineIndex }
	::= { pm1005CfgLabellineTable 1 }


Pm1005CfgLabellineEntry ::=
	SEQUENCE {
	pm1005CfgLabellineIndex
		INTEGER,
	pm1005CfgLabellinePortn
		DisplayString
	}


pm1005CfgLabellineIndex OBJECT-TYPE
	SYNTAX  INTEGER(0..128)
	MAX-ACCESS  read-only
	STATUS current
	DESCRIPTION
        "
        Index definition for the labelline 
        table
        "
	::= { pm1005CfgLabellineEntry 1 }


pm1005CfgLabellinePortn OBJECT-TYPE
	SYNTAX  DisplayString( SIZE(1..16))
	MAX-ACCESS read-write
	STATUS current
	DESCRIPTION
        "
        Default settings on the label
         of the lines :These registers
         configures the default initialisation 
        settings of the labels of the lines.
        "
	::= { pm1005CfgLabellineEntry 3 }


--- *****************************************************
---     LEAF for the table Group startuptlh
--- *****************************************************

pm1005CfgStartuptlh OBJECT IDENTIFIER ::= { pm1005Config 4 }



--- *****************************************************
---     LEAF for the table 25A8
--- *****************************************************

pm1005CfgOtxtlhTable OBJECT-TYPE
	SYNTAX  SEQUENCE OF Pm1005CfgOtxtlhEntry
	MAX-ACCESS not-accessible
	STATUS current
	DESCRIPTION
        "
        List of  Article
        "
	::= { pm1005CfgStartuptlh 1 }


pm1005CfgOtxtlhEntry OBJECT-TYPE
	SYNTAX Pm1005CfgOtxtlhEntry
	MAX-ACCESS not-accessible
	STATUS current
	DESCRIPTION
        "
        Row definition for the startuptlh 
        table
        "
	INDEX   { pm1005CfgOtxtlhIndex }
	::= { pm1005CfgOtxtlhTable 1 }


Pm1005CfgOtxtlhEntry ::=
	SEQUENCE {
	pm1005CfgOtxtlhIndex
		INTEGER,
	pm1005CfgNuPortn
		Unsigned32,
	pm1005CfgLineDitherRatePortn
		Unsigned32,
	pm1005CfgLineDitherFhzPortn
		Unsigned32,
	pm1005CfgLinePwrLaserPortn
		Unsigned32,
	pm1005CfgLineFCurrentPortn
		Unsigned32,
	pm1005CfgLineGridCurrentPortn
		Unsigned32,
	pm1005CfgFPortn
		Unsigned32,
	pm1005CfgReservedPortn
		Unsigned32,
	pm1005CfgLinePhotodiodeModePortn
		Unsigned32,
	pm1005CfgLinePhotodiodeValuePortn
		Unsigned32
	}


pm1005CfgOtxtlhIndex OBJECT-TYPE
	SYNTAX  INTEGER(0..128)
	MAX-ACCESS  read-only
	STATUS current
	DESCRIPTION
        "
        Index definition for the otxtlh 
        table
        "
	::= { pm1005CfgOtxtlhEntry 1 }


pm1005CfgNuPortn OBJECT-TYPE
	SYNTAX  Unsigned32 (0..65536)
	MAX-ACCESS read-write
	STATUS deprecated
	DESCRIPTION
        "
        :
        "
	::= { pm1005CfgOtxtlhEntry 3 }


pm1005CfgLineDitherRatePortn OBJECT-TYPE
	SYNTAX  Unsigned32 (0..65536)
	MAX-ACCESS read-write
	STATUS current
	DESCRIPTION
        "
        Default Line OTX TLH FM amplitude 
        :This register configures the start-up 
        width of the frequency modulation 
        of the Line OTX TLH
        "
	::= { pm1005CfgOtxtlhEntry 4 }


pm1005CfgLineDitherFhzPortn OBJECT-TYPE
	SYNTAX  Unsigned32 (0..65536)
	MAX-ACCESS read-write
	STATUS current
	DESCRIPTION
        "
        Default Line OTX TLH FM frequency 
        :This register configures the start-up 
        frequency of the frequency modulation 
        of the Line OTX TLH
        "
	::= { pm1005CfgOtxtlhEntry 5 }


pm1005CfgLinePwrLaserPortn OBJECT-TYPE
	SYNTAX  Unsigned32 (0..65536)
	MAX-ACCESS read-write
	STATUS current
	DESCRIPTION
        "
        Defaut Line OTX TLH output Power 
        :This register configures the start-up 
        output power of the Line OTX TLH 
         (Unit = dBm)
        "
	::= { pm1005CfgOtxtlhEntry 6 }


pm1005CfgLineFCurrentPortn OBJECT-TYPE
	SYNTAX  Unsigned32 (0..65536)
	MAX-ACCESS read-write
	STATUS current
	DESCRIPTION
        "
        Default Line OTX TLH Channel :This 
        register configures the start-up 
        laser channel of the Line OTX TLH
        "
	::= { pm1005CfgOtxtlhEntry 7 }


pm1005CfgLineGridCurrentPortn OBJECT-TYPE
	SYNTAX  Unsigned32 (0..65536)
	MAX-ACCESS read-write
	STATUS current
	DESCRIPTION
        "
        Default Line OTX TLH Grid :This 
        register configures the start-up 
        laser grid of the Line OTX TLH
        "
	::= { pm1005CfgOtxtlhEntry 8 }


pm1005CfgFPortn OBJECT-TYPE
	SYNTAX  Unsigned32 (0..65536)
	MAX-ACCESS read-write
	STATUS current
	DESCRIPTION
        "
        Default Line OTX TLH lowest Freq 
        :This register configures the start-up 
        lowest frequency supported on the 
        Line OTX TLH
        "
	::= { pm1005CfgOtxtlhEntry 9 }


pm1005CfgReservedPortn OBJECT-TYPE
	SYNTAX  Unsigned32 (0..65536)
	MAX-ACCESS read-write
	STATUS deprecated
	DESCRIPTION
        "
        :
        "
	::= { pm1005CfgOtxtlhEntry 10 }


pm1005CfgLinePhotodiodeModePortn OBJECT-TYPE
	SYNTAX  Unsigned32 (0..65536)
	MAX-ACCESS read-write
	STATUS current
	DESCRIPTION
        "
        Default Line OTX TLH APD mode
         :This register configures the
         start-up APD mode of the Line
         OTX TLH
        "
	::= { pm1005CfgOtxtlhEntry 11 }


pm1005CfgLinePhotodiodeValuePortn OBJECT-TYPE
	SYNTAX  Unsigned32 (0..65536)
	MAX-ACCESS read-write
	STATUS current
	DESCRIPTION
        "
        Default Line OTX TLH APD atten. 
        :This register configures the start-up 
        APD attenuation on the Line OTX 
        TLH
        "
	::= { pm1005CfgOtxtlhEntry 12 }


--- *****************************************************
---     LEAF for the table Group startuptablefive
--- *****************************************************

pm1005CfgStartuptablefive OBJECT IDENTIFIER ::= { pm1005Config 5 }



--- *****************************************************
---     LEAF for the table 0005
--- *****************************************************

pm1005CfgOtxtlhcapabilitiesTable OBJECT-TYPE
	SYNTAX  SEQUENCE OF Pm1005CfgOtxtlhcapabilitiesEntry
	MAX-ACCESS not-accessible
	STATUS current
	DESCRIPTION
        "
        List of  Article
        "
	::= { pm1005CfgStartuptablefive 1 }


pm1005CfgOtxtlhcapabilitiesEntry OBJECT-TYPE
	SYNTAX Pm1005CfgOtxtlhcapabilitiesEntry
	MAX-ACCESS not-accessible
	STATUS current
	DESCRIPTION
        "
        Row definition for the startuptablefive 
        table
        "
	INDEX   { pm1005CfgOtxtlhcapabilitiesIndex }
	::= { pm1005CfgOtxtlhcapabilitiesTable 1 }


Pm1005CfgOtxtlhcapabilitiesEntry ::=
	SEQUENCE {
	pm1005CfgOtxtlhcapabilitiesIndex
		INTEGER,
	pm1005CfgComponentTypePortn
		Unsigned32,
	pm1005CfgMiscellaneousPortn
		Unsigned32,
	pm1005CfgFirstChannelPortn
		Unsigned32,
	pm1005CfgLastChannelPortn
		Unsigned32,
	pm1005CfgGridPortn
		Unsigned32
	}


pm1005CfgOtxtlhcapabilitiesIndex OBJECT-TYPE
	SYNTAX  INTEGER(0..128)
	MAX-ACCESS  read-only
	STATUS current
	DESCRIPTION
        "
        Index definition for the otxtlhcapabilities 
        table
        "
	::= { pm1005CfgOtxtlhcapabilitiesEntry 1 }


pm1005CfgComponentTypePortn OBJECT-TYPE
	SYNTAX  Unsigned32 (0..65536)
	MAX-ACCESS read-only
	STATUS current
	DESCRIPTION
        "
        Component parameters :This OID 
        defines the component parameters
        "
	::= { pm1005CfgOtxtlhcapabilitiesEntry 3 }


pm1005CfgMiscellaneousPortn OBJECT-TYPE
	SYNTAX  Unsigned32 (0..65536)
	MAX-ACCESS read-only
	STATUS current
	DESCRIPTION
        "
        Miscellaneous default settings 
        :This OID defines the miscellaneous 
        parameters
        "
	::= { pm1005CfgOtxtlhcapabilitiesEntry 4 }


pm1005CfgFirstChannelPortn OBJECT-TYPE
	SYNTAX  Unsigned32 (0..65536)
	MAX-ACCESS read-only
	STATUS current
	DESCRIPTION
        "
        Number of the first channel of 
        the component :This OID defines 
        the first channel number of the 
        PM
        "
	::= { pm1005CfgOtxtlhcapabilitiesEntry 5 }


pm1005CfgLastChannelPortn OBJECT-TYPE
	SYNTAX  Unsigned32 (0..65536)
	MAX-ACCESS read-only
	STATUS current
	DESCRIPTION
        "
        Number of the last channel of
         the component :This OID defines 
        the last channel number of the
         PM
        "
	::= { pm1005CfgOtxtlhcapabilitiesEntry 6 }


pm1005CfgGridPortn OBJECT-TYPE
	SYNTAX  Unsigned32 (0..65536)
	MAX-ACCESS read-only
	STATUS current
	DESCRIPTION
        "
        Grid value of the component :This 
        OID defines the grid of the PM
        "
	::= { pm1005CfgOtxtlhcapabilitiesEntry 7 }



pm1005CfgWriteConfiguration  OBJECT-TYPE
	SYNTAX EkiOnOff
	MAX-ACCESS read-write
	STATUS current
	DESCRIPTION
	"Write configuration to module:This OID 
	 writes the complete configuration to the module"
	::= { pm1005Config 257 }






--- *****************************************************
---     TRAP OBJECTS
--- *****************************************************

pm1005trapPortNumber OBJECT-TYPE
	SYNTAX INTEGER(1..64)
	MAX-ACCESS read-only
	STATUS current
	DESCRIPTION
	"Last port which generates a trap"
	::= { pm1005traps 2 }

pm1005trapLineNumber OBJECT-TYPE
	SYNTAX INTEGER(1..64)
	MAX-ACCESS read-only
	STATUS current
	DESCRIPTION
	"Last Line which generates a trap"
	::= { pm1005traps 3 }

pm1005trapBoardNumber OBJECT-TYPE
	SYNTAX INTEGER(1..64)
	MAX-ACCESS read-only
	STATUS current
	DESCRIPTION
	"Last module which generates a trap"
	::= { pm1005traps 4 }







--- *****************************************************
---     LINE TRAPS
--- *****************************************************

pm1005LineTrapNotUrgentGoesOn NOTIFICATION-TYPE
	OBJECTS {pm1005AlmLineDdmWarningPortn, pm1005trapLineNumber, pm1005trapBoardNumber}
	STATUS current
	--&FILTNAME    "PM1005 Line Not Urgent ON"
	--&ACTIONS     { log, minor }
	--&MATCH       { pm1005AlmLineDdmWarningPortn "on", pm1005trapLineNumber "$2", pm1005trapBoardNumber "$3"}
	--&MESG        "DDM Warning appears on Line Port $2 of PM1005 in Slot $3 ($A)"
	DESCRIPTION "Not urgent Line default is activated"
	::= { pm1005traps 30 }

pm1005LineTrapNotUrgentGoesOff NOTIFICATION-TYPE
	OBJECTS {pm1005AlmLineDdmWarningPortn, pm1005trapLineNumber, pm1005trapBoardNumber}
	STATUS current
	--&FILTNAME    "PM1005 Line Not Urgent OFF"
	--&ACTIONS     { log, normal }
	--&CLEARS      { "PM1005 Line Not Urgent ON" }
	--&MATCH       { pm1005AlmLineDdmWarningPortn "on", pm1005trapLineNumber "$2", pm1005trapBoardNumber "$3"}
	--&MESG        "DDM Warning disappears on Line Port $2 of PM1005 in Slot $3 ($A)"
	DESCRIPTION "Not urgent Line default disappeared"
	::= { pm1005traps 31 }

pm1005LineTrapUrgentGoesOn NOTIFICATION-TYPE
	OBJECTS {pm1005AlmLineDdmAlmPortn, pm1005trapLineNumber, pm1005trapBoardNumber}
	STATUS current
	--&FILTNAME    "PM1005 Line Urgent ON"
	--&ACTIONS     { log, major }
	--&MATCH       { pm1005AlmLineDdmAlmPortn "on", pm1005trapLineNumber "$2", pm1005trapBoardNumber "$3"}
	--&MESG        "DDM Alarm appears on Line Port $2 of PM1005 in Slot $3 ($A)"
	DESCRIPTION "Urgent Line default is activated"
	::= { pm1005traps 32 }

pm1005LineTrapUrgentGoesOff NOTIFICATION-TYPE
	OBJECTS {pm1005AlmLineDdmAlmPortn, pm1005trapLineNumber, pm1005trapBoardNumber}
	STATUS current
	--&FILTNAME    "PM1005 Line Urgent OFF"
	--&ACTIONS     { log, normal }
	--&CLEARS      { "PM1005 Line Urgent ON" }
	--&MATCH       { pm1005AlmLineDdmAlmPortn "on", pm1005trapLineNumber "$2", pm1005trapBoardNumber "$3"}
	--&MESG        "DDM Alarm disappears on Line Port $2 of PM1005 in Slot $3 ($A)"
	DESCRIPTION "Urgent Line default disappeared"
	::= { pm1005traps 33 }

pm1005LineTrapCritGoesOn NOTIFICATION-TYPE
	OBJECTS {pm1005AlmLineFailPortn , pm1005AlmLineHwFailPortn , pm1005trapLineNumber, pm1005trapBoardNumber}
	STATUS current
	--&FILTNAME    "PM1005 Line Fail ON"
	--&ACTIONS     { log, critical }
	--&MATCH       { pm1005AlmLineFailPortn "on", pm1005AlmLineHwFailPortn "*", pm1005trapLineNumber "$3", pm1005trapBoardNumber "$4"}
	--&MESG        "Line Port $3 Down on PM1005 in Slot $4 ($A)"
	
	--&FILTNAME    "PM1005 Line HW Fail ON (Hidden)"
	--&ACTIONS     { info }
	--&MATCH       { pm1005AlmLineFailPortn "*", pm1005AlmLineHwFailPortn "on", pm1005trapLineNumber "$3", pm1005trapBoardNumber "$4"}
	--&MESG        "Line Port $3 Down on PM1005 in Slot $4 ($A)"
	DESCRIPTION "Critical Line default is activated"
	::= { pm1005traps 34 }

pm1005LineTrapCritGoesOff NOTIFICATION-TYPE
	OBJECTS {pm1005AlmLineFailPortn , pm1005AlmLineHwFailPortn , pm1005trapLineNumber, pm1005trapBoardNumber}
	STATUS current
	--&FILTNAME    "PM1005 Line Fail OFF"
	--&ACTIONS     { log,  normal }
	--&CLEARS      { "PM1005 Line Fail ON" }
	--&MATCH       { pm1005AlmLineFailPortn "on", pm1005AlmLineHwFailPortn "*", pm1005trapLineNumber "$3", pm1005trapBoardNumber "$4"}
	--&MESG        "Line Port $3 Up on PM1005 in Slot $4 ($A)"

	--&FILTNAME    "PM1005 Line HW Fail OFF (Hidden)"
	--&ACTIONS     { info }
	--&MATCH       { pm1005AlmLineFailPortn "*", pm1005AlmLineHwFailPortn "on", pm1005trapLineNumber "$3", pm1005trapBoardNumber "$4"}
	--&MESG        "Line Port $3 Up on PM1005 in Slot $4 ($A)"
	DESCRIPTION "Critical Line default disappeared"
	::= { pm1005traps 35 }






--- *****************************************************
---     CLIENT TRAPS
--- *****************************************************

pm1005ClientTrapNotUrgentGoesOn NOTIFICATION-TYPE
	OBJECTS {pm1005AlmSfpDdmWarningPortn, pm1005trapPortNumber, pm1005trapBoardNumber}
	STATUS current
	--&FILTNAME    "PM1005 Client Not Urgent ON"
	--&ACTIONS     { log, minor }
	--&MATCH       { pm1005AlmSfpDdmWarningPortn "on", pm1005trapPortNumber "$2", pm1005trapBoardNumber "$3"}
	--&MESG        "DDM Warning appears on Client Port $2 of PM1005 in Slot $3 ($A)"
	DESCRIPTION "Not urgent client default is activated"
	::= { pm1005traps 40 }

pm1005ClientTrapNotUrgentGoesOff NOTIFICATION-TYPE
	OBJECTS {pm1005AlmSfpDdmWarningPortn, pm1005trapPortNumber, pm1005trapBoardNumber}
	STATUS current
	--&FILTNAME    "PM1005 Client Not Urgent OFF"
	--&ACTIONS     { log, normal }
	--&CLEARS      { "PM1005 Client Not Urgent ON" }
	--&MATCH       { pm1005AlmSfpDdmWarningPortn "on", pm1005trapPortNumber "$2", pm1005trapBoardNumber "$3"}
	--&MESG        "DDM Warning appears on Client Port $2 of PM1005 in Slot $3 ($A)"
	DESCRIPTION "Not urgent client default disappeared"
	::= { pm1005traps 41 }

pm1005ClientTrapUrgentGoesOn NOTIFICATION-TYPE
	OBJECTS {pm1005AlmSfpDdmAlmPortn, pm1005trapPortNumber, pm1005trapBoardNumber}
	STATUS current
	--&FILTNAME    "PM1005 Client Urgent ON"
	--&ACTIONS     { log, major }
	--&MATCH       { pm1005AlmSfpDdmAlmPortn "on", pm1005trapPortNumber "$2", pm1005trapBoardNumber "$3"}
	--&MESG        "DDM Alarm appears on Client Port $2 of PM1005 in Slot $3 ($A)"
	DESCRIPTION "Urgent client default is activated"
	::= { pm1005traps 42 }

pm1005ClientTrapUrgentGoesOff NOTIFICATION-TYPE
	OBJECTS {pm1005AlmSfpDdmAlmPortn, pm1005trapPortNumber, pm1005trapBoardNumber}
	STATUS current
	--&FILTNAME    "PM1005 Client Urgent OFF"
	--&ACTIONS     { log, normal }
	--&CLEARS      { "PM1005 Client Urgent ON" }
	--&MATCH       { pm1005AlmSfpDdmAlmPortn "on", pm1005trapPortNumber "$2", pm1005trapBoardNumber "$3"}
	--&MESG        "DDM Alarm disappears on Client Port $2 of PM1005 in Slot $3 ($A)"
	DESCRIPTION "Urgent client default disappeared"
	::= { pm1005traps 43 }

pm1005ClientTrapCritGoesOn NOTIFICATION-TYPE
	OBJECTS {pm1005AlmFailAccPortn, pm1005AlmHwFailAccPortn, pm1005trapPortNumber, pm1005trapBoardNumber}
	STATUS current
	--&FILTNAME    "PM1005 Client Fail ON"
	--&ACTIONS     { log, critical }
	--&MATCH       { pm1005AlmFailAccPortn "on", pm1005AlmHwFailAccPortn "*", pm1005trapPortNumber "$3", pm1005trapBoardNumber "$4"}
	--&MESG        "Client Port $3 Down on PM1005 in Slot $4 ($A)"
	
	--&FILTNAME    "PM1005 Client HW Fail ON (Hidden)"
	--&ACTIONS     { info }
	--&MATCH       { pm1005AlmFailAccPortn "*", pm1005AlmHwFailAccPortn "on", pm1005trapPortNumber "$3", pm1005trapBoardNumber "$4"}
	--&MESG        "Client Port $3 Down on PM1005 in Slot $4 ($A)"
	DESCRIPTION "Critical client default is activated"
	::= { pm1005traps 44 }

pm1005ClientTrapCritGoesOff NOTIFICATION-TYPE
	OBJECTS {pm1005AlmFailAccPortn, pm1005AlmHwFailAccPortn, pm1005trapPortNumber, pm1005trapBoardNumber}
	STATUS current
	--&FILTNAME    "PM1005 Client Fail OFF"
	--&ACTIONS     { log, normal }
	--&CLEARS      { "PM1005 Client Fail ON" }
	--&MATCH       { pm1005AlmFailAccPortn "on", pm1005AlmHwFailAccPortn "*", pm1005trapPortNumber "$3", pm1005trapBoardNumber "$4"}
	--&MESG        "Client Port $3 Up on PM1005 in Slot $4 ($A)"
	
	--&FILTNAME    "PM1005 Client HW Fail OFF (Hidden)"
	--&ACTIONS     { info }
	--&MATCH       { pm1005AlmFailAccPortn "*", pm1005AlmHwFailAccPortn "on", pm1005trapPortNumber "$3", pm1005trapBoardNumber "$4"}
	--&MESG        "Client Port $3 Up on PM1005 in Slot $4 ($A)"
	DESCRIPTION "Critical client default disappeared"
	::= { pm1005traps 45 }






--- *****************************************************
---     HW TRAPS
--- *****************************************************

pm1005PowerTrapUrgentGoesOn NOTIFICATION-TYPE
	OBJECTS {pm1005AlmDefFuseB, pm1005AlmDefFuseA , pm1005trapBoardNumber}
	STATUS current
	--&FILTNAME    "PM1005 Fuse A Fail ON"
	--&ACTIONS     { log, major }
	--&MATCH       { pm1005AlmDefFuseB "*", pm1005AlmDefFuseA "on", pm1005trapBoardNumber "$3"}
	--&MESG        "Power Input A Fail on PM1005 in Slot $3 ($A)"

	--&FILTNAME    "PM1005 Fuse B Fail ON"
	--&ACTIONS     { log, major }
	--&MATCH       { pm1005AlmDefFuseB "on", pm1005AlmDefFuseA "*", pm1005trapBoardNumber "$3"}
	--&MESG        "Power Input B Fail on PM1005 in Slot $3 ($A)"
	DESCRIPTION "Urgent power supply default is activated"
	::= { pm1005traps 50 }

pm1005PowerTrapUrgentGoesOff NOTIFICATION-TYPE
	OBJECTS {pm1005AlmDefFuseB, pm1005AlmDefFuseA , pm1005trapBoardNumber}
	STATUS current
	--&FILTNAME    "PM1005 Fuse A&B Fail OFF"
	--&ACTIONS     { log, normal}
	--&CLEARS      { "PM1005 Fuse A Fail ON", "PM1005 Fuse B Fail ON" }
	--&MATCH       { pm1005AlmDefFuseB "on", pm1005AlmDefFuseA "on", pm1005trapBoardNumber "$3"}
	--&MESG        "Power Inputs A and B Present on PM1005 in Slot $3 ($A)"
	DESCRIPTION "Urgent power supply default disappeared"
	::= { pm1005traps 51 }






END
