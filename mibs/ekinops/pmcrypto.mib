-- *****************************************************************
-- EKINOPS-Pmcrypto.TXT:  MIB
--
--MIB Part Number:3MI00055AAAC
--MIB Version:01
--
-- Copyright (c) 2018 by Ekinops
-- All rights reserved.
-- 
-- *****************************************************************

EKINOPS-Pmcrypto-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress                
        		FROM SNMPv2-SMI
 	TEXTUAL-CONVENTION,
	DisplayString
                FROM SNMPv2-TC;

modulePmcrypto MODULE-IDENTITY
        LAST-UPDATED "201804130000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.fr"
        DESCRIPTION
          "Creation."


	REVISION "201709200000Z"
	DESCRIPTION
	  "Creation for PMCRYPTO module"
	REVISION "201802090000Z"
	DESCRIPTION
	  "Crypto alarm added"
	REVISION "201804130000Z"
	DESCRIPTION
	  "Alarm Type modification"
        ::= { ekinops 96 }



--- *****************************************************
---     LEAF LEVEL 2
--- *****************************************************


pmcryptoalarms OBJECT IDENTIFIER ::= { modulePmcrypto 2 }	
pmcryptoAlmOther OBJECT IDENTIFIER ::= { pmcryptoalarms 1 }
pmcryptoAlmOtherNurg OBJECT IDENTIFIER ::= { pmcryptoAlmOther 1 }
pmcryptoAlmOtherUrg OBJECT IDENTIFIER ::= { pmcryptoAlmOther 2 }
pmcryptoAlmOtherCrit OBJECT IDENTIFIER ::= { pmcryptoAlmOther 3 }

pmcryptoAlmClient OBJECT IDENTIFIER ::= { pmcryptoalarms 2 }
pmcryptoAlmClientNurg OBJECT IDENTIFIER ::= { pmcryptoAlmClient 1 }
pmcryptoAlmClientUrg OBJECT IDENTIFIER ::= { pmcryptoAlmClient 2 }
pmcryptoAlmClientCrit OBJECT IDENTIFIER ::= { pmcryptoAlmClient 3 }
	
pmcryptoAlmLine OBJECT IDENTIFIER ::= { pmcryptoalarms 3 }
pmcryptoAlmLineNurg OBJECT IDENTIFIER ::= { pmcryptoAlmLine 1 }
pmcryptoAlmLineUrg OBJECT IDENTIFIER ::= { pmcryptoAlmLine 2 }
pmcryptoAlmLineCrit OBJECT IDENTIFIER ::= { pmcryptoAlmLine 3 }





pmcryptomeasures OBJECT IDENTIFIER ::= { modulePmcrypto 3 }	
pmcryptoMesrOther OBJECT IDENTIFIER ::= { pmcryptomeasures 1 }	
pmcryptoMesrClient OBJECT IDENTIFIER ::= { pmcryptomeasures 2 }	
pmcryptoMesrLine OBJECT IDENTIFIER ::= { pmcryptomeasures 3 }	




pmcryptocounters OBJECT IDENTIFIER ::= { modulePmcrypto 4 }
pmcryptoCntOther OBJECT IDENTIFIER ::= { pmcryptocounters 1 }
pmcryptoCntClient OBJECT IDENTIFIER ::= { pmcryptocounters 2 }
pmcryptoCntLine OBJECT IDENTIFIER ::= { pmcryptocounters 3 }


pmcryptocontrolsWrite OBJECT IDENTIFIER ::= { modulePmcrypto 6 }
pmcryptoCtrlOther OBJECT IDENTIFIER ::= { pmcryptocontrolsWrite 1 }
pmcryptoCtrlClient OBJECT IDENTIFIER ::= { pmcryptocontrolsWrite 2 }
pmcryptoCtrlLine OBJECT IDENTIFIER ::= { pmcryptocontrolsWrite 3 }

pmcryptori OBJECT IDENTIFIER ::= { modulePmcrypto 7 }
pmcryptoriTable OBJECT IDENTIFIER ::= { pmcryptori 1 }

pmcryptodownload OBJECT IDENTIFIER ::= { modulePmcrypto 8 }
pmcryptoDwlOther OBJECT IDENTIFIER ::= { pmcryptodownload 1 }
pmcryptoDwlClient OBJECT IDENTIFIER ::= { pmcryptodownload 2 }
pmcryptoDwlLine OBJECT IDENTIFIER ::= { pmcryptodownload 3 }


pmcryptoConfig OBJECT IDENTIFIER ::= { modulePmcrypto 9 }

pmcryptotraps OBJECT IDENTIFIER ::= { modulePmcrypto 10 }



pmcryptoMonitoring OBJECT IDENTIFIER ::= { modulePmcrypto 11}

pmcryptoMonOther OBJECT IDENTIFIER ::= { pmcryptoMonitoring 1 }
pmcryptoMonRmon OBJECT IDENTIFIER ::= { pmcryptoMonOther 3 }

pmcryptoMonClient OBJECT IDENTIFIER ::= { pmcryptoMonitoring 2 }
pmcryptoMonClientRmonCounter OBJECT IDENTIFIER ::= { pmcryptoMonClient 4 }


pmcryptoMonPerfOther OBJECT IDENTIFIER ::= { pmcryptoMonitoring 5 }
pmcryptoMonPerfSync OBJECT IDENTIFIER ::= { pmcryptoMonPerfOther 1 }
pmcryptoMonPerfTimeStamp OBJECT IDENTIFIER ::= { pmcryptoMonPerfOther 2 }


pmcryptoMonPerfClient OBJECT IDENTIFIER ::= { pmcryptoMonitoring 6 }

pmcryptoMonPerfLine OBJECT IDENTIFIER ::= { pmcryptoMonitoring 7 }



--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************



PmcryptoOtxGrid ::= TEXTUAL-CONVENTION
    STATUS      current
    DESCRIPTION "Different grids on OTX-TLH on client and line ports"
    SYNTAX INTEGER {
		otxgrid200(200),
		otxgrid100(100),
		otxgrid50(50)
           }


PmcryptoClientProtocolA ::= TEXTUAL-CONVENTION
    STATUS      current
    DESCRIPTION "Different values on the protocol on the client ports"
    SYNTAX INTEGER {
		protocolclientvalue0A(1),
		protocolclientvalue1A(2),
		protocolclientvalue2A(3)
           }


PmcryptoClientProtocolB ::= TEXTUAL-CONVENTION
    STATUS      current
    DESCRIPTION "Different values on the protocol on the client ports"
    SYNTAX INTEGER {
		protocolclientvalue0B(1),
		protocolclientvalue1B(2),
		protocolclientvalue2B(3),
		protocolclientvalue3B(4),
		protocolclientvalue4B(5)
           }


PmcryptoClientProtocolC ::= TEXTUAL-CONVENTION
    STATUS      current
    DESCRIPTION "Different values on the protocol on the client ports"
    SYNTAX INTEGER {
		protocolclientvalue0C(1)
           }


PmcryptoProtocolMode ::= TEXTUAL-CONVENTION
    STATUS      current
    DESCRIPTION "Different values on the protocol mode"
    SYNTAX INTEGER {
		protocolmodevalue0(1),
		protocolmodevalue1(2),
		protocolmodevalue2(3)
           }

PmcryptoOtxChannel ::= TEXTUAL-CONVENTION
    STATUS      current
    DESCRIPTION "Channel selection on transceiver Tx line ports"
    SYNTAX INTEGER

PmcryptoOrxChannel ::= TEXTUAL-CONVENTION
    STATUS      current
    DESCRIPTION "Channel selection on transceiver Rx line ports"
    SYNTAX INTEGER

PmcryptoDccMode ::= TEXTUAL-CONVENTION
    STATUS      current
    DESCRIPTION "Mode for DCC"
    SYNTAX INTEGER {
		dccNo(0),
		dccLine1(1),
		dccLine2(2)
           }





--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pmcryptoRinvReloadInventory OBJECT-TYPE
  SYNTAX EkiOnOff
  MAX-ACCESS read-write
  STATUS current
  DESCRIPTION
        "Reload the inventory: This OID triggers an 
         inventory reload."
  ::= { pmcryptori 2 }

pmcryptoRinvHwPlatform OBJECT-TYPE
  SYNTAX DisplayString
  MAX-ACCESS read-only
  STATUS current
  DESCRIPTION
        "HW platform description: This OID contains the 
         description of the Hardware platform."
  ::= { pmcryptori 3 }
  
pmcryptoRinvModulePlatform OBJECT-TYPE
  SYNTAX DisplayString
  MAX-ACCESS read-only
  STATUS current
  DESCRIPTION
        "Module platform description: This OID contains the 
         description of the Module."
  ::= { pmcryptori 4 }
  
pmcryptoRinvSwPlatform OBJECT-TYPE
  SYNTAX DisplayString
  MAX-ACCESS read-only
  STATUS current
  DESCRIPTION
        "SW platform description: This OID contains the 
         description of the Software platform."
  ::= { pmcryptori 5 }
  
pmcryptoRinvGwPlatform OBJECT-TYPE
  SYNTAX DisplayString
  MAX-ACCESS read-only
  STATUS current
  DESCRIPTION
        "GW platform description: This OID contains the 
         description of the Gateware platform."
  ::= { pmcryptori 6 }


pmcryptoRinvSfpTable OBJECT-TYPE
      SYNTAX  SEQUENCE OF PmcryptoRinvSfpEntry
      MAX-ACCESS  not-accessible
      STATUS  current
      DESCRIPTION
              "List of the SFPs on the selected module"
      ::= { pmcryptoriTable 1 }

pmcryptoRinvSfpEntry OBJECT-TYPE
        SYNTAX  PmcryptoRinvSfpEntry
        MAX-ACCESS  not-accessible
        STATUS  current
        DESCRIPTION
              "Row definition for the SFP table"
        INDEX   { pmcryptoRinvSfpIndex }
        ::= { pmcryptoRinvSfpTable 1 }
    


PmcryptoRinvSfpEntry::=
        SEQUENCE {
          pmcryptoRinvSfpIndex 
              Integer32,
          pmcryptoRinvsfp
              DisplayString
        }


    pmcryptoRinvSfpIndex OBJECT-TYPE
        SYNTAX  Integer32(1..16)
        MAX-ACCESS  read-only
        STATUS  current
        DESCRIPTION
              "Index for SFP table"
        ::= { pmcryptoRinvSfpEntry 1 }


    pmcryptoRinvsfp OBJECT-TYPE
        SYNTAX  DisplayString
        MAX-ACCESS  read-only
        STATUS  current
        DESCRIPTION
              "Inventory for the SFP: This OID contains the inventory for the SFP"
        ::= { pmcryptoRinvSfpEntry 2 }




pmcryptoRinvLineTable OBJECT-TYPE
      SYNTAX  SEQUENCE OF PmcryptoRinvLineEntry
      MAX-ACCESS  not-accessible
      STATUS  current
      DESCRIPTION
              "List of the XFPs on the selected module"
      ::= { pmcryptoriTable 2 }

pmcryptoRinvLineEntry OBJECT-TYPE
        SYNTAX  PmcryptoRinvLineEntry
        MAX-ACCESS  not-accessible
        STATUS  current
        DESCRIPTION
              "Row definition for the XFP table"
        INDEX   { pmcryptoRinvLineIndex }
        ::= { pmcryptoRinvLineTable 1 }
    


PmcryptoRinvLineEntry::=
        SEQUENCE {
          pmcryptoRinvLineIndex 
              Integer32,
          pmcryptoRinvxfpLine
              DisplayString
        }


    pmcryptoRinvLineIndex OBJECT-TYPE
        SYNTAX  Integer32(1..16)
        MAX-ACCESS  read-only
        STATUS  current
        DESCRIPTION
              "Index for XFP table"
        ::= { pmcryptoRinvLineEntry 1 }


    pmcryptoRinvxfpLine OBJECT-TYPE
        SYNTAX  DisplayString
        MAX-ACCESS  read-only
        STATUS  current
        DESCRIPTION
              "Inventory for the XFP: This OID contains the inventory for the XFP"
        ::= { pmcryptoRinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pmcryptoAlmsynthAlm0 OBJECT IDENTIFIER ::= { pmcryptoAlmOtherCrit 0 }




pmcryptoAlmDefFuseB OBJECT-TYPE
	  SYNTAX EkiOnOff
	  MAX-ACCESS read-only
	  STATUS current
	  DESCRIPTION
        "
        Fuse B Fail :This OID indicates 
        that the fuse of the power input 
        B is in fail condition <Help> Status 
        of the Fuse B <Condtype> DEF_FUSE_B 
        <Probcause> powerProblem (36) <Alarmtype> 
        equipmentAlarm (5) <Polarity> (2) 
        "
	  ::= { pmcryptoAlmsynthAlm0 16 }



pmcryptoAlmDefFuseA OBJECT-TYPE
	  SYNTAX EkiOnOff
	  MAX-ACCESS read-only
	  STATUS current
	  DESCRIPTION
        "
        Fuse A Fail :This OID indicates 
        that the fuse of the power input 
        A is in fail condition <Help> Status 
        of the Fuse A <Condtype> DEF_FUSE_A 
        <Probcause> powerProblem (36) <Alarmtype> 
        equipmentAlarm (5) <Polarity> (2) 
        "
	  ::= { pmcryptoAlmsynthAlm0 15 }



pmcryptoAlmModGlobFail OBJECT-TYPE
	  SYNTAX EkiOnOff
	  MAX-ACCESS read-only
	  STATUS current
	  DESCRIPTION
        "
        Module Failure :This OID is set 
        on detection of a failure originating 
        from the RM <Help> This alarm is 
        set on detection of a failure originating 
        from the equipment <Condtype> MOD_GLOB_FAIL 
        <Probcause> other (1) <Alarmtype> 
        synthesisAlarm (12)  <Polarity> 
        (2) 
        "
	  ::= { pmcryptoAlmsynthAlm0 9 }



pmcryptoAlmFailFan OBJECT-TYPE
	  SYNTAX EkiOnOff
	  MAX-ACCESS read-only
	  STATUS current
	  DESCRIPTION
        "
        Fan Fail :This OID is at 1 when 
        any fail occurs on the fan tray 
        <Help> This alarm indicates that 
        the Fan tray module is in a failure 
        condition <Condtype> FAIL_FAN <Probcause> 
        equipmentMalfunction (16) <Alarmtype> 
        equipmentAlarm (5) <Polarity> (2) 
        "
	  ::= { pmcryptoAlmsynthAlm0 2 }



--- *****************************************************
---     LEAF for the synthAlm2 article
--- *****************************************************
pmcryptoAlmsynthAlm2 OBJECT IDENTIFIER ::= { pmcryptoAlmOtherNurg 2 }




pmcryptoAlmMaintenanceOn OBJECT-TYPE
	  SYNTAX EkiOnOff
	  MAX-ACCESS read-only
	  STATUS current
	  DESCRIPTION
        "
        Maintenance Mode :This OID indicates 
        that the RM is in maintenance mode. 
        <Help> This alarm indicates that 
        the maintenance mode is enabled 
        on the PM <Condtype> MAINTENANCE_ON 
        <Probcause> informationalStatus(1000) 
        <Alarmtype> other (1) <Polarity> 
        (2) 
        "
	  ::= { pmcryptoAlmsynthAlm2 5 }



pmcryptoAlmCorrelatOff OBJECT-TYPE
	  SYNTAX EkiOnOff
	  MAX-ACCESS read-only
	  STATUS current
	  DESCRIPTION
        "
        Not Used :This OID, when set,
         indicates that alarm correlation 
        is not being performed. <Condtype> 
        CORRELAT_OFF <Probcause> informationalStatus(1000) 
        <Alarmtype> other (1) <Polarity> 
        (2) 
        "
	  ::= { pmcryptoAlmsynthAlm2 4 }



pmcryptoAlmConfTableLoad OBJECT-TYPE
	  SYNTAX EkiOnOff
	  MAX-ACCESS read-only
	  STATUS current
	  DESCRIPTION
        "
        PM Configuration Load :This OID 
         is at 1 during the loading of
         configuration tables in the modules 
        RAM. <Condtype> CONF_TABLE_LOAD 
        <Probcause> informationalStatus(1000) 
        <Alarmtype> other (1) <Polarity> 
        (2) 
        "
	  ::= { pmcryptoAlmsynthAlm2 3 }



pmcryptoAlmInvUpload OBJECT-TYPE
	  SYNTAX EkiOnOff
	  MAX-ACCESS read-only
	  STATUS current
	  DESCRIPTION
        "
        Inventory Upload :This OID is
         at 1 during the uploading of PM 
        inventory information. <Condtype> 
        INV_UPLOAD <Probcause> informationalStatus(1000) 
        <Alarmtype> other (1) <Polarity> 
        (2) 
        "
	  ::= { pmcryptoAlmsynthAlm2 2 }



pmcryptoAlmConfTableSave OBJECT-TYPE
	  SYNTAX EkiOnOff
	  MAX-ACCESS read-only
	  STATUS current
	  DESCRIPTION
        "
        PM Configuration Save :This OID 
        is at 1 during the saving of a
         new configuration table in the 
        module Flash memory. <Condtype> 
        CONF_TABLE_SAVE <Probcause> informationalStatus(1000) 
        <Alarmtype> other (1) <Polarity> 
        (2) 
        "
	  ::= { pmcryptoAlmsynthAlm2 1 }



--- *********************************************************
---     TABLE for the pmcryptoAlmsynthAlmPort articles
--- *********************************************************

pmcryptoAlmsynthAlmPortTable OBJECT-TYPE
	SYNTAX  SEQUENCE OF PmcryptoAlmsynthAlmPortEntry
	MAX-ACCESS not-accessible
	STATUS current
	DESCRIPTION
        "
        List of pmcryptoAlmsynthAlmPort 
        Article
        "
	::= { pmcryptoAlmClientCrit 8 }


pmcryptoAlmsynthAlmPortEntry OBJECT-TYPE
	SYNTAX PmcryptoAlmsynthAlmPortEntry
	MAX-ACCESS not-accessible
	STATUS current
	DESCRIPTION
        "
        Row definition for the pmcryptoAlmsynthAlmPort 
        table
        "
	INDEX   { pmcryptoAlmsynthAlmPortIndex }
	::= { pmcryptoAlmsynthAlmPortTable 1 }


PmcryptoAlmsynthAlmPortEntry ::=
	SEQUENCE {
	pmcryptoAlmsynthAlmPortIndex
		INTEGER,
	pmcryptoAlmUpCsfPortn
		EkiOnOff,
	pmcryptoAlmFailAccPortn
		EkiOnOff,
	pmcryptoAlmSfpDdmAlmPortn
		EkiOnOff,
	pmcryptoAlmSfpDdmWarningPortn
		EkiOnOff,
	pmcryptoAlmDwCaisPortn
		EkiOnOff,
	pmcryptoAlmClientRemoteOosPortn
		EkiOnOff,
	pmcryptoAlmClientLocalOosPortn
		EkiOnOff,
	pmcryptoAlmDwLsdPortn
		EkiOnOff,
	pmcryptoAlmHwFailAccPortn
		EkiOnOff,
	pmcryptoAlmDdmAbsentPortn
		EkiOnOff,
	pmcryptoAlmSfpAbsentPortn
		EkiOnOff
	}


pmcryptoAlmsynthAlmPortIndex OBJECT-TYPE
	SYNTAX  INTEGER(0..128)
	MAX-ACCESS  read-only
	STATUS current
	DESCRIPTION
        "
        Index definition for the pmcryptoAlmsynthAlmPort 
        table
        "
	::= { pmcryptoAlmsynthAlmPortEntry 1 }


pmcryptoAlmUpCsfPortn OBJECT-TYPE
	SYNTAX  EkiOnOff
	MAX-ACCESS read-only
	STATUS current
	DESCRIPTION
        "
        Client Signal Fail Inserted :This 
        OID indicates a CSF has been inserted 
        in the upstream client port. <Help> 
        This status indicates if a Client 
        Signal Fail is currently inserted 
        on the line signal for this client 
        port <Condtype> UP_CSF_1 <Probcause> 
        informationalStatus(1000) <Alarmtype> 
        other (1) <Polarity> (2) 
        "
	::= { pmcryptoAlmsynthAlmPortEntry 17 }


pmcryptoAlmFailAccPortn OBJECT-TYPE
	SYNTAX  EkiOnOff
	MAX-ACCESS read-only
	STATUS current
	DESCRIPTION
        "
        Client Access Fail :This OID indicates 
        a failure on the Client port <Help> 
        This alarm indicates a failure
         on the Client port <Condtype>
         FAIL_ACC_1 <Probcause> equipmentMalfunction 
        (16) <Alarmtype> synthesisAlarm 
        (12)  <Polarity> (2) 
        "
	::= { pmcryptoAlmsynthAlmPortEntry 13 }


pmcryptoAlmSfpDdmAlmPortn OBJECT-TYPE
	SYNTAX  EkiOnOff
	MAX-ACCESS read-only
	STATUS current
	DESCRIPTION
        "
        Alarm On Client Trscv DDM :This 
        OID indicates an alarm is being 
        received from the Client Transceiver 
        DDM <Help> This alarm indicates 
        if a DDM Alarm has been detected 
        on the client transceiver <Condtype> 
        SFP_DDM_ALM_1 <Probcause> inputOutputDeviceError 
        (24) <Alarmtype> synthesisAlarm 
        (12)  <Polarity> (2) 
        "
	::= { pmcryptoAlmsynthAlmPortEntry 11 }


pmcryptoAlmSfpDdmWarningPortn OBJECT-TYPE
	SYNTAX  EkiOnOff
	MAX-ACCESS read-only
	STATUS current
	DESCRIPTION
        "
        Warning On Client Trscv DDM :This 
        OID indicates a warning is being 
        received from the Client Transceiver 
        DDM <Help> This alarm indicates 
        if a DDM Warning has been detected 
        on the client transceiver <Condtype> 
        SFP_DDM_WARNING_1 <Probcause> inputOutputDeviceError 
        (24) <Alarmtype> synthesisAlarm 
        (12)  <Polarity> (2) 
        "
	::= { pmcryptoAlmsynthAlmPortEntry 10 }


pmcryptoAlmDwCaisPortn OBJECT-TYPE
	SYNTAX  EkiOnOff
	MAX-ACCESS read-only
	STATUS current
	DESCRIPTION
        "
        Client AIS Inserted :This OID
         indicates a CAIS has been inserted 
        on the output client port. <Help> 
        This status indicates if a Client 
        Alarm Indication Signal is currently 
        inserted on the client interface 
        <Condtype> DW_CAIS_1 <Probcause> 
        informationalStatus(1000) <Alarmtype> 
        other (1) <Polarity> (2) 
        "
	::= { pmcryptoAlmsynthAlmPortEntry 9 }


pmcryptoAlmClientRemoteOosPortn OBJECT-TYPE
	SYNTAX  EkiOnOff
	MAX-ACCESS read-only
	STATUS current
	DESCRIPTION
        "
        Remote Client Port In Service
         :This OID indicates that the remote 
        Client port is In Service (1) or 
        Out of Service (2) <Help> This
         status indicates if the remote 
        client port is in service <Condtype> 
        CLIENT_REMOTE_OOS <Probcause> informationalStatus(1000) 
        <Alarmtype> other (1) <Polarity> 
        (2) 
        "
	::= { pmcryptoAlmsynthAlmPortEntry 8 }


pmcryptoAlmClientLocalOosPortn OBJECT-TYPE
	SYNTAX  EkiOnOff
	MAX-ACCESS read-only
	STATUS current
	DESCRIPTION
        "
        Local Client Port In Service :This 
        OID indicates that the local Client 
        port is In Service (1) or Out of 
        Service (2) <Help> This status
         indicates if the local client
         port is in service <Condtype>
         CLIENT_LOCAL_OOS <Probcause> informationalStatus(1000) 
        <Alarmtype> other (1) <Polarity> 
        (2)
        "
	::= { pmcryptoAlmsynthAlmPortEntry 7 }


pmcryptoAlmDwLsdPortn OBJECT-TYPE
	SYNTAX  EkiOnOff
	MAX-ACCESS read-only
	STATUS current
	DESCRIPTION
        "
        Client Trscv Laser Shutdown :This 
        OID indicates the Client transceiver 
        laser is shutdown <Help> This status 
        indicates if the client transceiver 
        laser is shutdown <Condtype> DW_LSD_1 
        <Probcause> other (1) <Alarmtype> 
        equipmentAlarm (5) <Polarity> (2) 
        "
	::= { pmcryptoAlmsynthAlmPortEntry 6 }


pmcryptoAlmHwFailAccPortn OBJECT-TYPE
	SYNTAX  EkiOnOff
	MAX-ACCESS read-only
	STATUS current
	DESCRIPTION
        "
        Client HW Fail :This OID indicates 
        a failure on client port, most
         probably caused by a HW issue. 
        <Help> This alarm indicates a failure 
        on client port, most probably caused 
        by a HW issue. <Condtype> HW_FAIL_ACC_1 
        <Probcause> equipmentMalfunction 
        (16) <Alarmtype> synthesisAlarm 
        (12)  <Polarity> (2) 
        "
	::= { pmcryptoAlmsynthAlmPortEntry 5 }


pmcryptoAlmDdmAbsentPortn OBJECT-TYPE
	SYNTAX  EkiOnOff
	MAX-ACCESS read-only
	STATUS current
	DESCRIPTION
        "
        DDM Supported On Client Trscv
         :This OID indicates that the Client 
        transceiver supports the Digital 
        Diagnostic Monitoring function
         <Help> This status indicates if 
        the client transceiver includes 
        the DDM feature <Condtype> DDM_ABSENT_1 
        <Probcause> informationalStatus(1000) 
        <Alarmtype> other (1) <Polarity> 
        (2) 
        "
	::= { pmcryptoAlmsynthAlmPortEntry 3 }


pmcryptoAlmSfpAbsentPortn OBJECT-TYPE
	SYNTAX  EkiOnOff
	MAX-ACCESS read-only
	STATUS current
	DESCRIPTION
        "
        Client Optical Module Absent :This 
        OID indicates that the Transceiver 
        is not present in the client port. 
        <Help> This alarm indicates if
         the client transceiver is not
         plugged <Condtype> SFP_ABSENT_1 
        <Probcause> inputOutputDeviceError 
        (24) <Alarmtype> equipmentAlarm 
        (5) <Polarity> (2) <Event> ObjectCDSingleClientInv
        "
	::= { pmcryptoAlmsynthAlmPortEntry 2 }


--- *********************************************************
---     TABLE for the pmcryptoAlmsynthAlmLine articles
--- *********************************************************

pmcryptoAlmsynthAlmLineTable OBJECT-TYPE
	SYNTAX  SEQUENCE OF PmcryptoAlmsynthAlmLineEntry
	MAX-ACCESS not-accessible
	STATUS current
	DESCRIPTION
        "
        List of pmcryptoAlmsynthAlmLine 
        Article
        "
	::= { pmcryptoAlmLineCrit 40 }


pmcryptoAlmsynthAlmLineEntry OBJECT-TYPE
	SYNTAX PmcryptoAlmsynthAlmLineEntry
	MAX-ACCESS not-accessible
	STATUS current
	DESCRIPTION
        "
        Row definition for the pmcryptoAlmsynthAlmLine 
        table
        "
	INDEX   { pmcryptoAlmsynthAlmLineIndex }
	::= { pmcryptoAlmsynthAlmLineTable 1 }


PmcryptoAlmsynthAlmLineEntry ::=
	SEQUENCE {
	pmcryptoAlmsynthAlmLineIndex
		INTEGER,
	pmcryptoAlmLineFailPortn
		EkiOnOff,
	pmcryptoAlmLineDdmAlmPortn
		EkiOnOff,
	pmcryptoAlmLineDdmWarningPortn
		EkiOnOff,
	pmcryptoAlmUpRdiInsPortn
		EkiOnOff,
	pmcryptoAlmLineLocalOosPortn
		EkiOnOff,
	pmcryptoAlmXfpTxOffPortn
		EkiOnOff,
	pmcryptoAlmLineHwFailPortn
		EkiOnOff,
	pmcryptoAlmXfpInitNotComplPortn
		EkiOnOff,
	pmcryptoAlmXfpAbsentPortn
		EkiOnOff
	}


pmcryptoAlmsynthAlmLineIndex OBJECT-TYPE
	SYNTAX  INTEGER(0..128)
	MAX-ACCESS  read-only
	STATUS current
	DESCRIPTION
        "
        Index definition for the pmcryptoAlmsynthAlmLine 
        table
        "
	::= { pmcryptoAlmsynthAlmLineEntry 1 }


pmcryptoAlmLineFailPortn OBJECT-TYPE
	SYNTAX  EkiOnOff
	MAX-ACCESS read-only
	STATUS current
	DESCRIPTION
        "
        Line Port Failure :This OID indicates 
        a failure on the line port <Help> 
        This alarm indicates a failure
         on the line port <Condtype> LINE_FAIL 
        <Probcause> equipmentMalfunction 
        (16) <Alarmtype> synthesisAlarm 
        (12)  <Polarity> (2) 
        "
	::= { pmcryptoAlmsynthAlmLineEntry 13 }


pmcryptoAlmLineDdmAlmPortn OBJECT-TYPE
	SYNTAX  EkiOnOff
	MAX-ACCESS read-only
	STATUS current
	DESCRIPTION
        "
        Alarm On Line Optical Module DDM 
        :This OID indicates an alarm is 
        present coming out of Line transceiver 
        DDM <Help> This alarm indicates 
        if a DDM Alarm has been detected 
        on the line transceiver <Condtype> 
        LINE_DDM_ALM <Probcause> inputOutputDeviceError 
        (24) <Alarmtype> equipmentAlarm 
        (5) <Polarity> (2) 
        "
	::= { pmcryptoAlmsynthAlmLineEntry 11 }


pmcryptoAlmLineDdmWarningPortn OBJECT-TYPE
	SYNTAX  EkiOnOff
	MAX-ACCESS read-only
	STATUS current
	DESCRIPTION
        "
        Warning On Line Optical Module 
        DDM :This OID indicates a warning 
        is present coming out of Line transceiver 
        DDM <Help> This alarm indicates 
        if a DDM Warning has been detected 
        on the line transceiver <Condtype> 
        LINE_DDM_WARNING <Probcause> inputOutputDeviceError 
        (24) <Alarmtype> equipmentAlarm 
        (5) <Polarity> (2) 
        "
	::= { pmcryptoAlmsynthAlmLineEntry 10 }


pmcryptoAlmUpRdiInsPortn OBJECT-TYPE
	SYNTAX  EkiOnOff
	MAX-ACCESS read-only
	STATUS current
	DESCRIPTION
        "
        MS-RDI/L-RDI Inserted On Line
         :This OID indicates an upstream 
        MS-RDI/L-RDI has been inserted
         in the outgoing 10 Gb/s SDH/SONET 
        signal. <Help> This status indicates 
        if a MS-RDI/L-RDI is currently
         inserted on the line interface. 
        <Condtype> UP_RDI_INS <Probcause> 
        informationalStatus(1000) <Alarmtype> 
        other (1) <Polarity> (2) 
        "
	::= { pmcryptoAlmsynthAlmLineEntry 9 }


pmcryptoAlmLineLocalOosPortn OBJECT-TYPE
	SYNTAX  EkiOnOff
	MAX-ACCESS read-only
	STATUS current
	DESCRIPTION
        "
        Line Port In Service :This OID 
        indicates that the Line port is 
        In Service (1) of Out or Service 
        (2) <Help> This status indicates 
        if the line port is in service
         <Condtype> LINE_LOCAL_OOS <Probcause> 
        informationalStatus(1000) <Alarmtype> 
        other (1) <Polarity> (2) 
        "
	::= { pmcryptoAlmsynthAlmLineEntry 7 }


pmcryptoAlmXfpTxOffPortn OBJECT-TYPE
	SYNTAX  EkiOnOff
	MAX-ACCESS read-only
	STATUS current
	DESCRIPTION
        "
        Line Trscv Laser Shutdown :This 
        OID indicates the Line transceiver 
        laser is shutdown <Help> This status 
        indicates if the Line transceiver 
        laser is shutdown <Condtype> XFP_TX_OFF 
        <Probcause> other (1) <Alarmtype> 
        equipmentAlarm (5) <Polarity> (2) 
        "
	::= { pmcryptoAlmsynthAlmLineEntry 6 }


pmcryptoAlmLineHwFailPortn OBJECT-TYPE
	SYNTAX  EkiOnOff
	MAX-ACCESS read-only
	STATUS current
	DESCRIPTION
        "
        Line Port HW Failure :This OID 
        indicates a failure on line port, 
        most probably caused by a HW issue 
        <Help> This alarm indicates a failure 
        on line port, most probably caused 
        by a HW issue <Condtype> LINE_HW_FAIL 
        <Probcause> equipmentMalfunction 
        (16) <Alarmtype> synthesisAlarm 
        (12)  <Polarity> (2) 
        "
	::= { pmcryptoAlmsynthAlmLineEntry 5 }


pmcryptoAlmXfpInitNotComplPortn OBJECT-TYPE
	SYNTAX  EkiOnOff
	MAX-ACCESS read-only
	STATUS current
	DESCRIPTION
        "
        Line Optical Module Ready :This 
        OID indicates that the optical
         interface is not operational.
         <Help> This status indicates if 
        the line transceiver has been correctly 
        initialized <Condtype> XFP_INIT_NOT_COMPL 
        <Probcause> equipmentMalfunction 
        (16) <Alarmtype> equipmentAlarm 
        (5) <Polarity> (2) 
        "
	::= { pmcryptoAlmsynthAlmLineEntry 3 }


pmcryptoAlmXfpAbsentPortn OBJECT-TYPE
	SYNTAX  EkiOnOff
	MAX-ACCESS read-only
	STATUS current
	DESCRIPTION
        "
        Line Optical Module Absent :This 
        OID indicates that the line optical 
        interface is not present. <Help> 
        This alarm indicates if the line 
        transceiver is not plugged <Condtype> 
        XFP_ABSENT <Probcause> inputOutputDeviceError 
        (24) <Alarmtype> equipmentAlarm 
        (5) <Polarity> (2) <Event> ObjectCDINV
        "
	::= { pmcryptoAlmsynthAlmLineEntry 2 }


--- *********************************************************
---     TABLE for the pmcryptoAlmlineQsfpAlmDdm articles
--- *********************************************************

pmcryptoAlmlineQsfpAlmDdmTable OBJECT-TYPE
	SYNTAX  SEQUENCE OF PmcryptoAlmlineQsfpAlmDdmEntry
	MAX-ACCESS not-accessible
	STATUS current
	DESCRIPTION
        "
        List of pmcryptoAlmlineQsfpAlmDdm 
        Article
        "
	::= { pmcryptoAlmLineNurg 72 }


pmcryptoAlmlineQsfpAlmDdmEntry OBJECT-TYPE
	SYNTAX PmcryptoAlmlineQsfpAlmDdmEntry
	MAX-ACCESS not-accessible
	STATUS current
	DESCRIPTION
        "
        Row definition for the pmcryptoAlmlineQsfpAlmDdm 
        table
        "
	INDEX   { pmcryptoAlmlineQsfpAlmDdmIndex }
	::= { pmcryptoAlmlineQsfpAlmDdmTable 1 }


PmcryptoAlmlineQsfpAlmDdmEntry ::=
	SEQUENCE {
	pmcryptoAlmlineQsfpAlmDdmIndex
		INTEGER,
	pmcryptoAlmLineRxPwrHighAlmPortn
		EkiOnOff,
	pmcryptoAlmLineRxPwrLowAlmPortn
		EkiOnOff,
	pmcryptoAlmLineTempHighAlmPortn
		EkiOnOff,
	pmcryptoAlmLineTempLowAlmPortn
		EkiOnOff,
	pmcryptoAlmLineVccHighAlmPortn
		EkiOnOff,
	pmcryptoAlmLineVccLowAlmPortn
		EkiOnOff,
	pmcryptoAlmLineTxBiasHighAlmPortn
		EkiOnOff,
	pmcryptoAlmLineTxBiasLowAlmPortn
		EkiOnOff,
	pmcryptoAlmLineTxPwrHighAlmPortn
		EkiOnOff,
	pmcryptoAlmLineTxPwLowAlmPortn
		EkiOnOff
	}


pmcryptoAlmlineQsfpAlmDdmIndex OBJECT-TYPE
	SYNTAX  INTEGER(0..128)
	MAX-ACCESS  read-only
	STATUS current
	DESCRIPTION
        "
        Index definition for the pmcryptoAlmlineQsfpAlmDdm 
        table
        "
	::= { pmcryptoAlmlineQsfpAlmDdmEntry 1 }


pmcryptoAlmLineRxPwrHighAlmPortn OBJECT-TYPE
	SYNTAX  EkiOnOff
	MAX-ACCESS read-only
	STATUS current
	DESCRIPTION
        "
        Client Trscv Rx Power High Alarm 
        :This OID indicates that the Trscv 
        input power is higher than the
         threshold value written in the 
        Trscv EEPROM <Help> Alarm indicating 
        that the Trscv input power is higher 
        than the threshold value written 
        in the Trscv EEPROM <Condtype>
         LINE_RX_PWR_HIGH_ALM_1 <Probcause> 
        receiveFailure (41) <Alarmtype> 
        equipmentAlarm (5) <Polarity> (2) 
        "
	::= { pmcryptoAlmlineQsfpAlmDdmEntry 17 }


pmcryptoAlmLineRxPwrLowAlmPortn OBJECT-TYPE
	SYNTAX  EkiOnOff
	MAX-ACCESS read-only
	STATUS current
	DESCRIPTION
        "
        Client Trscv Rx Power Low Alarm 
        :This OID indicates that the Trscv 
        input power is lower than the threshold 
        value written in the Trscv EEPROM 
        <Help> Alarm indicating that the 
        Trscv input power is lower than 
        the threshold value written in
         the Trscv EEPROM <Condtype> LINE_RX_PWR_LOW_ALM_1 
        <Probcause> receiveFailure (41) 
        <Alarmtype> equipmentAlarm (5)
         <Polarity> (2) 
        "
	::= { pmcryptoAlmlineQsfpAlmDdmEntry 16 }


pmcryptoAlmLineTempHighAlmPortn OBJECT-TYPE
	SYNTAX  EkiOnOff
	MAX-ACCESS read-only
	STATUS current
	DESCRIPTION
        "
        Client Trscv Temp High Alarm :This 
        OID indicates that the Trscv temperature 
        is higher than the threshold value 
        written in the Trscv EEPROM <Help> 
        Alarm indicating that the Trscv 
        temperature is higher than the
         threshold value written in the 
        Trscv EEPROM <Condtype> LINE_TEMP_HIGH_ALM_1 
        <Probcause> temperatureUnacceptable 
        (51) <Alarmtype> equipmentAlarm 
        (5) <Polarity> (2) 
        "
	::= { pmcryptoAlmlineQsfpAlmDdmEntry 9 }


pmcryptoAlmLineTempLowAlmPortn OBJECT-TYPE
	SYNTAX  EkiOnOff
	MAX-ACCESS read-only
	STATUS current
	DESCRIPTION
        "
        Client Trscv Temp Low Alarm :This 
        OID indicates that the Trscv temperature 
        is lower than the threshold value 
        written in the Trscv EEPROM <Help> 
        Alarm indicating that the Trscv 
        temperature is lower than the threshold 
        value written in the Trscv EEPROM 
        <Condtype> LINE_TEMP_LOW_ALM_1
         <Probcause> temperatureUnacceptable 
        (51) <Alarmtype> equipmentAlarm 
        (5) <Polarity> (2) 
        "
	::= { pmcryptoAlmlineQsfpAlmDdmEntry 8 }


pmcryptoAlmLineVccHighAlmPortn OBJECT-TYPE
	SYNTAX  EkiOnOff
	MAX-ACCESS read-only
	STATUS current
	DESCRIPTION
        "
        Client Trscv Power Supply High 
        Alarm :This OID indicates that
         the Trscv power supply is higher 
        than the threshold value written 
        in the Trscv EEPROM <Help> Alarm 
        indicating that the Trscv power 
        supply is higher than the threshold 
        value written in the Trscv EEPROM 
        <Condtype> LINE_VCC_HIGH_ALM_1
         <Probcause> powerProblem (36)
         <Alarmtype> equipmentAlarm (5) 
        <Polarity> (2) 
        "
	::= { pmcryptoAlmlineQsfpAlmDdmEntry 7 }


pmcryptoAlmLineVccLowAlmPortn OBJECT-TYPE
	SYNTAX  EkiOnOff
	MAX-ACCESS read-only
	STATUS current
	DESCRIPTION
        "
        Client Trscv Power Supply Low
         Alarm :This OID indicates that 
        the Trscv power supply is lower 
        than the threshold value written 
        in the Trscv EEPROM <Help> Alarm 
        indicating that the Trscv power 
        supply is lower than the threshold 
        value written in the Trscv EEPROM 
        <Condtype> LINE_VCC_LOW_ALM_1 <Probcause> 
        powerProblem (36) <Alarmtype> equipmentAlarm 
        (5) <Polarity> (2) 
        "
	::= { pmcryptoAlmlineQsfpAlmDdmEntry 6 }


pmcryptoAlmLineTxBiasHighAlmPortn OBJECT-TYPE
	SYNTAX  EkiOnOff
	MAX-ACCESS read-only
	STATUS current
	DESCRIPTION
        "
        Client Trscv Bias High Alarm :This 
        OID indicates that the Trscv laser 
        bias current is higher than the 
        threshold value written in the
         Trscv EEPROM <Help> Alarm indicating 
        that the Trscv laser bias current 
        is higher than the threshold value 
        written in the Trscv EEPROM <Condtype> 
        LINE_TX_BIAS_HIGH_ALM_1 <Probcause> 
        transmitterFailure (56) <Alarmtype> 
        equipmentAlarm (5) <Polarity> (2) 
        "
	::= { pmcryptoAlmlineQsfpAlmDdmEntry 5 }


pmcryptoAlmLineTxBiasLowAlmPortn OBJECT-TYPE
	SYNTAX  EkiOnOff
	MAX-ACCESS read-only
	STATUS current
	DESCRIPTION
        "
        Client Trscv Bias Low Alarm :This 
        OID indicates that the Trscv laser 
        bias current is lower than the
         threshold value written in the 
        Trscv EEPROM <Help> Alarm indicating 
        that the Trscv laser bias current 
        is lower than the threshold value 
        written in the Trscv EEPROM <Condtype> 
        LINE_TX_BIAS_LOW_ALM_1 <Probcause> 
        transmitterFailure (56) <Alarmtype> 
        equipmentAlarm (5) <Polarity> (2) 
        "
	::= { pmcryptoAlmlineQsfpAlmDdmEntry 4 }


pmcryptoAlmLineTxPwrHighAlmPortn OBJECT-TYPE
	SYNTAX  EkiOnOff
	MAX-ACCESS read-only
	STATUS current
	DESCRIPTION
        "
        Client Trscv Tx Power High Alarm 
        :This OID indicates that the Trscv 
        output power is higher than the 
        threshold value written in the
         Trscv EEPROM <Help> Alarm indicating 
        that the Trscv output power is
         higher than the threshold value 
        written in the Trscv EEPROM <Condtype> 
        LINE_TX_PWR_HIGH_ALM_1 <Probcause> 
        transmitterFailure (56) <Alarmtype> 
        equipmentAlarm (5) <Polarity> (2) 
        "
	::= { pmcryptoAlmlineQsfpAlmDdmEntry 3 }


pmcryptoAlmLineTxPwLowAlmPortn OBJECT-TYPE
	SYNTAX  EkiOnOff
	MAX-ACCESS read-only
	STATUS current
	DESCRIPTION
        "
        Client Trscv Tx Power Low Alarm 
        :This OID indicates that the Trscv 
        output power is lower than the
         threshold value written in the 
        Trscv EEPROM <Help> Alarm indicating 
        that the Trscv output power is
         lower than the threshold value 
        written in the Trscv EEPROM <Condtype> 
        LINE_TX_PW_LOW_ALM_1 <Probcause> 
        transmitterFailure (56) <Alarmtype> 
        equipmentAlarm (5) <Polarity> (2) 
        "
	::= { pmcryptoAlmlineQsfpAlmDdmEntry 2 }


--- *****************************************************
---     LEAF for the msaModuleState article
--- *****************************************************
pmcryptoAlmmsaModuleState OBJECT IDENTIFIER ::= { pmcryptoAlmOtherCrit 78 }




pmcryptoAlmMsaFault OBJECT-TYPE
	  SYNTAX EkiOnOff
	  MAX-ACCESS read-only
	  STATUS current
	  DESCRIPTION
        "
        Line Trscv Fault :This OID indicates 
        the Line Trscv is in Fault state 
        <Help> Status indicating the Line 
        Trscv is in Fault state <Condtype> 
        MSA_FAULT <Probcause> informationalStatus(1000) 
        <Alarmtype> other (1) <Polarity> 
        (2) 
        "
	  ::= { pmcryptoAlmmsaModuleState 7 }



pmcryptoAlmMsaReady OBJECT-TYPE
	  SYNTAX EkiOnOff
	  MAX-ACCESS read-only
	  STATUS current
	  DESCRIPTION
        "
        Line Trscv Ready :This OID indicates 
        the Line Trscv is ready to operate 
        <Help> Status indicating the Line 
        Trscv is ready to operate <Condtype> 
        MSA_READY <Probcause> informationalStatus(1000) 
        <Alarmtype> other (1) <Polarity> 
        (2) 
        "
	  ::= { pmcryptoAlmmsaModuleState 6 }



--- *********************************************************
---     TABLE for the pmcryptoAlmlineQsfpWarnDdm articles
--- *********************************************************

pmcryptoAlmlineQsfpWarnDdmTable OBJECT-TYPE
	SYNTAX  SEQUENCE OF PmcryptoAlmlineQsfpWarnDdmEntry
	MAX-ACCESS not-accessible
	STATUS current
	DESCRIPTION
        "
        List of pmcryptoAlmlineQsfpWarnDdm 
        Article
        "
	::= { pmcryptoAlmLineNurg 104 }


pmcryptoAlmlineQsfpWarnDdmEntry OBJECT-TYPE
	SYNTAX PmcryptoAlmlineQsfpWarnDdmEntry
	MAX-ACCESS not-accessible
	STATUS current
	DESCRIPTION
        "
        Row definition for the pmcryptoAlmlineQsfpWarnDdm 
        table
        "
	INDEX   { pmcryptoAlmlineQsfpWarnDdmIndex }
	::= { pmcryptoAlmlineQsfpWarnDdmTable 1 }


PmcryptoAlmlineQsfpWarnDdmEntry ::=
	SEQUENCE {
	pmcryptoAlmlineQsfpWarnDdmIndex
		INTEGER,
	pmcryptoAlmLineRxPwrHighWngPortn
		EkiOnOff,
	pmcryptoAlmLineRxPwrLowWngPortn
		EkiOnOff,
	pmcryptoAlmLineTempHighWngPortn
		EkiOnOff,
	pmcryptoAlmLineTempLowWngPortn
		EkiOnOff,
	pmcryptoAlmLineVccHighWngPortn
		EkiOnOff,
	pmcryptoAlmLineVccLowWngPortn
		EkiOnOff,
	pmcryptoAlmLineTxBiasHighWngPortn
		EkiOnOff,
	pmcryptoAlmLineTxBiasLowWngPortn
		EkiOnOff,
	pmcryptoAlmLineTxPwrHighWngPortn
		EkiOnOff,
	pmcryptoAlmLineTxPwLowWngPortn
		EkiOnOff
	}


pmcryptoAlmlineQsfpWarnDdmIndex OBJECT-TYPE
	SYNTAX  INTEGER(0..128)
	MAX-ACCESS  read-only
	STATUS current
	DESCRIPTION
        "
        Index definition for the pmcryptoAlmlineQsfpWarnDdm 
        table
        "
	::= { pmcryptoAlmlineQsfpWarnDdmEntry 1 }


pmcryptoAlmLineRxPwrHighWngPortn OBJECT-TYPE
	SYNTAX  EkiOnOff
	MAX-ACCESS read-only
	STATUS current
	DESCRIPTION
        "
        Client Trscv Rx Power High Warning 
        :This OID indicates that the Trscv 
        input power is higher than the
         threshold value written in the 
        Trscv EEPROM <Help> Warning indicating 
        that the Trscv input power is higher 
        than the threshold value written 
        in the Trscv EEPROM <Condtype>
         LINE_RX_PWR_HIGH_WNG_1 <Probcause> 
        receiveFailure (41) <Alarmtype> 
        equipmentAlarm (5) <Polarity> (2) 
        "
	::= { pmcryptoAlmlineQsfpWarnDdmEntry 17 }


pmcryptoAlmLineRxPwrLowWngPortn OBJECT-TYPE
	SYNTAX  EkiOnOff
	MAX-ACCESS read-only
	STATUS current
	DESCRIPTION
        "
        Client Trscv Rx Power Low Warning 
        :This OID indicates that the Trscv 
        input power is lower than the threshold 
        value written in the Trscv EEPROM 
        <Help> Warning indicating that
         the Trscv input power is lower 
        than the threshold value written 
        in the Trscv EEPROM <Condtype>
         LINE_RX_PWR_LOW_WNG_1 <Probcause> 
        receiveFailure (41) <Alarmtype> 
        equipmentAlarm (5) <Polarity> (2) 
        "
	::= { pmcryptoAlmlineQsfpWarnDdmEntry 16 }


pmcryptoAlmLineTempHighWngPortn OBJECT-TYPE
	SYNTAX  EkiOnOff
	MAX-ACCESS read-only
	STATUS current
	DESCRIPTION
        "
        Client Trscv Temp High Warning 
        :This OID indicates that the Trscv 
        temperature is higher than the
         threshold value written in the 
        Trscv EEPROM <Help> Warning indicating 
        that the Trscv temperature is higher 
        than the threshold value written 
        in the Trscv EEPROM <Condtype>
         LINE_TEMP_HIGH_WNG_1 <Probcause> 
        temperatureUnacceptable (51) <Alarmtype> 
        equipmentAlarm (5) <Polarity> (2) 
        "
	::= { pmcryptoAlmlineQsfpWarnDdmEntry 9 }


pmcryptoAlmLineTempLowWngPortn OBJECT-TYPE
	SYNTAX  EkiOnOff
	MAX-ACCESS read-only
	STATUS current
	DESCRIPTION
        "
        Client Trscv Temp Low Warning
         :This OID indicates that the Trscv 
        temperature is lower than the threshold 
        value written in the Trscv EEPROM 
        <Help> Warning indicating that
         the Trscv temperature is lower 
        than the threshold value written 
        in the Trscv EEPROM <Condtype>
         LINE_TEMP_LOW_WNG_1 <Probcause> 
        temperatureUnacceptable (51) <Alarmtype> 
        equipmentAlarm (5) <Polarity> (2) 
        "
	::= { pmcryptoAlmlineQsfpWarnDdmEntry 8 }


pmcryptoAlmLineVccHighWngPortn OBJECT-TYPE
	SYNTAX  EkiOnOff
	MAX-ACCESS read-only
	STATUS current
	DESCRIPTION
        "
        Client Trscv Power Supply High 
        Warning :This OID indicates that 
        the Trscv power supply is higher 
        than the threshold value written 
        in the Trscv EEPROM <Help> Warning 
        indicating that the Trscv power 
        supply is higher than the threshold 
        value written in the Trscv EEPROM 
        <Condtype> LINE_VCC_HIGH_WNG_1
         <Probcause> powerProblem (36)
         <Alarmtype> equipmentAlarm (5) 
        <Polarity> (2) 
        "
	::= { pmcryptoAlmlineQsfpWarnDdmEntry 7 }


pmcryptoAlmLineVccLowWngPortn OBJECT-TYPE
	SYNTAX  EkiOnOff
	MAX-ACCESS read-only
	STATUS current
	DESCRIPTION
        "
        Client Trscv Power Supply Low
         Warning :This OID indicates that 
        the Trscv power supply is lower 
        than the threshold value written 
        in the Trscv EEPROM <Help> Warning 
        indicating that the Trscv power 
        supply is lower than the threshold 
        value written in the Trscv EEPROM 
        <Condtype> LINE_VCC_LOW_WNG_1 <Probcause> 
        powerProblem (36) <Alarmtype> equipmentAlarm 
        (5) <Polarity> (2) 
        "
	::= { pmcryptoAlmlineQsfpWarnDdmEntry 6 }


pmcryptoAlmLineTxBiasHighWngPortn OBJECT-TYPE
	SYNTAX  EkiOnOff
	MAX-ACCESS read-only
	STATUS current
	DESCRIPTION
        "
        Client Trscv Bias High Warning 
        :This OID indicates that the Trscv 
        laser bias current is higher than 
        the threshold value written in
         the Trscv EEPROM <Help> Warning 
        indicating that the Trscv laser 
        bias current is higher than the 
        threshold value written in the
         Trscv EEPROM <Condtype> LINE_TX_BIAS_HIGH_WNG_1 
        <Probcause> transmitterFailure
         (56) <Alarmtype> equipmentAlarm 
        (5) <Polarity> (2) 
        "
	::= { pmcryptoAlmlineQsfpWarnDdmEntry 5 }


pmcryptoAlmLineTxBiasLowWngPortn OBJECT-TYPE
	SYNTAX  EkiOnOff
	MAX-ACCESS read-only
	STATUS current
	DESCRIPTION
        "
        Client Trscv Bias Low Warning
         :This OID indicates that the Trscv 
        laser bias current is lower than 
        the threshold value written in
         the Trscv EEPROM <Help> Warning 
        indicating that the Trscv laser 
        bias current is lower than the
         threshold value written in the 
        Trscv EEPROM <Condtype> LINE_TX_BIAS_LOW_WNG_1 
        <Probcause> transmitterFailure
         (56) <Alarmtype> equipmentAlarm 
        (5) <Polarity> (2) 
        "
	::= { pmcryptoAlmlineQsfpWarnDdmEntry 4 }


pmcryptoAlmLineTxPwrHighWngPortn OBJECT-TYPE
	SYNTAX  EkiOnOff
	MAX-ACCESS read-only
	STATUS current
	DESCRIPTION
        "
        Client Trscv Tx Power High Warning 
        :This OID indicates that the Trscv 
        output power is higher than the 
        threshold value written in the
         Trscv EEPROM <Help> Warning indicating 
        that the Trscv output power is
         higher than the threshold value 
        written in the Trscv EEPROM <Condtype> 
        LINE_TX_PWR_HIGH_WNG_1 <Probcause> 
        transmitterFailure (56) <Alarmtype> 
        equipmentAlarm (5) <Polarity> (2) 
        "
	::= { pmcryptoAlmlineQsfpWarnDdmEntry 3 }


pmcryptoAlmLineTxPwLowWngPortn OBJECT-TYPE
	SYNTAX  EkiOnOff
	MAX-ACCESS read-only
	STATUS current
	DESCRIPTION
        "
        Client Trscv Tx Power Low Warning 
        :This OID indicates that the Trscv 
        output power is lower than the
         threshold value written in the 
        Trscv EEPROM <Help> Warning indicating 
        that the Trscv output power is
         lower than the threshold value 
        written in the Trscv EEPROM <Condtype> 
        LINE_TX_PW_LOW_WNG_1 <Probcause> 
        transmitterFailure (56) <Alarmtype> 
        equipmentAlarm (5) <Polarity> (2) 
        "
	::= { pmcryptoAlmlineQsfpWarnDdmEntry 2 }


--- *********************************************************
---     TABLE for the pmcryptoAlmclientHostLaneFault articles
--- *********************************************************

pmcryptoAlmclientHostLaneFaultTable OBJECT-TYPE
	SYNTAX  SEQUENCE OF PmcryptoAlmclientHostLaneFaultEntry
	MAX-ACCESS not-accessible
	STATUS current
	DESCRIPTION
        "
        List of pmcryptoAlmclientHostLaneFault 
        Article
        "
	::= { pmcryptoAlmClientUrg 152 }


pmcryptoAlmclientHostLaneFaultEntry OBJECT-TYPE
	SYNTAX PmcryptoAlmclientHostLaneFaultEntry
	MAX-ACCESS not-accessible
	STATUS current
	DESCRIPTION
        "
        Row definition for the pmcryptoAlmclientHostLaneFault 
        table
        "
	INDEX   { pmcryptoAlmclientHostLaneFaultIndex }
	::= { pmcryptoAlmclientHostLaneFaultTable 1 }


PmcryptoAlmclientHostLaneFaultEntry ::=
	SEQUENCE {
	pmcryptoAlmclientHostLaneFaultIndex
		INTEGER,
	pmcryptoAlmOtu2eProtocDetectedPortn
		EkiOnOff,
	pmcryptoAlmOtu2ProtocDetectedPortn
		EkiOnOff,
	pmcryptoAlm10gbeProtocDetectedPortn
		EkiOnOff,
	pmcryptoAlmStm64ProtocDetectedPortn
		EkiOnOff,
	pmcryptoAlmRfDetectedPortn
		EkiOnOff,
	pmcryptoAlmLfDetectedPortn
		EkiOnOff,
	pmcryptoAlmClientLaneTxFifoErrorPortn
		EkiOnOff,
	pmcryptoAlmClientTxHostLolPortn
		EkiOnOff,
	pmcryptoAlmClientCsfDetectedPortn
		EkiOnOff,
	pmcryptoAlmClientLanesNotAlignedPortn
		EkiOnOff,
	pmcryptoAlmClientLanes6466UnlockPortn
		EkiOnOff,
	pmcryptoAlmClientLanesMarkerUnlockPortn
		EkiOnOff,
	pmcryptoAlmClientInputLossOfSigPortn
		EkiOnOff,
	pmcryptoAlmClientLossOfSyncPortn
		EkiOnOff
	}


pmcryptoAlmclientHostLaneFaultIndex OBJECT-TYPE
	SYNTAX  INTEGER(0..128)
	MAX-ACCESS  read-only
	STATUS current
	DESCRIPTION
        "
        Index definition for the pmcryptoAlmclientHostLaneFault 
        table
        "
	::= { pmcryptoAlmclientHostLaneFaultEntry 1 }


pmcryptoAlmOtu2eProtocDetectedPortn OBJECT-TYPE
	SYNTAX  EkiOnOff
	MAX-ACCESS read-only
	STATUS current
	DESCRIPTION
        "
        OTU2e Protocol Detected :This
         OID indicates an OTU2e  Protocol 
        detected on the Client Port <Help> 
        Status indicating a OTU2e protocol 
        received on the Client side <Condtype> 
        OTU2E_PROTOC_DETECTED <Probcause> 
        informationalStatus(1000) <Alarmtype> 
        other(1) <Polarity> (2)
        "
	::= { pmcryptoAlmclientHostLaneFaultEntry 17 }


pmcryptoAlmOtu2ProtocDetectedPortn OBJECT-TYPE
	SYNTAX  EkiOnOff
	MAX-ACCESS read-only
	STATUS current
	DESCRIPTION
        "
        OTU2 Protocol Detected :This OID 
        indicates an OTU2  Protocol detected 
        on the Client Port <Help> Status 
        indicating a OTU2 protocol received 
        on the Client side <Condtype> OTU2_PROTOC_DETECTED 
        <Probcause> informationalStatus(1000) 
        <Alarmtype> other(1) <Polarity> 
        (2)
        "
	::= { pmcryptoAlmclientHostLaneFaultEntry 16 }


pmcryptoAlm10gbeProtocDetectedPortn OBJECT-TYPE
	SYNTAX  EkiOnOff
	MAX-ACCESS read-only
	STATUS current
	DESCRIPTION
        "
        10GbE Protocol Detected :This
         OID indicates a 10GbE Protocol 
        detected on the Client Port <Help> 
        Status indicating a 10GbE protocol 
        received on the Client side <Condtype> 
        10GBE_PROTOC_DETECTED <Probcause> 
        informationalStatus(1000) <Alarmtype> 
        other(1) <Polarity> (2)
        "
	::= { pmcryptoAlmclientHostLaneFaultEntry 15 }


pmcryptoAlmStm64ProtocDetectedPortn OBJECT-TYPE
	SYNTAX  EkiOnOff
	MAX-ACCESS read-only
	STATUS current
	DESCRIPTION
        "
        STM64 Protocol Detected :This
         OID indicates a STM64 Protocol 
        detected on the Client Port <Help> 
        Status indicating a STM64 protocol 
        received on the Client side <Condtype> 
        STM64_PROTOC_DETECTED <Probcause> 
        informationalStatus(1000) <Alarmtype> 
        other(1) <Polarity> (2)
        "
	::= { pmcryptoAlmclientHostLaneFaultEntry 14 }


pmcryptoAlmRfDetectedPortn OBJECT-TYPE
	SYNTAX  EkiOnOff
	MAX-ACCESS read-only
	STATUS current
	DESCRIPTION
        "
        Remote Fault Signal Detected :This 
        OID indicates a Remote Fault Signal 
        is detected on the client input 
        port<Help> This alarm indicates 
        a Remote Fault Signal is detected 
        on the client input port <Condtype> 
        RF_DETECTED <Probcause> receiverFailure 
        (42) <Alarmtype> equipmentAlarm 
        (5) <Polarity> (2)
        "
	::= { pmcryptoAlmclientHostLaneFaultEntry 13 }


pmcryptoAlmLfDetectedPortn OBJECT-TYPE
	SYNTAX  EkiOnOff
	MAX-ACCESS read-only
	STATUS current
	DESCRIPTION
        "
        Local Fault Signal Detected :This 
        OID indicates a Local Fault Signal 
        is detected on the client input 
        port<Help> This alarm indicates 
        a Local Fault Signal is detected 
        on the client input port <Condtype> 
        LF_DETECTED <Probcause> receiverFailure 
        (42) <Alarmtype> equipmentAlarm 
        (5) <Polarity> (2)
        "
	::= { pmcryptoAlmclientHostLaneFaultEntry 12 }


pmcryptoAlmClientLaneTxFifoErrorPortn OBJECT-TYPE
	SYNTAX  EkiOnOff
	MAX-ACCESS read-only
	STATUS current
	DESCRIPTION
        "
        Client Host Lane Tx FIFO Error 
        :This OID indicates a Tx FIFO Error 
        on the Client Trscv Host Lane <Help> 
        Alarm indicating a Tx FIFO Error 
        on the Client Trscv Host Lane <Condtype> 
        CLIENT_LANE_TX_FIFO_ERROR <Probcause> 
        receiverFailure (42) <Alarmtype> 
        equipmentAlarm (5) <Polarity> (2) 
        "
	::= { pmcryptoAlmclientHostLaneFaultEntry 11 }


pmcryptoAlmClientTxHostLolPortn OBJECT-TYPE
	SYNTAX  EkiOnOff
	MAX-ACCESS read-only
	STATUS current
	DESCRIPTION
        "
        Client Host Lane Tx Loss Of Lock 
        :This OID indicates a Tx Loss of 
        Lock on the Client Trscv Host Lane 
        <Help> Alarm indicating a Tx Loss 
        of Lock on the Client Trscv Host 
        Lane <Condtype> CLIENT_TX_HOST_LOL 
        <Probcause> receiverFailure (42) 
        <Alarmtype> equipmentAlarm (5)
         <Polarity> (2) 
        "
	::= { pmcryptoAlmclientHostLaneFaultEntry 10 }


pmcryptoAlmClientCsfDetectedPortn OBJECT-TYPE
	SYNTAX  EkiOnOff
	MAX-ACCESS read-only
	STATUS current
	DESCRIPTION
        "
        Client Signal Fail Detected :This 
        OID indicates that a CSF has been 
        detected on client port in the
         downstream direction   <Help>
          This alarm indicates if a Client 
        Signal Fail has been detected in 
        the incoming line frame for this 
        client port <Condtype> CLIENT_CSF_DETECTED 
        <Probcause> receiveFailure (41) 
        <Alarmtype> other(1) <Polarity> 
        (2)
        "
	::= { pmcryptoAlmclientHostLaneFaultEntry 7 }


pmcryptoAlmClientLanesNotAlignedPortn OBJECT-TYPE
	SYNTAX  EkiOnOff
	MAX-ACCESS read-only
	STATUS current
	DESCRIPTION
        "
        Client Lanes Not Aligned :This 
        OID indicates the Client lanes
         are not aligned <Help> Alarm indicating 
        the Client lanes are not aligned 
        <Condtype> CLIENT_LANES_NOT_ALIGNED 
        <Probcause> receiveFailure (41) 
        <Alarmtype> integrityViolation
         (7) <Polarity> (2) 
        "
	::= { pmcryptoAlmclientHostLaneFaultEntry 6 }


pmcryptoAlmClientLanes6466UnlockPortn OBJECT-TYPE
	SYNTAX  EkiOnOff
	MAX-ACCESS read-only
	STATUS current
	DESCRIPTION
        "
        Client Lanes 64/66b Unlock :This 
        OID indicates the Client 64/66b 
        decoder is not lock <Help> Alarm 
        indicating the Client 64/66b decoder 
        is not lock <Condtype> CLIENT_LANES_64_66_UNLOCK 
        <Probcause> receiveFailure (41) 
        <Alarmtype> integrityViolation
         (7) <Polarity> (2) 
        "
	::= { pmcryptoAlmclientHostLaneFaultEntry 5 }


pmcryptoAlmClientLanesMarkerUnlockPortn OBJECT-TYPE
	SYNTAX  EkiOnOff
	MAX-ACCESS read-only
	STATUS current
	DESCRIPTION
        "
        Client Lanes Marker Unlock :This 
        OID indicates the Client lanes
         marker alignment is not lock <Help> 
        Alarm indicating the Client lanes 
        marker alignment is not lock <Condtype> 
        CLIENT_LANES_MARKER_UNLOCK <Probcause> 
        receiveFailure (41) <Alarmtype> 
        integrityViolation (7) <Polarity> 
        (2) 
        "
	::= { pmcryptoAlmclientHostLaneFaultEntry 4 }


pmcryptoAlmClientInputLossOfSigPortn OBJECT-TYPE
	SYNTAX  EkiOnOff
	MAX-ACCESS read-only
	STATUS current
	DESCRIPTION
        "
        Client Input Loss Of Signal :This 
        OID indicates a Loss of Signal
         is detected on the Client Trscv 
        <Help> Alarm indicating a Loss
         of Signal is detected on the Client 
        Trscv <Condtype> CLIENT_INPUT_LOSS_OF_SIG 
        <Probcause> receiveFailure (41) 
        <Alarmtype> physicalViolation (9) 
        <Polarity> (2) 
        "
	::= { pmcryptoAlmclientHostLaneFaultEntry 3 }


pmcryptoAlmClientLossOfSyncPortn OBJECT-TYPE
	SYNTAX  EkiOnOff
	MAX-ACCESS read-only
	STATUS current
	DESCRIPTION
        "
        Client Frame Alignment Loss :This 
        OID indicates the module is not 
        aligned with the incoming Client 
        signal <Help> Alarm indicating
         the module is not aligned with 
        the incoming client signal <Condtype> 
        CLIENT_LOSS_OF_SYNC <Probcause> 
        receiveFailure (41) <Alarmtype> 
        integrityViolation (7) <Polarity> 
        (2) 
        "
	::= { pmcryptoAlmclientHostLaneFaultEntry 2 }


--- *********************************************************
---     TABLE for the pmcryptoAlmlineHostLaneFault articles
--- *********************************************************

pmcryptoAlmlineHostLaneFaultTable OBJECT-TYPE
	SYNTAX  SEQUENCE OF PmcryptoAlmlineHostLaneFaultEntry
	MAX-ACCESS not-accessible
	STATUS current
	DESCRIPTION
        "
        List of pmcryptoAlmlineHostLaneFault 
        Article
        "
	::= { pmcryptoAlmLineUrg 196 }


pmcryptoAlmlineHostLaneFaultEntry OBJECT-TYPE
	SYNTAX PmcryptoAlmlineHostLaneFaultEntry
	MAX-ACCESS not-accessible
	STATUS current
	DESCRIPTION
        "
        Row definition for the pmcryptoAlmlineHostLaneFault 
        table
        "
	INDEX   { pmcryptoAlmlineHostLaneFaultIndex }
	::= { pmcryptoAlmlineHostLaneFaultTable 1 }


PmcryptoAlmlineHostLaneFaultEntry ::=
	SEQUENCE {
	pmcryptoAlmlineHostLaneFaultIndex
		INTEGER,
	pmcryptoAlmLineOtu4DlomPortn
		EkiOnOff,
	pmcryptoAlmLineOchr4DlosPPortn
		EkiOnOff,
	pmcryptoAlmLineEncryptionFailurePortn
		EkiOnOff,
	pmcryptoAlmClientOtu4DtimPortn
		EkiOnOff,
	pmcryptoAlmOtu4DdegPortn
		EkiOnOff,
	pmcryptoAlmLineSmIaeDetectedPortn
		EkiOnOff,
	pmcryptoAlmLineSmIaeInsertedPortn
		EkiOnOff,
	pmcryptoAlmLineSmBdiDetectedPortn
		EkiOnOff,
	pmcryptoAlmLineSmBdiInsertedPortn
		EkiOnOff,
	pmcryptoAlmLineLossOfFramePortn
		EkiOnOff,
	pmcryptoAlmLineInputLossOfSignalPortn
		EkiOnOff
	}


pmcryptoAlmlineHostLaneFaultIndex OBJECT-TYPE
	SYNTAX  INTEGER(0..128)
	MAX-ACCESS  read-only
	STATUS current
	DESCRIPTION
        "
        Index definition for the pmcryptoAlmlineHostLaneFault 
        table
        "
	::= { pmcryptoAlmlineHostLaneFaultEntry 1 }


pmcryptoAlmLineOtu4DlomPortn OBJECT-TYPE
	SYNTAX  EkiOnOff
	MAX-ACCESS read-only
	STATUS current
	DESCRIPTION
        "
        OTU4 DLOM :This OID indicates
         that a Loss Of Multiframe has
         been detected on line port <Help> 
         This alarm indicates if a Loss 
        Of Multiframe has been detected 
        on the line port <Condtype> LINE_OTU4_DLOM 
        <Probcause> equipmentMalfunction(16) 
        <Alarmtype> equipmentAlarm (5)
         <Polarity> (2) 
        "
	::= { pmcryptoAlmlineHostLaneFaultEntry 17 }


pmcryptoAlmLineOchr4DlosPPortn OBJECT-TYPE
	SYNTAX  EkiOnOff
	MAX-ACCESS read-only
	STATUS current
	DESCRIPTION
        "
        Ochr4 - DLOS-P :This OID indicates 
        that a Transmitter failure has
         been detected on line port <Help> 
         This alarm indicates if a Transmitter 
        Failure has been detected on the 
        line port <Condtype> LINE_OCHR4_DLOS_P 
        <Probcause> equipmentMalfunction(16) 
        <Alarmtype> other (1) <Polarity> 
        (2) 
        "
	::= { pmcryptoAlmlineHostLaneFaultEntry 12 }


pmcryptoAlmLineEncryptionFailurePortn OBJECT-TYPE
	SYNTAX  EkiOnOff
	MAX-ACCESS read-only
	STATUS current
	DESCRIPTION
        "
        Encryption Failure :This OID indicates 
        the encryption mechanism failed, 
        impacting the traffic (the line 
        traffic is down). <Help> This alarm 
        indicates the encryption mechanism 
        failed, impacting the traffic (the 
        line traffic is down). <Condtype> 
        LINE_ENCRYPTION_FAILURE <Probcause> 
        authenticationFailure(59) <Alarmtype> 
        integrityViolation(7)  <Polarity> 
        (2) 
        "
	::= { pmcryptoAlmlineHostLaneFaultEntry 10 }


pmcryptoAlmClientOtu4DtimPortn OBJECT-TYPE
	SYNTAX  EkiOnOff
	MAX-ACCESS read-only
	STATUS current
	DESCRIPTION
        "
        OTU4 DTIM :This OID indicates
         that a Trace Identifier Mismatch 
        has been detected on line port
         <Help>  This alarm indicates if 
        a Trace Identifier Mismatch has 
        been detected on the line port
         <Condtype> CLIENT_OTU4_DTIM <Probcause> 
        other(1) <Alarmtype> other (1)
         <Polarity> (2) 
        "
	::= { pmcryptoAlmlineHostLaneFaultEntry 9 }


pmcryptoAlmOtu4DdegPortn OBJECT-TYPE
	SYNTAX  EkiOnOff
	MAX-ACCESS read-only
	STATUS current
	DESCRIPTION
        "
        OTU4 DDEG :This OID indicates
         that a Signal Degrade has been 
        detected on line port <Help>  This 
        alarm indicates if a Signal Degrade 
        has been detected upon threshold 
        and confirmation parameters on
         the line port <Condtype> OTU4_DDEG 
        <Probcause> degradedSignal(13)
         <Alarmtype> other (1) <Polarity> 
        (2) 
        "
	::= { pmcryptoAlmlineHostLaneFaultEntry 8 }


pmcryptoAlmLineSmIaeDetectedPortn OBJECT-TYPE
	SYNTAX  EkiOnOff
	MAX-ACCESS read-only
	STATUS current
	DESCRIPTION
        "
        Line SM IAE Detected :This OID 
        indicates a SM Incoming Alignment 
        Error is detected on the incoming 
        Line signal <Help> Alarm indicating 
        a SM Incoming Alignment Error is 
        detected on the incoming Line signal 
        <Condtype> LINE_SM_IAE_DETECTED 
        <Probcause> receiveFailure (41) 
        <Alarmtype> integrityViolation
         (7) <Polarity> (2) 
        "
	::= { pmcryptoAlmlineHostLaneFaultEntry 7 }


pmcryptoAlmLineSmIaeInsertedPortn OBJECT-TYPE
	SYNTAX  EkiOnOff
	MAX-ACCESS read-only
	STATUS current
	DESCRIPTION
        "
        Line SM IAE Inserted :This OID 
        indicates a SM Incoming Alignment 
        Error is inserted on the outgoing 
        Line signal <Help> Status indicating 
        a SM Incoming Alignment Error is 
        inserted on the outgoing Line signal 
        <Condtype> LINE_SM_IAE_INSERTED 
        <Probcause> informationalStatus(1000) 
        <Alarmtype> other (1) <Polarity> 
        (2) 
        "
	::= { pmcryptoAlmlineHostLaneFaultEntry 6 }


pmcryptoAlmLineSmBdiDetectedPortn OBJECT-TYPE
	SYNTAX  EkiOnOff
	MAX-ACCESS read-only
	STATUS current
	DESCRIPTION
        "
        Line SM BDI Detected :This OID 
        indicates a SM Backward Defect
         Indication is detected on the
         incoming Line signal <Help> Alarm 
        indicating a SM Backward Defect 
        Indication is detected on the incoming 
        Line signal <Condtype> LINE_SM_BDI_DETECTED 
        <Probcause> receiveFailure (41) 
        <Alarmtype> integrityViolation
         (7) <Polarity> (2) 
        "
	::= { pmcryptoAlmlineHostLaneFaultEntry 5 }


pmcryptoAlmLineSmBdiInsertedPortn OBJECT-TYPE
	SYNTAX  EkiOnOff
	MAX-ACCESS read-only
	STATUS current
	DESCRIPTION
        "
        Line SM BDI Inserted :This OID 
        indicates a SM Backward Defect
         Indication is inserted on the
         outgoing Line signal <Help> Status 
        indicating a SM Backward Defect 
        Indication is inserted on the outgoing 
        Line signal <Condtype> LINE_SM_BDI_INSERTED 
        <Probcause> informationalStatus(1000) 
        <Alarmtype> other (1) <Polarity> 
        (2) 
        "
	::= { pmcryptoAlmlineHostLaneFaultEntry 4 }


pmcryptoAlmLineLossOfFramePortn OBJECT-TYPE
	SYNTAX  EkiOnOff
	MAX-ACCESS read-only
	STATUS current
	DESCRIPTION
        "
        Line Loss Of Frame :This OID indicates 
        the module is not aligned with
         the incoming Line signal <Help> 
        Alarm indicating the module is
         not aligned with the incoming
         Line signal <Condtype> LINE_LOSS_OF_FRAME 
        <Probcause> receiveFailure (41) 
        <Alarmtype> integrityViolation
         (7) <Polarity> (2) 
        "
	::= { pmcryptoAlmlineHostLaneFaultEntry 3 }


pmcryptoAlmLineInputLossOfSignalPortn OBJECT-TYPE
	SYNTAX  EkiOnOff
	MAX-ACCESS read-only
	STATUS current
	DESCRIPTION
        "
        Line Input Loss Of Signal :This 
        OID indicates a Loss of Signal
         is detected on the Line Trscv
         <Help> Alarm indicating a Loss 
        of Signal is detected on the Line 
        Trscv <Condtype> LINE_INPUT_LOSS_OF_SIGNAL 
        <Probcause> receiveFailure (41) 
        <Alarmtype> physicalViolation (9) 
        <Polarity> (2) 
        "
	::= { pmcryptoAlmlineHostLaneFaultEntry 2 }


--- *********************************************************
---     TABLE for the pmcryptoAlmlineOdu4Alm articles
--- *********************************************************

pmcryptoAlmlineOdu4AlmTable OBJECT-TYPE
	SYNTAX  SEQUENCE OF PmcryptoAlmlineOdu4AlmEntry
	MAX-ACCESS not-accessible
	STATUS current
	DESCRIPTION
        "
        List of pmcryptoAlmlineOdu4Alm 
        Article
        "
	::= { pmcryptoAlmLineUrg 208 }


pmcryptoAlmlineOdu4AlmEntry OBJECT-TYPE
	SYNTAX PmcryptoAlmlineOdu4AlmEntry
	MAX-ACCESS not-accessible
	STATUS current
	DESCRIPTION
        "
        Row definition for the pmcryptoAlmlineOdu4Alm 
        table
        "
	INDEX   { pmcryptoAlmlineOdu4AlmIndex }
	::= { pmcryptoAlmlineOdu4AlmTable 1 }


PmcryptoAlmlineOdu4AlmEntry ::=
	SEQUENCE {
	pmcryptoAlmlineOdu4AlmIndex
		INTEGER,
	pmcryptoAlmLineOdu4DlckPortn
		EkiOnOff,
	pmcryptoAlmLineOdu4IlckPortn
		EkiOnOff,
	pmcryptoAlmLineOdu4DbdiPortn
		EkiOnOff,
	pmcryptoAlmLineOdu4IbdiPortn
		EkiOnOff,
	pmcryptoAlmLineOdu4DociPortn
		EkiOnOff,
	pmcryptoAlmLineOdu4IociPortn
		EkiOnOff,
	pmcryptoAlmLineOdu4DaisPortn
		EkiOnOff,
	pmcryptoAlmLineOdu4DtimPortn
		EkiOnOff,
	pmcryptoAlmLineOdu4IaisPortn
		EkiOnOff,
	pmcryptoAlmLineOdu4DdegPortn
		EkiOnOff,
	pmcryptoAlmLineOdu4DplmPortn
		EkiOnOff
	}


pmcryptoAlmlineOdu4AlmIndex OBJECT-TYPE
	SYNTAX  INTEGER(0..128)
	MAX-ACCESS  read-only
	STATUS current
	DESCRIPTION
        "
        Index definition for the pmcryptoAlmlineOdu4Alm 
        table
        "
	::= { pmcryptoAlmlineOdu4AlmEntry 1 }


pmcryptoAlmLineOdu4DlckPortn OBJECT-TYPE
	SYNTAX  EkiOnOff
	MAX-ACCESS read-only
	STATUS current
	DESCRIPTION
        "
        ODU4 DLCK :This OID indicates
         that a Locked Indication has been 
        detected on line port <Help>  This 
        alarm indicates if a Locked Indication 
        has been detected on the line port 
        <Condtype> LINE_ODU4_DLCK <Probcause> 
        other(1) <Alarmtype> other(1) <Polarity> 
        (2)
        "
	::= { pmcryptoAlmlineOdu4AlmEntry 17 }


pmcryptoAlmLineOdu4IlckPortn OBJECT-TYPE
	SYNTAX  EkiOnOff
	MAX-ACCESS read-only
	STATUS current
	DESCRIPTION
        "
        ODU4 ILCK :This OID indicates
         that a Locked Indication has been 
        inserted on line port <Help>  This 
        alarm indicates if a Locked Indication 
        has been inserted on the line port 
        <Condtype> LINE_ODU4_ILCK <Probcause> 
        other(1) <Alarmtype> other(1) <Polarity> 
        (2)
        "
	::= { pmcryptoAlmlineOdu4AlmEntry 16 }


pmcryptoAlmLineOdu4DbdiPortn OBJECT-TYPE
	SYNTAX  EkiOnOff
	MAX-ACCESS read-only
	STATUS current
	DESCRIPTION
        "
        ODU4 DBDI :This OID indicates
         that a Backward Defect Indication 
        has been detected on line port<Help> 
         This alarm indicates if a Backward 
        Defect Indication has been detected 
        on the line port <Condtype> LINE_ODU4_DBDI 
        <Probcause> other(1) <Alarmtype> 
        other(1) <Polarity> (2)
        "
	::= { pmcryptoAlmlineOdu4AlmEntry 15 }


pmcryptoAlmLineOdu4IbdiPortn OBJECT-TYPE
	SYNTAX  EkiOnOff
	MAX-ACCESS read-only
	STATUS current
	DESCRIPTION
        "
        ODU4 IBDI :This OID indicates
         that a Backward Defect Indication 
        has been inserted on line port
         <Help>  This alarm indicates if 
        a Backward Defect Indication has 
        been inserted on the line port
         <Condtype> LINE_ODU4_IBDI <Probcause> 
        other(1) <Alarmtype> other(1) <Polarity> 
        (2)
        "
	::= { pmcryptoAlmlineOdu4AlmEntry 14 }


pmcryptoAlmLineOdu4DociPortn OBJECT-TYPE
	SYNTAX  EkiOnOff
	MAX-ACCESS read-only
	STATUS current
	DESCRIPTION
        "
        ODU4 DOCI :This OID indicates
         that a Open Connection has been 
        detected on line port <Help>  This 
        alarm indicates if an Open Connection 
        Indication has been detected on 
        the line port <Condtype> LINE_ODU4_DOCI 
        <Probcause> other(1) <Alarmtype> 
        other(1) <Polarity> (2)
        "
	::= { pmcryptoAlmlineOdu4AlmEntry 13 }


pmcryptoAlmLineOdu4IociPortn OBJECT-TYPE
	SYNTAX  EkiOnOff
	MAX-ACCESS read-only
	STATUS current
	DESCRIPTION
        "
        ODU4 IOCI :This OID indicates
         that an Open Connection has been 
        inserted on line port <Help>  This 
        alarm indicates if an Open Connection 
        Indication has been inserted on 
        the line port <Condtype> LINE_ODU4_IOCI 
        <Probcause> other(1) <Alarmtype> 
        other(1) <Polarity> (2)
        "
	::= { pmcryptoAlmlineOdu4AlmEntry 12 }


pmcryptoAlmLineOdu4DaisPortn OBJECT-TYPE
	SYNTAX  EkiOnOff
	MAX-ACCESS read-only
	STATUS current
	DESCRIPTION
        "
        ODU4 DAIS :This OID indicates
         that a Alarm Indication SIgnal 
        has been detected on line port<Help> 
         This alarm indicates if an Alarm 
        Indication Signal has been detected 
        on the line port <Condtype> LINE_ODU4_DAIS 
        <Probcause> equipmentMalfunction(16) 
        <Alarmtype> equipmentAlarm (5)
         <Polarity> (2) 
        "
	::= { pmcryptoAlmlineOdu4AlmEntry 10 }


pmcryptoAlmLineOdu4DtimPortn OBJECT-TYPE
	SYNTAX  EkiOnOff
	MAX-ACCESS read-only
	STATUS current
	DESCRIPTION
        "
        ODU4 DTIM :This OID indicates
         that a Trace Identifier Mismatch 
        has been detected on line port<Help> 
         This alarm indicates if an Trace 
        Identifier Mismatch has been detected 
        on the line port <Condtype> LINE_ODU4_DTIM 
        <Probcause> equipmentMalfunction(16) 
        <Alarmtype> equipmentAlarm (5)
         <Polarity> (2) 
        "
	::= { pmcryptoAlmlineOdu4AlmEntry 9 }


pmcryptoAlmLineOdu4IaisPortn OBJECT-TYPE
	SYNTAX  EkiOnOff
	MAX-ACCESS read-only
	STATUS current
	DESCRIPTION
        "
        ODU4 IAIS :This OID indicates
         that an Alarm Indication Signal 
        has been inserted on line port
         <Help>  This alarm indicates if 
        an Alarm Indication Signal has
         been inserted on the line port 
        <Condtype> LINE_ODU4_IAIS <Probcause> 
        equipmentMalfunction(16) <Alarmtype> 
        equipmentAlarm (5) <Polarity> (2) 
        "
	::= { pmcryptoAlmlineOdu4AlmEntry 8 }


pmcryptoAlmLineOdu4DdegPortn OBJECT-TYPE
	SYNTAX  EkiOnOff
	MAX-ACCESS read-only
	STATUS current
	DESCRIPTION
        "
        ODU4 DDEG :This OID indicates
         that a Signal Degrade has been 
        detected on line port<Help> Alarm 
        indicating a Signal Degrade upon 
        threshold and confirmation parameters 
        <Condtype> LINE_ODU4_DDEG <Probcause> 
        degradedSignal(13) <Alarmtype>
         other(1) <Polarity> (2)
        "
	::= { pmcryptoAlmlineOdu4AlmEntry 6 }


pmcryptoAlmLineOdu4DplmPortn OBJECT-TYPE
	SYNTAX  EkiOnOff
	MAX-ACCESS read-only
	STATUS current
	DESCRIPTION
        "
        ODU4 DPLM :This OID indicates
         a Payload Mismatch is detected 
        on the line port<Help> Alarm indicating 
        a Payload Mismatch <Condtype> LINE_ODU4_DPLM 
        <Probcause> receiveFailure (41) 
        <Alarmtype> equipmentAlarm (5)
         <Polarity> (2) 
        "
	::= { pmcryptoAlmlineOdu4AlmEntry 4 }


--- *********************************************************
---     TABLE for the pmcryptoAlmclientSfpAlmDdm articles
--- *********************************************************

pmcryptoAlmclientSfpAlmDdmTable OBJECT-TYPE
	SYNTAX  SEQUENCE OF PmcryptoAlmclientSfpAlmDdmEntry
	MAX-ACCESS not-accessible
	STATUS current
	DESCRIPTION
        "
        List of pmcryptoAlmclientSfpAlmDdm 
        Article
        "
	::= { pmcryptoAlmClientUrg 240 }


pmcryptoAlmclientSfpAlmDdmEntry OBJECT-TYPE
	SYNTAX PmcryptoAlmclientSfpAlmDdmEntry
	MAX-ACCESS not-accessible
	STATUS current
	DESCRIPTION
        "
        Row definition for the pmcryptoAlmclientSfpAlmDdm 
        table
        "
	INDEX   { pmcryptoAlmclientSfpAlmDdmIndex }
	::= { pmcryptoAlmclientSfpAlmDdmTable 1 }


PmcryptoAlmclientSfpAlmDdmEntry ::=
	SEQUENCE {
	pmcryptoAlmclientSfpAlmDdmIndex
		INTEGER,
	pmcryptoAlmRxPwrHighAlaPortn
		EkiOnOff,
	pmcryptoAlmRxPwrLowAlaPortn
		EkiOnOff,
	pmcryptoAlmTempHighAlaPortn
		EkiOnOff,
	pmcryptoAlmTempLowAlaPortn
		EkiOnOff,
	pmcryptoAlmVccHighAlaPortn
		EkiOnOff,
	pmcryptoAlmVccLowAlaPortn
		EkiOnOff,
	pmcryptoAlmTxBiasHighAlaPortn
		EkiOnOff,
	pmcryptoAlmTxBiasLowAlaPortn
		EkiOnOff,
	pmcryptoAlmTxPwrHighAlaPortn
		EkiOnOff,
	pmcryptoAlmTxPwrLowAlaPortn
		EkiOnOff
	}


pmcryptoAlmclientSfpAlmDdmIndex OBJECT-TYPE
	SYNTAX  INTEGER(0..128)
	MAX-ACCESS  read-only
	STATUS current
	DESCRIPTION
        "
        Index definition for the pmcryptoAlmclientSfpAlmDdm 
        table
        "
	::= { pmcryptoAlmclientSfpAlmDdmEntry 1 }


pmcryptoAlmRxPwrHighAlaPortn OBJECT-TYPE
	SYNTAX  EkiOnOff
	MAX-ACCESS read-only
	STATUS current
	DESCRIPTION
        "
        Client Trscv Rx Power High :This 
        OID indicates that the Trscv input 
        power of port is higher than the 
        threshold value written in the
         Trscv EEPROM <Help> Alarm indicating 
        that the Trscv input power of port 
        is higher than the threshold value 
        written in the Trscv EEPROM <Condtype> 
        RX_PWR_HIGH_ALA_1 <Probcause> receiveFailure 
        (41) <Alarmtype> equipmentAlarm 
        (5) <Polarity> (2) 
        "
	::= { pmcryptoAlmclientSfpAlmDdmEntry 17 }


pmcryptoAlmRxPwrLowAlaPortn OBJECT-TYPE
	SYNTAX  EkiOnOff
	MAX-ACCESS read-only
	STATUS current
	DESCRIPTION
        "
        Client Trscv Rx Power Low :This 
        OID indicates that the Trscv input 
        power of port is lower than the 
        threshold value written in the
         Trscv EEPROM <Help> Alarm indicating 
        that the Trscv input power of port 
        is lower than the threshold value 
        written in the Trscv EEPROM <Condtype> 
        RX_PWR_LOW_ALA_1 <Probcause> receiveFailure 
        (41) <Alarmtype> equipmentAlarm 
        (5) <Polarity> (2) 
        "
	::= { pmcryptoAlmclientSfpAlmDdmEntry 16 }


pmcryptoAlmTempHighAlaPortn OBJECT-TYPE
	SYNTAX  EkiOnOff
	MAX-ACCESS read-only
	STATUS current
	DESCRIPTION
        "
        Client Trscv Temp High :This OID 
        indicates that the Trscv temperature 
        of port is higher than the threshold 
        value written in the Trscv EEPROM 
        <Help> Alarm indicating that the 
        Trscv temperature of port is higher 
        than the threshold value written 
        in the Trscv EEPROM <Condtype>
         TEMP_HIGH_ALA_1 <Probcause> temperatureUnacceptable 
        (51) <Alarmtype> equipmentAlarm 
        (5) <Polarity> (2) 
        "
	::= { pmcryptoAlmclientSfpAlmDdmEntry 9 }


pmcryptoAlmTempLowAlaPortn OBJECT-TYPE
	SYNTAX  EkiOnOff
	MAX-ACCESS read-only
	STATUS current
	DESCRIPTION
        "
        Client Trscv Temp Low :This OID 
        indicates that the Trscv temperature 
        of port is lower than the threshold 
        value written in the Trscv EEPROM 
        <Help> Alarm indicating that the 
        Trscv temperature of port is lower 
        than the threshold value written 
        in the Trscv EEPROM <Condtype>
         TEMP_LOW_ALA_1 <Probcause> temperatureUnacceptable 
        (51) <Alarmtype> equipmentAlarm 
        (5) <Polarity> (2) 
        "
	::= { pmcryptoAlmclientSfpAlmDdmEntry 8 }


pmcryptoAlmVccHighAlaPortn OBJECT-TYPE
	SYNTAX  EkiOnOff
	MAX-ACCESS read-only
	STATUS current
	DESCRIPTION
        "
        Client Trscv Power Supply High 
        :This OID indicates that the Trscv 
        power supply of port is higher
         than the threshold value written 
        in the Trscv EEPROM <Help> Alarm 
        indicating that the Trscv power 
        supply of port is higher than the 
        threshold value written in the
         Trscv EEPROM <Condtype> VCC_HIGH_ALA_1 
        <Probcause> powerProblem (36) <Alarmtype> 
        equipmentAlarm (5) <Polarity> (2) 
        "
	::= { pmcryptoAlmclientSfpAlmDdmEntry 7 }


pmcryptoAlmVccLowAlaPortn OBJECT-TYPE
	SYNTAX  EkiOnOff
	MAX-ACCESS read-only
	STATUS current
	DESCRIPTION
        "
        Client Trscv Power Supply Low
         :This OID indicates that the Trscv 
        power supply of port is lower than 
        the threshold value written in
         the Trscv EEPROM <Help> Alarm
         indicating that the Trscv power 
        supply of port is lower than the 
        threshold value written in the
         Trscv EEPROM <Condtype> VCC_LOW_ALA_1 
        <Probcause> powerProblem (36) <Alarmtype> 
        equipmentAlarm (5) <Polarity> (2) 
        "
	::= { pmcryptoAlmclientSfpAlmDdmEntry 6 }


pmcryptoAlmTxBiasHighAlaPortn OBJECT-TYPE
	SYNTAX  EkiOnOff
	MAX-ACCESS read-only
	STATUS current
	DESCRIPTION
        "
        Client Trscv Bias High :This OID 
        indicates that the Trscv laser
         bias current of port is higher 
        than the threshold value written 
        in the Trscv EEPROM <Help> Alarm 
        indicating that the Trscv laser 
        bias current of port is higher
         than the threshold value written 
        in the Trscv EEPROM <Condtype>
         TX_BIAS_HIGH_ALA_1 <Probcause> 
        transmitterFailure (56) <Alarmtype> 
        equipmentAlarm (5) <Polarity> (2) 
        "
	::= { pmcryptoAlmclientSfpAlmDdmEntry 5 }


pmcryptoAlmTxBiasLowAlaPortn OBJECT-TYPE
	SYNTAX  EkiOnOff
	MAX-ACCESS read-only
	STATUS current
	DESCRIPTION
        "
        Client Trscv Bias Low :This OID 
        indicates that the Trscv laser
         bias current of port is lower
         than the threshold value written 
        in the Trscv EEPROM <Help> Alarm 
        indicating that the Trscv laser 
        bias current of port is lower than 
        the threshold value written in
         the Trscv EEPROM <Condtype> TX_BIAS_LOW_ALA_1 
        <Probcause> transmitterFailure
         (56) <Alarmtype> equipmentAlarm 
        (5) <Polarity> (2) 
        "
	::= { pmcryptoAlmclientSfpAlmDdmEntry 4 }


pmcryptoAlmTxPwrHighAlaPortn OBJECT-TYPE
	SYNTAX  EkiOnOff
	MAX-ACCESS read-only
	STATUS current
	DESCRIPTION
        "
        Client Trscv Tx Power High :This 
        OID indicates that the Trscv output 
        power of port is higher than the 
        threshold value written in the
         Trscv EEPROM <Help> Alarm indicating 
        that the Trscv output power of
         port is higher than the threshold 
        value written in the Trscv EEPROM 
        <Condtype> TX_PWR_HIGH_ALA_1 <Probcause> 
        transmitterFailure (56) <Alarmtype> 
        equipmentAlarm (5) <Polarity> (2) 
        "
	::= { pmcryptoAlmclientSfpAlmDdmEntry 3 }


pmcryptoAlmTxPwrLowAlaPortn OBJECT-TYPE
	SYNTAX  EkiOnOff
	MAX-ACCESS read-only
	STATUS current
	DESCRIPTION
        "
        Client Trscv Tx Power Low :This 
        OID indicates that the Trscv output 
        power of port is lower than the 
        threshold value written in the
         Trscv EEPROM <Help> Alarm indicating 
        that the Trscv output power of
         port is lower than the threshold 
        value written in the Trscv EEPROM 
        <Condtype> TX_PWR_LOW_ALA_1 <Probcause> 
        transmitterFailure (56) <Alarmtype> 
        equipmentAlarm (5) <Polarity> (2) 
        "
	::= { pmcryptoAlmclientSfpAlmDdmEntry 2 }


--- *********************************************************
---     TABLE for the pmcryptoAlmclientSfpWarnDdm articles
--- *********************************************************

pmcryptoAlmclientSfpWarnDdmTable OBJECT-TYPE
	SYNTAX  SEQUENCE OF PmcryptoAlmclientSfpWarnDdmEntry
	MAX-ACCESS not-accessible
	STATUS current
	DESCRIPTION
        "
        List of pmcryptoAlmclientSfpWarnDdm 
        Article
        "
	::= { pmcryptoAlmClientNurg 272 }


pmcryptoAlmclientSfpWarnDdmEntry OBJECT-TYPE
	SYNTAX PmcryptoAlmclientSfpWarnDdmEntry
	MAX-ACCESS not-accessible
	STATUS current
	DESCRIPTION
        "
        Row definition for the pmcryptoAlmclientSfpWarnDdm 
        table
        "
	INDEX   { pmcryptoAlmclientSfpWarnDdmIndex }
	::= { pmcryptoAlmclientSfpWarnDdmTable 1 }


PmcryptoAlmclientSfpWarnDdmEntry ::=
	SEQUENCE {
	pmcryptoAlmclientSfpWarnDdmIndex
		INTEGER,
	pmcryptoAlmRxPwrHighWngPortn
		EkiOnOff,
	pmcryptoAlmRxPwrLowWngPortn
		EkiOnOff,
	pmcryptoAlmTempHighWngPortn
		EkiOnOff,
	pmcryptoAlmTempLowWngPortn
		EkiOnOff,
	pmcryptoAlmVccHighWngPortn
		EkiOnOff,
	pmcryptoAlmVccLowWngPortn
		EkiOnOff,
	pmcryptoAlmTxBiasHighWngPortn
		EkiOnOff,
	pmcryptoAlmTxBiasLowWngPortn
		EkiOnOff,
	pmcryptoAlmTxPwrHighWngPortn
		EkiOnOff,
	pmcryptoAlmTxPwLowWngPortn
		EkiOnOff
	}


pmcryptoAlmclientSfpWarnDdmIndex OBJECT-TYPE
	SYNTAX  INTEGER(0..128)
	MAX-ACCESS  read-only
	STATUS current
	DESCRIPTION
        "
        Index definition for the pmcryptoAlmclientSfpWarnDdm 
        table
        "
	::= { pmcryptoAlmclientSfpWarnDdmEntry 1 }


pmcryptoAlmRxPwrHighWngPortn OBJECT-TYPE
	SYNTAX  EkiOnOff
	MAX-ACCESS read-only
	STATUS current
	DESCRIPTION
        "
        Client Trscv Rx Power High Warning 
        :This OID indicates that the Trscv 
        input power is higher than the
         threshold value written in the 
        Trscv EEPROM <Help> Warning indicating 
        that the Trscv input power is higher 
        than the threshold value written 
        in the Trscv EEPROM <Condtype>
         RX_PWR_HIGH_WNG_1 <Probcause>
         receiveFailure (41) <Alarmtype> 
        equipmentAlarm (5) <Polarity> (2) 
        "
	::= { pmcryptoAlmclientSfpWarnDdmEntry 17 }


pmcryptoAlmRxPwrLowWngPortn OBJECT-TYPE
	SYNTAX  EkiOnOff
	MAX-ACCESS read-only
	STATUS current
	DESCRIPTION
        "
        Client Trscv Rx Power Low Warning 
        :This OID indicates that the Trscv 
        input power is lower than the threshold 
        value written in the Trscv EEPROM 
        <Help> Warning indicating that
         the Trscv input power is lower 
        than the threshold value written 
        in the Trscv EEPROM <Condtype>
         RX_PWR_LOW_WNG_1 <Probcause> receiveFailure 
        (41) <Alarmtype> equipmentAlarm 
        (5) <Polarity> (2) 
        "
	::= { pmcryptoAlmclientSfpWarnDdmEntry 16 }


pmcryptoAlmTempHighWngPortn OBJECT-TYPE
	SYNTAX  EkiOnOff
	MAX-ACCESS read-only
	STATUS current
	DESCRIPTION
        "
        Client Trscv Temp High Warning 
        :This OID indicates that the Trscv 
        temperature is higher than the
         threshold value written in the 
        Trscv EEPROM <Help> Warning indicating 
        that the Trscv temperature is higher 
        than the threshold value written 
        in the Trscv EEPROM <Condtype>
         TEMP_HIGH_WNG_1 <Probcause> temperatureUnacceptable 
        (51) <Alarmtype> equipmentAlarm 
        (5) <Polarity> (2) 
        "
	::= { pmcryptoAlmclientSfpWarnDdmEntry 9 }


pmcryptoAlmTempLowWngPortn OBJECT-TYPE
	SYNTAX  EkiOnOff
	MAX-ACCESS read-only
	STATUS current
	DESCRIPTION
        "
        Client Trscv Temp Low Warning
         :This OID indicates that the Trscv 
        temperature is lower than the threshold 
        value written in the Trscv EEPROM 
        <Help> Warning indicating that
         the Trscv temperature is lower 
        than the threshold value written 
        in the Trscv EEPROM <Condtype>
         TEMP_LOW_WNG_1 <Probcause> temperatureUnacceptable 
        (51) <Alarmtype> equipmentAlarm 
        (5) <Polarity> (2) 
        "
	::= { pmcryptoAlmclientSfpWarnDdmEntry 8 }


pmcryptoAlmVccHighWngPortn OBJECT-TYPE
	SYNTAX  EkiOnOff
	MAX-ACCESS read-only
	STATUS current
	DESCRIPTION
        "
        Client Trscv Power Supply High 
        Warning :This OID indicates that 
        the Trscv power supply is higher 
        than the threshold value written 
        in the Trscv EEPROM <Help> Warning 
        indicating that the Trscv power 
        supply is higher than the threshold 
        value written in the Trscv EEPROM 
        <Condtype> VCC_HIGH_WNG_1 <Probcause> 
        powerProblem (36) <Alarmtype> equipmentAlarm 
        (5) <Polarity> (2) 
        "
	::= { pmcryptoAlmclientSfpWarnDdmEntry 7 }


pmcryptoAlmVccLowWngPortn OBJECT-TYPE
	SYNTAX  EkiOnOff
	MAX-ACCESS read-only
	STATUS current
	DESCRIPTION
        "
        Client Trscv Power Supply Low
         Warning :This OID indicates that 
        the Trscv power supply is lower 
        than the threshold value written 
        in the Trscv EEPROM <Help> Warning 
        indicating that the Trscv power 
        supply is lower than the threshold 
        value written in the Trscv EEPROM 
        <Condtype> VCC_LOW_WNG_1 <Probcause> 
        powerProblem (36) <Alarmtype> equipmentAlarm 
        (5) <Polarity> (2) 
        "
	::= { pmcryptoAlmclientSfpWarnDdmEntry 6 }


pmcryptoAlmTxBiasHighWngPortn OBJECT-TYPE
	SYNTAX  EkiOnOff
	MAX-ACCESS read-only
	STATUS current
	DESCRIPTION
        "
        Client Trscv Bias High Warning 
        :This OID indicates that the Trscv 
        laser bias current is higher than 
        the threshold value written in
         the Trscv EEPROM <Help> Warning 
        indicating that the Trscv laser 
        bias current is higher than the 
        threshold value written in the
         Trscv EEPROM <Condtype> TX_BIAS_HIGH_WNG_1 
        <Probcause> transmitterFailure
         (56) <Alarmtype> equipmentAlarm 
        (5) <Polarity> (2) 
        "
	::= { pmcryptoAlmclientSfpWarnDdmEntry 5 }


pmcryptoAlmTxBiasLowWngPortn OBJECT-TYPE
	SYNTAX  EkiOnOff
	MAX-ACCESS read-only
	STATUS current
	DESCRIPTION
        "
        Client Trscv Bias Low Warning
         :This OID indicates that the Trscv 
        laser bias current is lower than 
        the threshold value written in
         the Trscv EEPROM <Help> Warning 
        indicating that the Trscv laser 
        bias current is lower than the
         threshold value written in the 
        Trscv EEPROM <Condtype> TX_BIAS_LOW_WNG_1 
        <Probcause> transmitterFailure
         (56) <Alarmtype> equipmentAlarm 
        (5) <Polarity> (2) 
        "
	::= { pmcryptoAlmclientSfpWarnDdmEntry 4 }


pmcryptoAlmTxPwrHighWngPortn OBJECT-TYPE
	SYNTAX  EkiOnOff
	MAX-ACCESS read-only
	STATUS current
	DESCRIPTION
        "
        Client Trscv Tx Power High Warning 
        :This OID indicates that the Trscv 
        output power is higher than the 
        threshold value written in the
         Trscv EEPROM <Help> Warning indicating 
        that the Trscv output power is
         higher than the threshold value 
        written in the Trscv EEPROM <Condtype> 
        TX_PWR_HIGH_WNG_1 <Probcause> transmitterFailure 
        (56) <Alarmtype> equipmentAlarm 
        (5) <Polarity> (2) 
        "
	::= { pmcryptoAlmclientSfpWarnDdmEntry 3 }


pmcryptoAlmTxPwLowWngPortn OBJECT-TYPE
	SYNTAX  EkiOnOff
	MAX-ACCESS read-only
	STATUS current
	DESCRIPTION
        "
        Client Trscv Tx Power Low Warning 
        :This OID indicates that the Trscv 
        output power is lower than the
         threshold value written in the 
        Trscv EEPROM <Help> Warning indicating 
        that the Trscv output power is
         lower than the threshold value 
        written in the Trscv EEPROM <Condtype> 
        TX_PW_LOW_WNG_1 <Probcause> transmitterFailure 
        (56) <Alarmtype> equipmentAlarm 
        (5) <Polarity> (2) 
        "
	::= { pmcryptoAlmclientSfpWarnDdmEntry 2 }


--- *********************************************************
---     TABLE for the pmcryptoAlmclientOtnAlm articles
--- *********************************************************

pmcryptoAlmclientOtnAlmTable OBJECT-TYPE
	SYNTAX  SEQUENCE OF PmcryptoAlmclientOtnAlmEntry
	MAX-ACCESS not-accessible
	STATUS current
	DESCRIPTION
        "
        List of pmcryptoAlmclientOtnAlm 
        Article
        "
	::= { pmcryptoAlmClientUrg 304 }


pmcryptoAlmclientOtnAlmEntry OBJECT-TYPE
	SYNTAX PmcryptoAlmclientOtnAlmEntry
	MAX-ACCESS not-accessible
	STATUS current
	DESCRIPTION
        "
        Row definition for the pmcryptoAlmclientOtnAlm 
        table
        "
	INDEX   { pmcryptoAlmclientOtnAlmIndex }
	::= { pmcryptoAlmclientOtnAlmTable 1 }


PmcryptoAlmclientOtnAlmEntry ::=
	SEQUENCE {
	pmcryptoAlmclientOtnAlmIndex
		INTEGER,
	pmcryptoAlmClientOtu2eDlomPortn
		EkiOnOff
	}


pmcryptoAlmclientOtnAlmIndex OBJECT-TYPE
	SYNTAX  INTEGER(0..128)
	MAX-ACCESS  read-only
	STATUS current
	DESCRIPTION
        "
        Index definition for the pmcryptoAlmclientOtnAlm 
        table
        "
	::= { pmcryptoAlmclientOtnAlmEntry 1 }


pmcryptoAlmClientOtu2eDlomPortn OBJECT-TYPE
	SYNTAX  EkiOnOff
	MAX-ACCESS read-only
	STATUS current
	DESCRIPTION
        "
        DLOM :This OID indicates that
         a Loss Of Multiframe has been
         detected on client port<Help>
          This alarm indicates if a Loss 
        Of Multiframe has been detected 
        on the client port <Condtype> CLIENT_OTU2E_DLOM 
        <Probcause> receiveFailure (41) 
        <Alarmtype> equipmentAlarm (5)
         <Polarity> (2) 
        "
	::= { pmcryptoAlmclientOtnAlmEntry 2 }


--- *****************************************************
---     LEAF for the modFanFail article
--- *****************************************************
pmcryptoAlmmodFanFail OBJECT IDENTIFIER ::= { pmcryptoAlmOtherUrg 336 }




pmcryptoAlmFanHighSpeed OBJECT-TYPE
	  SYNTAX EkiOnOff
	  MAX-ACCESS read-only
	  STATUS current
	  DESCRIPTION
        "
        Fan High Speed :This OID indicates 
        the fan is blowing at high speed 
        <Help> This alarm indicates the 
        fan is blowing at high speed <Condtype> 
        FAN_HIGH_SPEED <Probcause> other 
        (1) <Alarmtype> other (1) <Polarity> 
        (2) 
        "
	  ::= { pmcryptoAlmmodFanFail 2 }



pmcryptoAlmFanFail OBJECT-TYPE
	  SYNTAX EkiOnOff
	  MAX-ACCESS read-only
	  STATUS current
	  DESCRIPTION
        "
        Fan Module Failure :This OID indicates 
        that the FAN unit inside the module 
        is in fail condition  <Help>  This 
        alarm indicates that the FAN is 
        in a fail condition. <Condtype> 
        FAN_FAIL <Probcause> heatingVentCoolingSystemProblem 
        (22) <Alarmtype> equipmentAlarm 
        (5) <Polarity> (2) 
        "
	  ::= { pmcryptoAlmmodFanFail 1 }








--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pmcryptoCtrlconfMgnt1 OBJECT IDENTIFIER ::= { pmcryptoCtrlOther 1 }




pmcryptoCtrlConf2Clear1 OBJECT-TYPE
	  SYNTAX EkiOnOff
	  MAX-ACCESS read-write
	  STATUS current
	  DESCRIPTION
        "
        Clear Configuration Tables :This 
        OID clears the configuration tables 
        from configuration2 in the flash. 
         <Help>  This control restores
         the default configuration of the 
        module
        "
	  ::= { pmcryptoCtrlconfMgnt1 14 }



pmcryptoCtrlConf2Flash1 OBJECT-TYPE
	  SYNTAX EkiOnOff
	  MAX-ACCESS read-write
	  STATUS current
	  DESCRIPTION
        "
        Write Configuration Tables :This 
        OID saves the current configuration 
        of the PM as configuration2 in
         the flash.  <Help>  This control 
        saves the customer configuration 
        on the module
        "
	  ::= { pmcryptoCtrlconfMgnt1 10 }



pmcryptoCtrlConf2Load1 OBJECT-TYPE
	  SYNTAX EkiOnOff
	  MAX-ACCESS read-write
	  STATUS current
	  DESCRIPTION
        "
        Load Configuration Tables Set
         Nb 2 :When set this OID enables 
        loading from flash configuration2 
        into the PM.
        "
	  ::= { pmcryptoCtrlconfMgnt1 2 }



pmcryptoCtrlConf1Load1 OBJECT-TYPE
	  SYNTAX EkiOnOff
	  MAX-ACCESS read-write
	  STATUS current
	  DESCRIPTION
        "
        Load Configuration Tables Set
         Nb 1 :When set this OID enables 
        loading from flash configuration1 
        into the PM.
        "
	  ::= { pmcryptoCtrlconfMgnt1 1 }



--- *****************************************************
---     LEAF for the synth4 article
--- *****************************************************
pmcryptoCtrlsynth4 OBJECT IDENTIFIER ::= { pmcryptoCtrlOther 4 }




pmcryptoCtrlCorrelatOff OBJECT-TYPE
	  SYNTAX EkiOnOff
	  MAX-ACCESS read-write
	  STATUS current
	  DESCRIPTION
        "
        Disable Alarm Correlation :This 
        OID disables the alarm correlation 
        in the PM.
        "
	  ::= { pmcryptoCtrlsynth4 2 }



pmcryptoCtrlCorrelatOn OBJECT-TYPE
	  SYNTAX EkiOnOff
	  MAX-ACCESS read-write
	  STATUS current
	  DESCRIPTION
        "
        Enable Alarm Correlation :This 
        OID enables the alarm correlation 
        in the PM.
        "
	  ::= { pmcryptoCtrlsynth4 1 }



--- *****************************************************
---     LEAF for the swMgnt article
--- *****************************************************
pmcryptoCtrlswMgnt OBJECT IDENTIFIER ::= { pmcryptoCtrlOther 5 }




pmcryptoCtrlLoadSwBank2 OBJECT-TYPE
	  SYNTAX EkiOnOff
	  MAX-ACCESS read-write
	  STATUS current
	  DESCRIPTION
        "
        Set Software Nb 2 As Active :This 
        OID, when set, loads the SW from 
        bank2 into the PM. It must be followed 
        by a reset.  <Help>  This controls 
        selects the second SW bank as the 
        active bank for the next module 
        reset
        "
	  ::= { pmcryptoCtrlswMgnt 6 }



pmcryptoCtrlLoadSwBank1 OBJECT-TYPE
	  SYNTAX EkiOnOff
	  MAX-ACCESS read-write
	  STATUS current
	  DESCRIPTION
        "
        Set Software Nb 1 As Active :This 
        OID, when set, loads the SW from 
        bank1 into the PM. It must be followed 
        by a reset.  <Help>  This controls 
        selects the first SW bank as the 
        active bank for the next module 
        reset
        "
	  ::= { pmcryptoCtrlswMgnt 5 }



pmcryptoCtrlWarmReset OBJECT-TYPE
	  SYNTAX EkiOnOff
	  MAX-ACCESS read-write
	  STATUS current
	  DESCRIPTION
        "
        PM Warm Reset :This OID, when
         set, causes a warm reset of the 
        PM. This reset is not traffic affecting, 
        and the configuration of PM remains 
        unchanged.  <Help>  This control 
        initiates a warm reset of the module. 
        "
	  ::= { pmcryptoCtrlswMgnt 3 }



pmcryptoCtrlColdReset OBJECT-TYPE
	  SYNTAX EkiOnOff
	  MAX-ACCESS read-write
	  STATUS current
	  DESCRIPTION
        "
        PM Cold Reset :This OID, when
         set, causes a cold reset of the 
        PM. This reset is traffic affecting, 
        and the configuration of PM is
         reloaded on start-up.  <Help>
          This control initiates a cold 
        reset of the module. 
        "
	  ::= { pmcryptoCtrlswMgnt 2 }



--- *****************************************************
---     LEAF for the gwMgnt article
--- *****************************************************
pmcryptoCtrlgwMgnt OBJECT IDENTIFIER ::= { pmcryptoCtrlOther 6 }




pmcryptoCtrlLoadGwBank4 OBJECT-TYPE
	  SYNTAX EkiOnOff
	  MAX-ACCESS read-write
	  STATUS current
	  DESCRIPTION
        "
        Set Gateware Nb 4 As Active :This 
        OID, when set, loads the GW from 
        bank4 (Flash) into the PM. It is 
        followed by an automatic gateware 
        cold reset.
        "
	  ::= { pmcryptoCtrlgwMgnt 8 }



pmcryptoCtrlLoadGwBank3 OBJECT-TYPE
	  SYNTAX EkiOnOff
	  MAX-ACCESS read-write
	  STATUS current
	  DESCRIPTION
        "
        Set Gateware Nb 3 As Active :This 
        OID, when set, loads the GW from 
        bank3 (Flash) into the PM. It is 
        followed by an automatic gateware 
        cold reset.  <Help>  This controls 
        initiates a cold reset of the module 
        and select the third GW bank as 
        the active bank
        "
	  ::= { pmcryptoCtrlgwMgnt 7 }



pmcryptoCtrlLoadGwBank2 OBJECT-TYPE
	  SYNTAX EkiOnOff
	  MAX-ACCESS read-write
	  STATUS current
	  DESCRIPTION
        "
        Set Gateware Nb 2 As Active :This 
        OID, when set, loads the GW from 
        bank2 (Flash) into the PM. It is 
        followed by an automatic gateware 
        cold reset.
        "
	  ::= { pmcryptoCtrlgwMgnt 6 }



pmcryptoCtrlLoadGwBank1 OBJECT-TYPE
	  SYNTAX EkiOnOff
	  MAX-ACCESS read-write
	  STATUS current
	  DESCRIPTION
        "
        Set Gateware Nb 1 As Active :This 
        OID, when set, loads the GW from 
        bank1 (Flash) into the PM. It is 
        followed by an automatic gateware 
        cold reset.  <Help>  This controls 
        initiates a cold reset of the module 
        and select the first GW bank as 
        the active bank
        "
	  ::= { pmcryptoCtrlgwMgnt 5 }



pmcryptoCtrlCurrentGwReset OBJECT-TYPE
	  SYNTAX EkiOnOff
	  MAX-ACCESS read-write
	  STATUS current
	  DESCRIPTION
        "
        Active Gateware Reset :This OID, 
        when set, resets the active gateware. 
        It is traffic affecting.
        "
	  ::= { pmcryptoCtrlgwMgnt 1 }



--- *********************************************************
---     TABLE for the pmcryptoCtrlaccessLoop articles
--- *********************************************************

pmcryptoCtrlaccessLoopTable OBJECT-TYPE
	SYNTAX  SEQUENCE OF PmcryptoCtrlaccessLoopEntry
	MAX-ACCESS not-accessible
	STATUS current
	DESCRIPTION
        "
        List of pmcryptoCtrlaccessLoop 
        Article
        "
	::= { pmcryptoCtrlClient 16 }


pmcryptoCtrlaccessLoopEntry OBJECT-TYPE
	SYNTAX PmcryptoCtrlaccessLoopEntry
	MAX-ACCESS not-accessible
	STATUS current
	DESCRIPTION
        "
        Row definition for the pmcryptoCtrlaccessLoop 
        table
        "
	INDEX   { pmcryptoCtrlaccessLoopIndex }
	::= { pmcryptoCtrlaccessLoopTable 1 }


PmcryptoCtrlaccessLoopEntry ::=
	SEQUENCE {
	pmcryptoCtrlaccessLoopIndex
		INTEGER,
	pmcryptoCtrlaccessLoopPortn
		EkiState
	}


pmcryptoCtrlaccessLoopIndex OBJECT-TYPE
	SYNTAX  INTEGER(0..128)
	MAX-ACCESS  read-only
	STATUS current
	DESCRIPTION
        "
        Index definition for the pmcryptoCtrlaccessLoop 
        table
        "
	::= { pmcryptoCtrlaccessLoopEntry 1 }


pmcryptoCtrlaccessLoopPortn OBJECT-TYPE
	SYNTAX  EkiState
	MAX-ACCESS read-write
	STATUS current
	DESCRIPTION
        "
        Client Facility Loopback :This 
        OID, when set at '1' puts the client 
        port in loopback, looping the received 
        10 Gb/s signal on the transmit
         10 Gb/s output.  <Help> This control 
        enables the Out Loopback on the 
        client port, looping the client 
        input signal on the client output
        "
	::= { pmcryptoCtrlaccessLoopEntry 2 }


--- *********************************************************
---     TABLE for the pmcryptoCtrlclientLoopToLine articles
--- *********************************************************

pmcryptoCtrlclientLoopToLineTable OBJECT-TYPE
	SYNTAX  SEQUENCE OF PmcryptoCtrlclientLoopToLineEntry
	MAX-ACCESS not-accessible
	STATUS current
	DESCRIPTION
        "
        List of pmcryptoCtrlclientLoopToLine 
        Article
        "
	::= { pmcryptoCtrlClient 17 }


pmcryptoCtrlclientLoopToLineEntry OBJECT-TYPE
	SYNTAX PmcryptoCtrlclientLoopToLineEntry
	MAX-ACCESS not-accessible
	STATUS current
	DESCRIPTION
        "
        Row definition for the pmcryptoCtrlclientLoopToLine 
        table
        "
	INDEX   { pmcryptoCtrlclientLoopToLineIndex }
	::= { pmcryptoCtrlclientLoopToLineTable 1 }


PmcryptoCtrlclientLoopToLineEntry ::=
	SEQUENCE {
	pmcryptoCtrlclientLoopToLineIndex
		INTEGER,
	pmcryptoCtrlclientLoopToLinePortn
		EkiState
	}


pmcryptoCtrlclientLoopToLineIndex OBJECT-TYPE
	SYNTAX  INTEGER(0..128)
	MAX-ACCESS  read-only
	STATUS current
	DESCRIPTION
        "
        Index definition for the pmcryptoCtrlclientLoopToLine 
        table
        "
	::= { pmcryptoCtrlclientLoopToLineEntry 1 }


pmcryptoCtrlclientLoopToLinePortn OBJECT-TYPE
	SYNTAX  EkiState
	MAX-ACCESS read-write
	STATUS current
	DESCRIPTION
        "
        Client Terminal Loopback :This 
        OID, when set, puts the client
         port in loop back, looping the 
        10 Gb/s output signal on the 10 
        Gb/s input.<Help> This control
         enables the In Loopback on the 
        client port, looping the client 
        output signal on the client input
        "
	::= { pmcryptoCtrlclientLoopToLineEntry 2 }


--- *********************************************************
---     TABLE for the pmcryptoCtrlcsfUpIns articles
--- *********************************************************

pmcryptoCtrlcsfUpInsTable OBJECT-TYPE
	SYNTAX  SEQUENCE OF PmcryptoCtrlcsfUpInsEntry
	MAX-ACCESS not-accessible
	STATUS current
	DESCRIPTION
        "
        List of pmcryptoCtrlcsfUpIns Article
        "
	::= { pmcryptoCtrlClient 21 }


pmcryptoCtrlcsfUpInsEntry OBJECT-TYPE
	SYNTAX PmcryptoCtrlcsfUpInsEntry
	MAX-ACCESS not-accessible
	STATUS current
	DESCRIPTION
        "
        Row definition for the pmcryptoCtrlcsfUpIns 
        table
        "
	INDEX   { pmcryptoCtrlcsfUpInsIndex }
	::= { pmcryptoCtrlcsfUpInsTable 1 }


PmcryptoCtrlcsfUpInsEntry ::=
	SEQUENCE {
	pmcryptoCtrlcsfUpInsIndex
		INTEGER,
	pmcryptoCtrlcsfUpInsPortn
		EkiState
	}


pmcryptoCtrlcsfUpInsIndex OBJECT-TYPE
	SYNTAX  INTEGER(0..128)
	MAX-ACCESS  read-only
	STATUS current
	DESCRIPTION
        "
        Index definition for the pmcryptoCtrlcsfUpIns 
        table
        "
	::= { pmcryptoCtrlcsfUpInsEntry 1 }


pmcryptoCtrlcsfUpInsPortn OBJECT-TYPE
	SYNTAX  EkiState
	MAX-ACCESS read-write
	STATUS current
	DESCRIPTION
        "
        Client Signal Fail Insertion :This 
        OID, when set, inserts  a client 
        signal fail in the upstream client 
        Port.  <Help>  This control inserts 
        a Client Signal Fail for the client 
        port
        "
	::= { pmcryptoCtrlcsfUpInsEntry 2 }


--- *********************************************************
---     TABLE for the pmcryptoCtrlcaisDwIns articles
--- *********************************************************

pmcryptoCtrlcaisDwInsTable OBJECT-TYPE
	SYNTAX  SEQUENCE OF PmcryptoCtrlcaisDwInsEntry
	MAX-ACCESS not-accessible
	STATUS current
	DESCRIPTION
        "
        List of pmcryptoCtrlcaisDwIns
         Article
        "
	::= { pmcryptoCtrlClient 22 }


pmcryptoCtrlcaisDwInsEntry OBJECT-TYPE
	SYNTAX PmcryptoCtrlcaisDwInsEntry
	MAX-ACCESS not-accessible
	STATUS current
	DESCRIPTION
        "
        Row definition for the pmcryptoCtrlcaisDwIns 
        table
        "
	INDEX   { pmcryptoCtrlcaisDwInsIndex }
	::= { pmcryptoCtrlcaisDwInsTable 1 }


PmcryptoCtrlcaisDwInsEntry ::=
	SEQUENCE {
	pmcryptoCtrlcaisDwInsIndex
		INTEGER,
	pmcryptoCtrlcaisDwInsPortn
		EkiState
	}


pmcryptoCtrlcaisDwInsIndex OBJECT-TYPE
	SYNTAX  INTEGER(0..128)
	MAX-ACCESS  read-only
	STATUS current
	DESCRIPTION
        "
        Index definition for the pmcryptoCtrlcaisDwIns 
        table
        "
	::= { pmcryptoCtrlcaisDwInsEntry 1 }


pmcryptoCtrlcaisDwInsPortn OBJECT-TYPE
	SYNTAX  EkiState
	MAX-ACCESS read-write
	STATUS current
	DESCRIPTION
        "
        Client AIS Insertion :This OID, 
        when set, inserts a client AIS
         on the downstream client Port. 
         <Help>  This control inserts a 
        Client AIS for the client port
        "
	::= { pmcryptoCtrlcaisDwInsEntry 2 }


--- *********************************************************
---     TABLE for the pmcryptoCtrlcommAccessLoop articles
--- *********************************************************

pmcryptoCtrlcommAccessLoopTable OBJECT-TYPE
	SYNTAX  SEQUENCE OF PmcryptoCtrlcommAccessLoopEntry
	MAX-ACCESS not-accessible
	STATUS current
	DESCRIPTION
        "
        List of pmcryptoCtrlcommAccessLoop 
        Article
        "
	::= { pmcryptoCtrlLine 64 }


pmcryptoCtrlcommAccessLoopEntry OBJECT-TYPE
	SYNTAX PmcryptoCtrlcommAccessLoopEntry
	MAX-ACCESS not-accessible
	STATUS current
	DESCRIPTION
        "
        Row definition for the pmcryptoCtrlcommAccessLoop 
        table
        "
	INDEX   { pmcryptoCtrlcommAccessLoopIndex }
	::= { pmcryptoCtrlcommAccessLoopTable 1 }


PmcryptoCtrlcommAccessLoopEntry ::=
	SEQUENCE {
	pmcryptoCtrlcommAccessLoopIndex
		INTEGER,
	pmcryptoCtrlcommAccessLoopPortn
		EkiState
	}


pmcryptoCtrlcommAccessLoopIndex OBJECT-TYPE
	SYNTAX  INTEGER(0..128)
	MAX-ACCESS  read-only
	STATUS current
	DESCRIPTION
        "
        Index definition for the pmcryptoCtrlcommAccessLoop 
        table
        "
	::= { pmcryptoCtrlcommAccessLoopEntry 1 }


pmcryptoCtrlcommAccessLoopPortn OBJECT-TYPE
	SYNTAX  EkiState
	MAX-ACCESS read-write
	STATUS current
	DESCRIPTION
        "
        Line Terminal Loopback :This OID, 
        when set, puts the module in common 
        access loop back, looping the 200 
        Gb/s output signal on the 200 Gb/s 
        input.<Help> This control enables 
        the In Loopback on the line port, 
        looping the 200 Gb/s output signal 
        on the 200 Gb/s input
        "
	::= { pmcryptoCtrlcommAccessLoopEntry 2 }


--- *********************************************************
---     TABLE for the pmcryptoCtrllineLoop articles
--- *********************************************************

pmcryptoCtrllineLoopTable OBJECT-TYPE
	SYNTAX  SEQUENCE OF PmcryptoCtrllineLoopEntry
	MAX-ACCESS not-accessible
	STATUS current
	DESCRIPTION
        "
        List of pmcryptoCtrllineLoop Article
        "
	::= { pmcryptoCtrlLine 66 }


pmcryptoCtrllineLoopEntry OBJECT-TYPE
	SYNTAX PmcryptoCtrllineLoopEntry
	MAX-ACCESS not-accessible
	STATUS current
	DESCRIPTION
        "
        Row definition for the pmcryptoCtrllineLoop 
        table
        "
	INDEX   { pmcryptoCtrllineLoopIndex }
	::= { pmcryptoCtrllineLoopTable 1 }


PmcryptoCtrllineLoopEntry ::=
	SEQUENCE {
	pmcryptoCtrllineLoopIndex
		INTEGER,
	pmcryptoCtrllineLoopPortn
		EkiState
	}


pmcryptoCtrllineLoopIndex OBJECT-TYPE
	SYNTAX  INTEGER(0..128)
	MAX-ACCESS  read-only
	STATUS current
	DESCRIPTION
        "
        Index definition for the pmcryptoCtrllineLoop 
        table
        "
	::= { pmcryptoCtrllineLoopEntry 1 }


pmcryptoCtrllineLoopPortn OBJECT-TYPE
	SYNTAX  EkiState
	MAX-ACCESS read-write
	STATUS current
	DESCRIPTION
        "
        Line Facility Loopback :This OID, 
        when set at '1' puts the module 
        in line loopback mode, looping
         the received 200 Gb/s signal on 
        the transmit 200 Gb/s output. The 
        Upstream part of the module is
         timed on the 200 Gb/s recovered 
        clock in that case.<Help> This
         control enables the Out Loopback 
        on the line port, looping the 200 
        Gb/s input signal on the 200 Gb/s 
        output
        "
	::= { pmcryptoCtrllineLoopEntry 2 }


--- *********************************************************
---     TABLE for the pmcryptoCtrlfecDisable articles
--- *********************************************************

pmcryptoCtrlfecDisableTable OBJECT-TYPE
	SYNTAX  SEQUENCE OF PmcryptoCtrlfecDisableEntry
	MAX-ACCESS not-accessible
	STATUS current
	DESCRIPTION
        "
        List of pmcryptoCtrlfecDisable 
        Article
        "
	::= { pmcryptoCtrlLine 69 }


pmcryptoCtrlfecDisableEntry OBJECT-TYPE
	SYNTAX PmcryptoCtrlfecDisableEntry
	MAX-ACCESS not-accessible
	STATUS current
	DESCRIPTION
        "
        Row definition for the pmcryptoCtrlfecDisable 
        table
        "
	INDEX   { pmcryptoCtrlfecDisableIndex }
	::= { pmcryptoCtrlfecDisableTable 1 }


PmcryptoCtrlfecDisableEntry ::=
	SEQUENCE {
	pmcryptoCtrlfecDisableIndex
		INTEGER,
	pmcryptoCtrlfecDisablePortn
		EkiState
	}


pmcryptoCtrlfecDisableIndex OBJECT-TYPE
	SYNTAX  INTEGER(0..128)
	MAX-ACCESS  read-only
	STATUS current
	DESCRIPTION
        "
        Index definition for the pmcryptoCtrlfecDisable 
        table
        "
	::= { pmcryptoCtrlfecDisableEntry 1 }


pmcryptoCtrlfecDisablePortn OBJECT-TYPE
	SYNTAX  EkiState
	MAX-ACCESS read-write
	STATUS current
	DESCRIPTION
        "
        Forward Error Correction Inhibition 
        :This OID, when set, inhibits the 
        Forward Error Correction feature 
        on the line input  <Help>  This 
        control enables/disables the Forward 
        Error Correction on the line interface
        "
	::= { pmcryptoCtrlfecDisableEntry 2 }


--- *****************************************************
---     LEAF for the ledTest article
--- *****************************************************
pmcryptoCtrlledTest OBJECT IDENTIFIER ::= { pmcryptoCtrlOther 192 }




pmcryptoCtrlLedOff OBJECT-TYPE
	  SYNTAX EkiOnOff
	  MAX-ACCESS read-write
	  STATUS current
	  DESCRIPTION
        "
        Leds Off :This OID switches off 
        all the Leds as a test feature. 
         <Help>  This control initiates 
        a test leds turning all the LEDs 
        to OFF
        "
	  ::= { pmcryptoCtrlledTest 3 }



pmcryptoCtrlRedLed OBJECT-TYPE
	  SYNTAX EkiOnOff
	  MAX-ACCESS read-write
	  STATUS current
	  DESCRIPTION
        "
        Red Leds Test :This OID switches 
        on all the red Leds as a test feature. 
         <Help>  This control initiates 
        a test leds turning all the LEDs 
        to red
        "
	  ::= { pmcryptoCtrlledTest 2 }



pmcryptoCtrlGreenLed OBJECT-TYPE
	  SYNTAX EkiOnOff
	  MAX-ACCESS read-write
	  STATUS current
	  DESCRIPTION
        "
        Green Leds Test :This OID switches 
        on all the green Leds as a test 
        feature.  <Help>  This control
         initiates a test leds turning
         all the LEDs to green
        "
	  ::= { pmcryptoCtrlledTest 1 }



--- *****************************************************
---     LEAF for the initSwitchMarvell article
--- *****************************************************
pmcryptoCtrlinitSwitchMarvell OBJECT IDENTIFIER ::= { pmcryptoCtrlOther 201 }




pmcryptoCtrlInitSwitchMarvell OBJECT-TYPE
	  SYNTAX EkiOnOff
	  MAX-ACCESS read-write
	  STATUS current
	  DESCRIPTION
        "
        Switch Initialization :This OID 
        operates an initialization of the 
        switch managed through the module 
         <Help>  This control activates 
        an initialization of the switch 
        managed through the module
        "
	  ::= { pmcryptoCtrlinitSwitchMarvell 1 }



--- *********************************************************
---     TABLE for the pmcryptoCtrlmsaLineLoop articles
--- *********************************************************

pmcryptoCtrlmsaLineLoopTable OBJECT-TYPE
	SYNTAX  SEQUENCE OF PmcryptoCtrlmsaLineLoopEntry
	MAX-ACCESS not-accessible
	STATUS current
	DESCRIPTION
        "
        List of pmcryptoCtrlmsaLineLoop 
        Article
        "
	::= { pmcryptoCtrlLine 209 }


pmcryptoCtrlmsaLineLoopEntry OBJECT-TYPE
	SYNTAX PmcryptoCtrlmsaLineLoopEntry
	MAX-ACCESS not-accessible
	STATUS current
	DESCRIPTION
        "
        Row definition for the pmcryptoCtrlmsaLineLoop 
        table
        "
	INDEX   { pmcryptoCtrlmsaLineLoopIndex }
	::= { pmcryptoCtrlmsaLineLoopTable 1 }


PmcryptoCtrlmsaLineLoopEntry ::=
	SEQUENCE {
	pmcryptoCtrlmsaLineLoopIndex
		INTEGER,
	pmcryptoCtrlmsaLineLoopPortn
		EkiState
	}


pmcryptoCtrlmsaLineLoopIndex OBJECT-TYPE
	SYNTAX  INTEGER(0..128)
	MAX-ACCESS  read-only
	STATUS current
	DESCRIPTION
        "
        Index definition for the pmcryptoCtrlmsaLineLoop 
        table
        "
	::= { pmcryptoCtrlmsaLineLoopEntry 1 }


pmcryptoCtrlmsaLineLoopPortn OBJECT-TYPE
	SYNTAX  EkiState
	MAX-ACCESS read-write
	STATUS current
	DESCRIPTION
        "
        MSA Line Loop :This OID operates 
        a line loopback on the MSA Line 
         <Help>  This control defines the 
        line loop back of the line transceiver
        "
	::= { pmcryptoCtrlmsaLineLoopEntry 2 }


--- *********************************************************
---     TABLE for the pmcryptoCtrlmsaTxReset articles
--- *********************************************************

pmcryptoCtrlmsaTxResetTable OBJECT-TYPE
	SYNTAX  SEQUENCE OF PmcryptoCtrlmsaTxResetEntry
	MAX-ACCESS not-accessible
	STATUS current
	DESCRIPTION
        "
        List of pmcryptoCtrlmsaTxReset 
        Article
        "
	::= { pmcryptoCtrlLine 210 }


pmcryptoCtrlmsaTxResetEntry OBJECT-TYPE
	SYNTAX PmcryptoCtrlmsaTxResetEntry
	MAX-ACCESS not-accessible
	STATUS current
	DESCRIPTION
        "
        Row definition for the pmcryptoCtrlmsaTxReset 
        table
        "
	INDEX   { pmcryptoCtrlmsaTxResetIndex }
	::= { pmcryptoCtrlmsaTxResetTable 1 }


PmcryptoCtrlmsaTxResetEntry ::=
	SEQUENCE {
	pmcryptoCtrlmsaTxResetIndex
		INTEGER,
	pmcryptoCtrlmsaTxResetPortn
		EkiState
	}


pmcryptoCtrlmsaTxResetIndex OBJECT-TYPE
	SYNTAX  INTEGER(0..128)
	MAX-ACCESS  read-only
	STATUS current
	DESCRIPTION
        "
        Index definition for the pmcryptoCtrlmsaTxReset 
        table
        "
	::= { pmcryptoCtrlmsaTxResetEntry 1 }


pmcryptoCtrlmsaTxResetPortn OBJECT-TYPE
	SYNTAX  EkiState
	MAX-ACCESS read-write
	STATUS current
	DESCRIPTION
        "
        Line MSA TX Reset :This OID resets 
        the TX portion of the MSA line
         module  <Help > This control 
         initiates a reset of the transmitting 
        side
        "
	::= { pmcryptoCtrlmsaTxResetEntry 2 }


--- *********************************************************
---     TABLE for the pmcryptoCtrlmsaRxReset articles
--- *********************************************************

pmcryptoCtrlmsaRxResetTable OBJECT-TYPE
	SYNTAX  SEQUENCE OF PmcryptoCtrlmsaRxResetEntry
	MAX-ACCESS not-accessible
	STATUS current
	DESCRIPTION
        "
        List of pmcryptoCtrlmsaRxReset 
        Article
        "
	::= { pmcryptoCtrlLine 211 }


pmcryptoCtrlmsaRxResetEntry OBJECT-TYPE
	SYNTAX PmcryptoCtrlmsaRxResetEntry
	MAX-ACCESS not-accessible
	STATUS current
	DESCRIPTION
        "
        Row definition for the pmcryptoCtrlmsaRxReset 
        table
        "
	INDEX   { pmcryptoCtrlmsaRxResetIndex }
	::= { pmcryptoCtrlmsaRxResetTable 1 }


PmcryptoCtrlmsaRxResetEntry ::=
	SEQUENCE {
	pmcryptoCtrlmsaRxResetIndex
		INTEGER,
	pmcryptoCtrlmsaRxResetPortn
		EkiState
	}


pmcryptoCtrlmsaRxResetIndex OBJECT-TYPE
	SYNTAX  INTEGER(0..128)
	MAX-ACCESS  read-only
	STATUS current
	DESCRIPTION
        "
        Index definition for the pmcryptoCtrlmsaRxReset 
        table
        "
	::= { pmcryptoCtrlmsaRxResetEntry 1 }


pmcryptoCtrlmsaRxResetPortn OBJECT-TYPE
	SYNTAX  EkiState
	MAX-ACCESS read-write
	STATUS current
	DESCRIPTION
        "
        Line MSA RX Reset :This OID resets 
        the RX portion of the MSA line
         module  <Help > This control 
         initiates a reset of the receiving 
        side
        "
	::= { pmcryptoCtrlmsaRxResetEntry 2 }


--- *********************************************************
---     TABLE for the pmcryptoCtrlmsaShutdown articles
--- *********************************************************

pmcryptoCtrlmsaShutdownTable OBJECT-TYPE
	SYNTAX  SEQUENCE OF PmcryptoCtrlmsaShutdownEntry
	MAX-ACCESS not-accessible
	STATUS current
	DESCRIPTION
        "
        List of pmcryptoCtrlmsaShutdown 
        Article
        "
	::= { pmcryptoCtrlLine 212 }


pmcryptoCtrlmsaShutdownEntry OBJECT-TYPE
	SYNTAX PmcryptoCtrlmsaShutdownEntry
	MAX-ACCESS not-accessible
	STATUS current
	DESCRIPTION
        "
        Row definition for the pmcryptoCtrlmsaShutdown 
        table
        "
	INDEX   { pmcryptoCtrlmsaShutdownIndex }
	::= { pmcryptoCtrlmsaShutdownTable 1 }


PmcryptoCtrlmsaShutdownEntry ::=
	SEQUENCE {
	pmcryptoCtrlmsaShutdownIndex
		INTEGER,
	pmcryptoCtrlmsaShutdownPortn
		EkiState
	}


pmcryptoCtrlmsaShutdownIndex OBJECT-TYPE
	SYNTAX  INTEGER(0..128)
	MAX-ACCESS  read-only
	STATUS current
	DESCRIPTION
        "
        Index definition for the pmcryptoCtrlmsaShutdown 
        table
        "
	::= { pmcryptoCtrlmsaShutdownEntry 1 }


pmcryptoCtrlmsaShutdownPortn OBJECT-TYPE
	SYNTAX  EkiState
	MAX-ACCESS read-write
	STATUS current
	DESCRIPTION
        "
        Line MSA Shutdown :This OID enters 
        a process to shutdown the MSA line 
        module  <Help > This control  initiates 
        a shutdown of the module
        "
	::= { pmcryptoCtrlmsaShutdownEntry 2 }


--- *********************************************************
---     TABLE for the pmcryptoCtrlforceKeyExchange articles
--- *********************************************************

pmcryptoCtrlforceKeyExchangeTable OBJECT-TYPE
	SYNTAX  SEQUENCE OF PmcryptoCtrlforceKeyExchangeEntry
	MAX-ACCESS not-accessible
	STATUS deprecated
	DESCRIPTION
        "
        List of pmcryptoCtrlforceKeyExchange 
        Article
        "
	::= { pmcryptoCtrlLine 221 }


pmcryptoCtrlforceKeyExchangeEntry OBJECT-TYPE
	SYNTAX PmcryptoCtrlforceKeyExchangeEntry
	MAX-ACCESS not-accessible
	STATUS deprecated
	DESCRIPTION
        "
        Row definition for the pmcryptoCtrlforceKeyExchange 
        table
        "
	INDEX   { pmcryptoCtrlforceKeyExchangeIndex }
	::= { pmcryptoCtrlforceKeyExchangeTable 1 }


PmcryptoCtrlforceKeyExchangeEntry ::=
	SEQUENCE {
	pmcryptoCtrlforceKeyExchangeIndex
		INTEGER,
	pmcryptoCtrlforceKeyExchangePortn
		EkiState
	}


pmcryptoCtrlforceKeyExchangeIndex OBJECT-TYPE
	SYNTAX  INTEGER(0..128)
	MAX-ACCESS  read-only
	STATUS deprecated
	DESCRIPTION
        "
        Index definition for the pmcryptoCtrlforceKeyExchange 
        table
        "
	::= { pmcryptoCtrlforceKeyExchangeEntry 1 }


pmcryptoCtrlforceKeyExchangePortn OBJECT-TYPE
	SYNTAX  EkiState
	MAX-ACCESS read-write
	STATUS deprecated
	DESCRIPTION
        "
         :
        "
	::= { pmcryptoCtrlforceKeyExchangeEntry 2 }


--- *********************************************************
---     TABLE for the pmcryptoCtrldisableEncryption articles
--- *********************************************************

pmcryptoCtrldisableEncryptionTable OBJECT-TYPE
	SYNTAX  SEQUENCE OF PmcryptoCtrldisableEncryptionEntry
	MAX-ACCESS not-accessible
	STATUS deprecated
	DESCRIPTION
        "
        List of pmcryptoCtrldisableEncryption 
        Article
        "
	::= { pmcryptoCtrlLine 222 }


pmcryptoCtrldisableEncryptionEntry OBJECT-TYPE
	SYNTAX PmcryptoCtrldisableEncryptionEntry
	MAX-ACCESS not-accessible
	STATUS deprecated
	DESCRIPTION
        "
        Row definition for the pmcryptoCtrldisableEncryption 
        table
        "
	INDEX   { pmcryptoCtrldisableEncryptionIndex }
	::= { pmcryptoCtrldisableEncryptionTable 1 }


PmcryptoCtrldisableEncryptionEntry ::=
	SEQUENCE {
	pmcryptoCtrldisableEncryptionIndex
		INTEGER,
	pmcryptoCtrldisableEncryptionPortn
		EkiState
	}


pmcryptoCtrldisableEncryptionIndex OBJECT-TYPE
	SYNTAX  INTEGER(0..128)
	MAX-ACCESS  read-only
	STATUS deprecated
	DESCRIPTION
        "
        Index definition for the pmcryptoCtrldisableEncryption 
        table
        "
	::= { pmcryptoCtrldisableEncryptionEntry 1 }


pmcryptoCtrldisableEncryptionPortn OBJECT-TYPE
	SYNTAX  EkiState
	MAX-ACCESS read-write
	STATUS deprecated
	DESCRIPTION
        "
         :
        "
	::= { pmcryptoCtrldisableEncryptionEntry 2 }


--- *********************************************************
---     TABLE for the pmcryptoCtrlresetMonitoring articles
--- *********************************************************

pmcryptoCtrlresetMonitoringTable OBJECT-TYPE
	SYNTAX  SEQUENCE OF PmcryptoCtrlresetMonitoringEntry
	MAX-ACCESS not-accessible
	STATUS deprecated
	DESCRIPTION
        "
        List of pmcryptoCtrlresetMonitoring 
        Article
        "
	::= { pmcryptoCtrlLine 223 }


pmcryptoCtrlresetMonitoringEntry OBJECT-TYPE
	SYNTAX PmcryptoCtrlresetMonitoringEntry
	MAX-ACCESS not-accessible
	STATUS deprecated
	DESCRIPTION
        "
        Row definition for the pmcryptoCtrlresetMonitoring 
        table
        "
	INDEX   { pmcryptoCtrlresetMonitoringIndex }
	::= { pmcryptoCtrlresetMonitoringTable 1 }


PmcryptoCtrlresetMonitoringEntry ::=
	SEQUENCE {
	pmcryptoCtrlresetMonitoringIndex
		INTEGER,
	pmcryptoCtrlresetMonitoringPortn
		EkiState
	}


pmcryptoCtrlresetMonitoringIndex OBJECT-TYPE
	SYNTAX  INTEGER(0..128)
	MAX-ACCESS  read-only
	STATUS deprecated
	DESCRIPTION
        "
        Index definition for the pmcryptoCtrlresetMonitoring 
        table
        "
	::= { pmcryptoCtrlresetMonitoringEntry 1 }


pmcryptoCtrlresetMonitoringPortn OBJECT-TYPE
	SYNTAX  EkiState
	MAX-ACCESS read-write
	STATUS deprecated
	DESCRIPTION
        "
         :
        "
	::= { pmcryptoCtrlresetMonitoringEntry 2 }


--- *****************************************************
---     LEAF for the resetCount article
--- *****************************************************
pmcryptoCtrlresetCount OBJECT IDENTIFIER ::= { pmcryptoCtrlOther 259 }




pmcryptoCtrlResetcount OBJECT-TYPE
	  SYNTAX EkiOnOff
	  MAX-ACCESS read-write
	  STATUS current
	  DESCRIPTION
        "
        Module Count Global Reset :This 
        OID resets all the errors counters 
        on the module  <Help > This control 
         initiates a reset of the errors 
        counters on the module
        "
	  ::= { pmcryptoCtrlresetCount 1 }



--- *****************************************************
---     LEAF for the resetRmon article
--- *****************************************************
pmcryptoCtrlresetRmon OBJECT IDENTIFIER ::= { pmcryptoCtrlOther 260 }




pmcryptoCtrlResetrmon OBJECT-TYPE
	  SYNTAX EkiOnOff
	  MAX-ACCESS read-write
	  STATUS current
	  DESCRIPTION
        "
        Module Rmon Global Reset :This 
        OID resets all the Rmon counters 
        on the module  <Help > This control 
         initiates a reset of the Rmon
         counters on the module
        "
	  ::= { pmcryptoCtrlresetRmon 1 }



--- *****************************************************
---     LEAF for the resetMeasurements article
--- *****************************************************
pmcryptoCtrlresetMeasurements OBJECT IDENTIFIER ::= { pmcryptoCtrlOther 261 }




pmcryptoCtrlResetmeasurements OBJECT-TYPE
	  SYNTAX EkiOnOff
	  MAX-ACCESS read-write
	  STATUS current
	  DESCRIPTION
        "
        Management Meas Global Reset :This 
        OID resets some measurements on 
        the management  <Help > This control 
         initiates a reset of some measurements 
        on the management
        "
	  ::= { pmcryptoCtrlresetMeasurements 1 }



--- *********************************************************
---     TABLE for the pmcryptoCtrlclientResetAllCount articles
--- *********************************************************

pmcryptoCtrlclientResetAllCountTable OBJECT-TYPE
	SYNTAX  SEQUENCE OF PmcryptoCtrlclientResetAllCountEntry
	MAX-ACCESS not-accessible
	STATUS current
	DESCRIPTION
        "
        List of pmcryptoCtrlclientResetAllCount 
        Article
        "
	::= { pmcryptoCtrlClient 262 }


pmcryptoCtrlclientResetAllCountEntry OBJECT-TYPE
	SYNTAX PmcryptoCtrlclientResetAllCountEntry
	MAX-ACCESS not-accessible
	STATUS current
	DESCRIPTION
        "
        Row definition for the pmcryptoCtrlclientResetAllCount 
        table
        "
	INDEX   { pmcryptoCtrlclientResetAllCountIndex }
	::= { pmcryptoCtrlclientResetAllCountTable 1 }


PmcryptoCtrlclientResetAllCountEntry ::=
	SEQUENCE {
	pmcryptoCtrlclientResetAllCountIndex
		INTEGER,
	pmcryptoCtrlclientResetAllCountsPortn
		EkiState
	}


pmcryptoCtrlclientResetAllCountIndex OBJECT-TYPE
	SYNTAX  INTEGER(0..128)
	MAX-ACCESS  read-only
	STATUS current
	DESCRIPTION
        "
        Index definition for the pmcryptoCtrlclientResetAllCount 
        table
        "
	::= { pmcryptoCtrlclientResetAllCountEntry 1 }


pmcryptoCtrlclientResetAllCountsPortn OBJECT-TYPE
	SYNTAX  EkiState
	MAX-ACCESS read-write
	STATUS current
	DESCRIPTION
        "
        Client Counters Reset :This OID 
        resets every counter on the client 
        port  <Help>   This control operates 
        a reset on the statistics current 
        ,previous and history client port 
        counters  
        "
	::= { pmcryptoCtrlclientResetAllCountEntry 2 }


--- *********************************************************
---     TABLE for the pmcryptoCtrllineResetAllCount articles
--- *********************************************************

pmcryptoCtrllineResetAllCountTable OBJECT-TYPE
	SYNTAX  SEQUENCE OF PmcryptoCtrllineResetAllCountEntry
	MAX-ACCESS not-accessible
	STATUS current
	DESCRIPTION
        "
        List of pmcryptoCtrllineResetAllCount 
        Article
        "
	::= { pmcryptoCtrlLine 263 }


pmcryptoCtrllineResetAllCountEntry OBJECT-TYPE
	SYNTAX PmcryptoCtrllineResetAllCountEntry
	MAX-ACCESS not-accessible
	STATUS current
	DESCRIPTION
        "
        Row definition for the pmcryptoCtrllineResetAllCount 
        table
        "
	INDEX   { pmcryptoCtrllineResetAllCountIndex }
	::= { pmcryptoCtrllineResetAllCountTable 1 }


PmcryptoCtrllineResetAllCountEntry ::=
	SEQUENCE {
	pmcryptoCtrllineResetAllCountIndex
		INTEGER,
	pmcryptoCtrllineResetAllCountsPortn
		EkiState
	}


pmcryptoCtrllineResetAllCountIndex OBJECT-TYPE
	SYNTAX  INTEGER(0..128)
	MAX-ACCESS  read-only
	STATUS current
	DESCRIPTION
        "
        Index definition for the pmcryptoCtrllineResetAllCount 
        table
        "
	::= { pmcryptoCtrllineResetAllCountEntry 1 }


pmcryptoCtrllineResetAllCountsPortn OBJECT-TYPE
	SYNTAX  EkiState
	MAX-ACCESS read-write
	STATUS current
	DESCRIPTION
        "
        Line Counters Reset :This OID
         resets every counter on the line 
        port  <Help>   This control operates 
        a reset on the statistics current 
        ,previous and history line port 
        counters  
        "
	::= { pmcryptoCtrllineResetAllCountEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pmcryptoCntclientInputErrorCounter articles
--- *********************************************************

pmcryptoCntclientInputErrorCounterTable OBJECT-TYPE
	SYNTAX  SEQUENCE OF PmcryptoCntclientInputErrorCounterEntry
	MAX-ACCESS not-accessible
	STATUS current
	DESCRIPTION
        "
        List of pmcryptoCntclientInputErrorCounter 
        Article
        "
	::= { pmcryptoCntClient 112 }


pmcryptoCntclientInputErrorCounterEntry OBJECT-TYPE
	SYNTAX PmcryptoCntclientInputErrorCounterEntry
	MAX-ACCESS not-accessible
	STATUS current
	DESCRIPTION
        "
        Row definition for the pmcryptoCntclientInputErrorCounter 
        table
        "
	INDEX   { pmcryptoCntclientInputErrorCounterIndex }
	::= { pmcryptoCntclientInputErrorCounterTable 1 }


PmcryptoCntclientInputErrorCounterEntry ::=
	SEQUENCE {
	pmcryptoCntclientInputErrorCounterIndex
		INTEGER,
	pmcryptoCntclientInputErrorCounterValuePortn
		Counter32,
	pmcryptoCntclientInputErrorCounterErrorPortn
		EkiOnOff,
	pmcryptoCntclientInputErrorCounterOverloadPortn
		EkiOnOff
	}


pmcryptoCntclientInputErrorCounterIndex OBJECT-TYPE
	SYNTAX  INTEGER(0..128)
	MAX-ACCESS  read-only
	STATUS current
	DESCRIPTION
        "
        Index definition for the pmcryptoCntclientInputErrorCounter 
        table
        "
	::= { pmcryptoCntclientInputErrorCounterEntry 1 }


pmcryptoCntclientInputErrorCounterValuePortn OBJECT-TYPE
	SYNTAX  Counter32
	MAX-ACCESS read-only
	STATUS current
	DESCRIPTION
        "
        Client Input Errors :This counter 
        is increased each time a 10b/8b 
        running disparity error is detected 
        on the Client input stream  <Help> 
         This counter gives the number
         of errors on the client port (FCS 
        errors for 10GbE and BIP8 errors 
        for STM64,OTU2,OTU2e)
        "
	::= { pmcryptoCntclientInputErrorCounterEntry 2 }


pmcryptoCntclientInputErrorCounterErrorPortn OBJECT-TYPE
	SYNTAX  EkiOnOff
	MAX-ACCESS read-only
	STATUS current
	DESCRIPTION
        "
        Client Counter Error :This OID 
        when set indicates the client error 
        counter value is invalid on Port
        "
	::= { pmcryptoCntclientInputErrorCounterEntry 3 }


pmcryptoCntclientInputErrorCounterOverloadPortn OBJECT-TYPE
	SYNTAX  EkiOnOff
	MAX-ACCESS read-only
	STATUS current
	DESCRIPTION
        "
        Client Counter Overload :This
         OID when set indicates a client 
        input error counter overload on 
        Port
        "
	::= { pmcryptoCntclientInputErrorCounterEntry 4 }


--- *********************************************************
---     TABLE for the pmcryptoCntclientCbipCounter articles
--- *********************************************************

pmcryptoCntclientCbipCounterTable OBJECT-TYPE
	SYNTAX  SEQUENCE OF PmcryptoCntclientCbipCounterEntry
	MAX-ACCESS not-accessible
	STATUS current
	DESCRIPTION
        "
        List of pmcryptoCntclientCbipCounter 
        Article
        "
	::= { pmcryptoCntClient 144 }


pmcryptoCntclientCbipCounterEntry OBJECT-TYPE
	SYNTAX PmcryptoCntclientCbipCounterEntry
	MAX-ACCESS not-accessible
	STATUS current
	DESCRIPTION
        "
        Row definition for the pmcryptoCntclientCbipCounter 
        table
        "
	INDEX   { pmcryptoCntclientCbipCounterIndex }
	::= { pmcryptoCntclientCbipCounterTable 1 }


PmcryptoCntclientCbipCounterEntry ::=
	SEQUENCE {
	pmcryptoCntclientCbipCounterIndex
		INTEGER,
	pmcryptoCntclientCbipCounterValuePortn
		Counter32,
	pmcryptoCntclientCbipCounterErrorPortn
		EkiOnOff,
	pmcryptoCntclientCbipCounterOverloadPortn
		EkiOnOff
	}


pmcryptoCntclientCbipCounterIndex OBJECT-TYPE
	SYNTAX  INTEGER(0..128)
	MAX-ACCESS  read-only
	STATUS current
	DESCRIPTION
        "
        Index definition for the pmcryptoCntclientCbipCounter 
        table
        "
	::= { pmcryptoCntclientCbipCounterEntry 1 }


pmcryptoCntclientCbipCounterValuePortn OBJECT-TYPE
	SYNTAX  Counter32
	MAX-ACCESS read-only
	STATUS current
	DESCRIPTION
        "
        Client Output Errors :This counter 
        is incremented each time a CBIP 
        parity error is detected on the 
        Client output stream  <Help>  This 
        counter gives the number of errors 
        on the client port (FCS errors
         for 10GbE and BIP8 errors for
         STM64,OTU2,OTU2e)
        "
	::= { pmcryptoCntclientCbipCounterEntry 2 }


pmcryptoCntclientCbipCounterErrorPortn OBJECT-TYPE
	SYNTAX  EkiOnOff
	MAX-ACCESS read-only
	STATUS current
	DESCRIPTION
        "
        Client Counter Error :This OID 
        when set indicates the CBIP error 
        counter value is invalid on Port
        "
	::= { pmcryptoCntclientCbipCounterEntry 3 }


pmcryptoCntclientCbipCounterOverloadPortn OBJECT-TYPE
	SYNTAX  EkiOnOff
	MAX-ACCESS read-only
	STATUS current
	DESCRIPTION
        "
        Client CBIP Counter Overload :This 
        OID when set indicates a CBIP error 
        counter overload on Port
        "
	::= { pmcryptoCntclientCbipCounterEntry 4 }


--- *********************************************************
---     TABLE for the pmcryptoCntlocalLineSmBip8ErrorCounter articles
--- *********************************************************

pmcryptoCntlocalLineSmBip8ErrorCounterTable OBJECT-TYPE
	SYNTAX  SEQUENCE OF PmcryptoCntlocalLineSmBip8ErrorCounterEntry
	MAX-ACCESS not-accessible
	STATUS current
	DESCRIPTION
        "
        List of pmcryptoCntlocalLineSmBip8ErrorCounter 
        Article
        "
	::= { pmcryptoCntLine 192 }


pmcryptoCntlocalLineSmBip8ErrorCounterEntry OBJECT-TYPE
	SYNTAX PmcryptoCntlocalLineSmBip8ErrorCounterEntry
	MAX-ACCESS not-accessible
	STATUS current
	DESCRIPTION
        "
        Row definition for the pmcryptoCntlocalLineSmBip8ErrorCounter 
        table
        "
	INDEX   { pmcryptoCntlocalLineSmBip8ErrorCounterIndex }
	::= { pmcryptoCntlocalLineSmBip8ErrorCounterTable 1 }


PmcryptoCntlocalLineSmBip8ErrorCounterEntry ::=
	SEQUENCE {
	pmcryptoCntlocalLineSmBip8ErrorCounterIndex
		INTEGER,
	pmcryptoCntlocalLineSmBip8ErrorCounterValuePortn
		Counter64,
	pmcryptoCntlocalLineSmBip8ErrorCounterErrorPortn
		EkiOnOff,
	pmcryptoCntlocalLineSmBip8ErrorCounterOverloadPortn
		EkiOnOff
	}


pmcryptoCntlocalLineSmBip8ErrorCounterIndex OBJECT-TYPE
	SYNTAX  INTEGER(0..128)
	MAX-ACCESS  read-only
	STATUS current
	DESCRIPTION
        "
        Index definition for the pmcryptoCntlocalLineSmBip8ErrorCounter 
        table
        "
	::= { pmcryptoCntlocalLineSmBip8ErrorCounterEntry 1 }


pmcryptoCntlocalLineSmBip8ErrorCounterValuePortn OBJECT-TYPE
	SYNTAX  Counter64
	MAX-ACCESS read-only
	STATUS current
	DESCRIPTION
        "
        Line Input SM-BIP8 Errors :This 
        OID gives the current Bit Error 
        Rate (residual SM-BIP8 error) after 
        FEC   <Help> This counter gives 
        the current Bit Error Rate after 
        the Soft Decision FEC (residual)
        "
	::= { pmcryptoCntlocalLineSmBip8ErrorCounterEntry 2 }


pmcryptoCntlocalLineSmBip8ErrorCounterErrorPortn OBJECT-TYPE
	SYNTAX  EkiOnOff
	MAX-ACCESS read-only
	STATUS current
	DESCRIPTION
        "
        Line Counter Error :This OID when 
        set indicates the B1 error counter 
        value is invalid on Port
        "
	::= { pmcryptoCntlocalLineSmBip8ErrorCounterEntry 3 }


pmcryptoCntlocalLineSmBip8ErrorCounterOverloadPortn OBJECT-TYPE
	SYNTAX  EkiOnOff
	MAX-ACCESS read-only
	STATUS current
	DESCRIPTION
        "
        Line Counter Overload :This OID 
        when set indicates a B1 error counter 
        overload on Port
        "
	::= { pmcryptoCntlocalLineSmBip8ErrorCounterEntry 4 }


--- *********************************************************
---     TABLE for the pmcryptoCntlocalLineFecCorrectedErrorsCounter articles
--- *********************************************************

pmcryptoCntlocalLineFecCorrectedErrorsCounterTable OBJECT-TYPE
	SYNTAX  SEQUENCE OF PmcryptoCntlocalLineFecCorrectedErrorsCounterEntry
	MAX-ACCESS not-accessible
	STATUS current
	DESCRIPTION
        "
        List of pmcryptoCntlocalLineFecCorrectedErrorsCounter 
        Article
        "
	::= { pmcryptoCntLine 193 }


pmcryptoCntlocalLineFecCorrectedErrorsCounterEntry OBJECT-TYPE
	SYNTAX PmcryptoCntlocalLineFecCorrectedErrorsCounterEntry
	MAX-ACCESS not-accessible
	STATUS current
	DESCRIPTION
        "
        Row definition for the pmcryptoCntlocalLineFecCorrectedErrorsCounter 
        table
        "
	INDEX   { pmcryptoCntlocalLineFecCorrectedErrorsCounterIndex }
	::= { pmcryptoCntlocalLineFecCorrectedErrorsCounterTable 1 }


PmcryptoCntlocalLineFecCorrectedErrorsCounterEntry ::=
	SEQUENCE {
	pmcryptoCntlocalLineFecCorrectedErrorsCounterIndex
		INTEGER,
	pmcryptoCntlocalLineFecCorrectedErrorsCounterValuePortn
		Counter64,
	pmcryptoCntlocalLineFecCorrectedErrorsCounterErrorPortn
		EkiOnOff,
	pmcryptoCntlocalLineFecCorrectedErrorsCounterOverloadPortn
		EkiOnOff
	}


pmcryptoCntlocalLineFecCorrectedErrorsCounterIndex OBJECT-TYPE
	SYNTAX  INTEGER(0..128)
	MAX-ACCESS  read-only
	STATUS current
	DESCRIPTION
        "
        Index definition for the pmcryptoCntlocalLineFecCorrectedErrorsCounter 
        table
        "
	::= { pmcryptoCntlocalLineFecCorrectedErrorsCounterEntry 1 }


pmcryptoCntlocalLineFecCorrectedErrorsCounterValuePortn OBJECT-TYPE
	SYNTAX  Counter64
	MAX-ACCESS read-only
	STATUS current
	DESCRIPTION
        "
        Line Input HD FEC Corrected Errors 
        :This OID gives the current Bit 
        Error Rate before the Hard Decision 
        FEC  <Help> This counter gives
         the current Bit Error Rate before 
        the Hard Decision FEC
        "
	::= { pmcryptoCntlocalLineFecCorrectedErrorsCounterEntry 2 }


pmcryptoCntlocalLineFecCorrectedErrorsCounterErrorPortn OBJECT-TYPE
	SYNTAX  EkiOnOff
	MAX-ACCESS read-only
	STATUS current
	DESCRIPTION
        "
        FEC Counter Error :This bit when 
        set indicates the FEC corrected 
        errors counter value is invalid 
        on Line
        "
	::= { pmcryptoCntlocalLineFecCorrectedErrorsCounterEntry 3 }


pmcryptoCntlocalLineFecCorrectedErrorsCounterOverloadPortn OBJECT-TYPE
	SYNTAX  EkiOnOff
	MAX-ACCESS read-only
	STATUS current
	DESCRIPTION
        "
        FEC Counter Overload :This bit 
        when set indicates a FEC corrected 
        errors counter overload on Line
        "
	::= { pmcryptoCntlocalLineFecCorrectedErrorsCounterEntry 4 }


--- *********************************************************
---     TABLE for the pmcryptoCntremoteLineSmBip8ErrorCounter articles
--- *********************************************************

pmcryptoCntremoteLineSmBip8ErrorCounterTable OBJECT-TYPE
	SYNTAX  SEQUENCE OF PmcryptoCntremoteLineSmBip8ErrorCounterEntry
	MAX-ACCESS not-accessible
	STATUS current
	DESCRIPTION
        "
        List of pmcryptoCntremoteLineSmBip8ErrorCounter 
        Article
        "
	::= { pmcryptoCntLine 194 }


pmcryptoCntremoteLineSmBip8ErrorCounterEntry OBJECT-TYPE
	SYNTAX PmcryptoCntremoteLineSmBip8ErrorCounterEntry
	MAX-ACCESS not-accessible
	STATUS current
	DESCRIPTION
        "
        Row definition for the pmcryptoCntremoteLineSmBip8ErrorCounter 
        table
        "
	INDEX   { pmcryptoCntremoteLineSmBip8ErrorCounterIndex }
	::= { pmcryptoCntremoteLineSmBip8ErrorCounterTable 1 }


PmcryptoCntremoteLineSmBip8ErrorCounterEntry ::=
	SEQUENCE {
	pmcryptoCntremoteLineSmBip8ErrorCounterIndex
		INTEGER,
	pmcryptoCntremoteLineSmBip8ErrorCounterValuePortn
		Counter64,
	pmcryptoCntremoteLineSmBip8ErrorCounterErrorPortn
		EkiOnOff,
	pmcryptoCntremoteLineSmBip8ErrorCounterOverloadPortn
		EkiOnOff
	}


pmcryptoCntremoteLineSmBip8ErrorCounterIndex OBJECT-TYPE
	SYNTAX  INTEGER(0..128)
	MAX-ACCESS  read-only
	STATUS current
	DESCRIPTION
        "
        Index definition for the pmcryptoCntremoteLineSmBip8ErrorCounter 
        table
        "
	::= { pmcryptoCntremoteLineSmBip8ErrorCounterEntry 1 }


pmcryptoCntremoteLineSmBip8ErrorCounterValuePortn OBJECT-TYPE
	SYNTAX  Counter64
	MAX-ACCESS read-only
	STATUS current
	DESCRIPTION
        "
        Remote SM BIP8 :This OID gives 
        the current Bit Error Rate (residual 
        SM-BIP8 error) after FEC on the 
        remote side  <Help> This counter 
        gives the current Bit Error Rate 
        (residual SM-BIP8 error) after
         FEC on the remote side
        "
	::= { pmcryptoCntremoteLineSmBip8ErrorCounterEntry 2 }


pmcryptoCntremoteLineSmBip8ErrorCounterErrorPortn OBJECT-TYPE
	SYNTAX  EkiOnOff
	MAX-ACCESS read-only
	STATUS current
	DESCRIPTION
        "
        Remote Counter Error :
        "
	::= { pmcryptoCntremoteLineSmBip8ErrorCounterEntry 3 }


pmcryptoCntremoteLineSmBip8ErrorCounterOverloadPortn OBJECT-TYPE
	SYNTAX  EkiOnOff
	MAX-ACCESS read-only
	STATUS current
	DESCRIPTION
        "
        Remote Counter Overload :
        "
	::= { pmcryptoCntremoteLineSmBip8ErrorCounterEntry 4 }


--- *********************************************************
---     TABLE for the pmcryptoCntlineDfrmTimCnt articles
--- *********************************************************

pmcryptoCntlineDfrmTimCntTable OBJECT-TYPE
	SYNTAX  SEQUENCE OF PmcryptoCntlineDfrmTimCntEntry
	MAX-ACCESS not-accessible
	STATUS current
	DESCRIPTION
        "
        List of pmcryptoCntlineDfrmTimCnt 
        Article
        "
	::= { pmcryptoCntLine 195 }


pmcryptoCntlineDfrmTimCntEntry OBJECT-TYPE
	SYNTAX PmcryptoCntlineDfrmTimCntEntry
	MAX-ACCESS not-accessible
	STATUS current
	DESCRIPTION
        "
        Row definition for the pmcryptoCntlineDfrmTimCnt 
        table
        "
	INDEX   { pmcryptoCntlineDfrmTimCntIndex }
	::= { pmcryptoCntlineDfrmTimCntTable 1 }


PmcryptoCntlineDfrmTimCntEntry ::=
	SEQUENCE {
	pmcryptoCntlineDfrmTimCntIndex
		INTEGER,
	pmcryptoCntlineDfrmTimCntValuePortn
		Counter64,
	pmcryptoCntlineDfrmTimCntErrorPortn
		EkiOnOff,
	pmcryptoCntlineDfrmTimCntOverloadPortn
		EkiOnOff
	}


pmcryptoCntlineDfrmTimCntIndex OBJECT-TYPE
	SYNTAX  INTEGER(0..128)
	MAX-ACCESS  read-only
	STATUS current
	DESCRIPTION
        "
        Index definition for the pmcryptoCntlineDfrmTimCnt 
        table
        "
	::= { pmcryptoCntlineDfrmTimCntEntry 1 }


pmcryptoCntlineDfrmTimCntValuePortn OBJECT-TYPE
	SYNTAX  Counter64
	MAX-ACCESS read-only
	STATUS current
	DESCRIPTION
        "
        Line Timer Counter :
        "
	::= { pmcryptoCntlineDfrmTimCntEntry 2 }


pmcryptoCntlineDfrmTimCntErrorPortn OBJECT-TYPE
	SYNTAX  EkiOnOff
	MAX-ACCESS read-only
	STATUS current
	DESCRIPTION
        "
        Line Counter Error :This OID when 
        set indicates the deframer timer 
        counter value is invalid on Port
        "
	::= { pmcryptoCntlineDfrmTimCntEntry 3 }


pmcryptoCntlineDfrmTimCntOverloadPortn OBJECT-TYPE
	SYNTAX  EkiOnOff
	MAX-ACCESS read-only
	STATUS current
	DESCRIPTION
        "
        Line Counter Overload :This OID 
        when set indicates a deframer timer 
        counter overload on Port
        "
	::= { pmcryptoCntlineDfrmTimCntEntry 4 }


--- *********************************************************
---     TABLE for the pmcryptoCntlocalLineTrscvPreSdFecErrorCounter articles
--- *********************************************************

pmcryptoCntlocalLineTrscvPreSdFecErrorCounterTable OBJECT-TYPE
	SYNTAX  SEQUENCE OF PmcryptoCntlocalLineTrscvPreSdFecErrorCounterEntry
	MAX-ACCESS not-accessible
	STATUS current
	DESCRIPTION
        "
        List of pmcryptoCntlocalLineTrscvPreSdFecErrorCounter 
        Article
        "
	::= { pmcryptoCntLine 196 }


pmcryptoCntlocalLineTrscvPreSdFecErrorCounterEntry OBJECT-TYPE
	SYNTAX PmcryptoCntlocalLineTrscvPreSdFecErrorCounterEntry
	MAX-ACCESS not-accessible
	STATUS current
	DESCRIPTION
        "
        Row definition for the pmcryptoCntlocalLineTrscvPreSdFecErrorCounter 
        table
        "
	INDEX   { pmcryptoCntlocalLineTrscvPreSdFecErrorCounterIndex }
	::= { pmcryptoCntlocalLineTrscvPreSdFecErrorCounterTable 1 }


PmcryptoCntlocalLineTrscvPreSdFecErrorCounterEntry ::=
	SEQUENCE {
	pmcryptoCntlocalLineTrscvPreSdFecErrorCounterIndex
		INTEGER,
	pmcryptoCntlocalLineTrscvPreSdFecErrorCounterValuePortn
		Counter64,
	pmcryptoCntlocalLineTrscvPreSdFecErrorCounterErrorPortn
		EkiOnOff,
	pmcryptoCntlocalLineTrscvPreSdFecErrorCounterOverloadPortn
		EkiOnOff
	}


pmcryptoCntlocalLineTrscvPreSdFecErrorCounterIndex OBJECT-TYPE
	SYNTAX  INTEGER(0..128)
	MAX-ACCESS  read-only
	STATUS current
	DESCRIPTION
        "
        Index definition for the pmcryptoCntlocalLineTrscvPreSdFecErrorCounter 
        table
        "
	::= { pmcryptoCntlocalLineTrscvPreSdFecErrorCounterEntry 1 }


pmcryptoCntlocalLineTrscvPreSdFecErrorCounterValuePortn OBJECT-TYPE
	SYNTAX  Counter64
	MAX-ACCESS read-only
	STATUS current
	DESCRIPTION
        "
        Pre-SD FEC Errors :This OID gives 
        the current Bit Error Rate before 
        the Soft Decision FEC  <Help> This 
        counter gives the current Bit Error 
        Rate before the Soft Decision FEC
        "
	::= { pmcryptoCntlocalLineTrscvPreSdFecErrorCounterEntry 2 }


pmcryptoCntlocalLineTrscvPreSdFecErrorCounterErrorPortn OBJECT-TYPE
	SYNTAX  EkiOnOff
	MAX-ACCESS read-only
	STATUS current
	DESCRIPTION
        "
        Line Counter Error :This OID when 
        set indicates the deframer timer 
        counter value is invalid on Port
        "
	::= { pmcryptoCntlocalLineTrscvPreSdFecErrorCounterEntry 3 }


pmcryptoCntlocalLineTrscvPreSdFecErrorCounterOverloadPortn OBJECT-TYPE
	SYNTAX  EkiOnOff
	MAX-ACCESS read-only
	STATUS current
	DESCRIPTION
        "
        Line Counter Overload :This OID 
        when set indicates a deframer timer 
        counter overload on Port
        "
	::= { pmcryptoCntlocalLineTrscvPreSdFecErrorCounterEntry 4 }


--- *********************************************************
---     TABLE for the pmcryptoCntlocalLineTrscvUncorrectedSdFecErrorCounter articles
--- *********************************************************

pmcryptoCntlocalLineTrscvUncorrectedSdFecErrorCounterTable OBJECT-TYPE
	SYNTAX  SEQUENCE OF PmcryptoCntlocalLineTrscvUncorrectedSdFecErrorCounterEntry
	MAX-ACCESS not-accessible
	STATUS current
	DESCRIPTION
        "
        List of pmcryptoCntlocalLineTrscvUncorrectedSdFecErrorCounter 
        Article
        "
	::= { pmcryptoCntLine 197 }


pmcryptoCntlocalLineTrscvUncorrectedSdFecErrorCounterEntry OBJECT-TYPE
	SYNTAX PmcryptoCntlocalLineTrscvUncorrectedSdFecErrorCounterEntry
	MAX-ACCESS not-accessible
	STATUS current
	DESCRIPTION
        "
        Row definition for the pmcryptoCntlocalLineTrscvUncorrectedSdFecErrorCounter 
        table
        "
	INDEX   { pmcryptoCntlocalLineTrscvUncorrectedSdFecErrorCounterIndex }
	::= { pmcryptoCntlocalLineTrscvUncorrectedSdFecErrorCounterTable 1 }


PmcryptoCntlocalLineTrscvUncorrectedSdFecErrorCounterEntry ::=
	SEQUENCE {
	pmcryptoCntlocalLineTrscvUncorrectedSdFecErrorCounterIndex
		INTEGER,
	pmcryptoCntlocalLineTrscvUncorrectedSdFecErrorCounterValuePortn
		Counter64,
	pmcryptoCntlocalLineTrscvUncorrectedSdFecErrorCounterErrorPortn
		EkiOnOff,
	pmcryptoCntlocalLineTrscvUncorrectedSdFecErrorCounterOverloadPortn
		EkiOnOff
	}


pmcryptoCntlocalLineTrscvUncorrectedSdFecErrorCounterIndex OBJECT-TYPE
	SYNTAX  INTEGER(0..128)
	MAX-ACCESS  read-only
	STATUS current
	DESCRIPTION
        "
        Index definition for the pmcryptoCntlocalLineTrscvUncorrectedSdFecErrorCounter 
        table
        "
	::= { pmcryptoCntlocalLineTrscvUncorrectedSdFecErrorCounterEntry 1 }


pmcryptoCntlocalLineTrscvUncorrectedSdFecErrorCounterValuePortn OBJECT-TYPE
	SYNTAX  Counter64
	MAX-ACCESS read-only
	STATUS current
	DESCRIPTION
        "
        Uncorrected SD FEC Errors :This 
        OID gives the current Bit Error 
        Rate after the Soft Decision FEC 
        (residual)  <Help> This counter 
        gives the current Bit Error Rate 
        after the Soft Decision FEC (residual)
        "
	::= { pmcryptoCntlocalLineTrscvUncorrectedSdFecErrorCounterEntry 2 }


pmcryptoCntlocalLineTrscvUncorrectedSdFecErrorCounterErrorPortn OBJECT-TYPE
	SYNTAX  EkiOnOff
	MAX-ACCESS read-only
	STATUS current
	DESCRIPTION
        "
        Line Counter Error :This OID when 
        set indicates the deframer timer 
        counter value is invalid on Port
        "
	::= { pmcryptoCntlocalLineTrscvUncorrectedSdFecErrorCounterEntry 3 }


pmcryptoCntlocalLineTrscvUncorrectedSdFecErrorCounterOverloadPortn OBJECT-TYPE
	SYNTAX  EkiOnOff
	MAX-ACCESS read-only
	STATUS current
	DESCRIPTION
        "
        Line Counter Overload :This OID 
        when set indicates a deframer timer 
        counter overload on Port
        "
	::= { pmcryptoCntlocalLineTrscvUncorrectedSdFecErrorCounterEntry 4 }


--- *********************************************************
---     TABLE for the pmcryptoCntlocalLineTrscvPreSdFecBitCounter articles
--- *********************************************************

pmcryptoCntlocalLineTrscvPreSdFecBitCounterTable OBJECT-TYPE
	SYNTAX  SEQUENCE OF PmcryptoCntlocalLineTrscvPreSdFecBitCounterEntry
	MAX-ACCESS not-accessible
	STATUS current
	DESCRIPTION
        "
        List of pmcryptoCntlocalLineTrscvPreSdFecBitCounter 
        Article
        "
	::= { pmcryptoCntLine 198 }


pmcryptoCntlocalLineTrscvPreSdFecBitCounterEntry OBJECT-TYPE
	SYNTAX PmcryptoCntlocalLineTrscvPreSdFecBitCounterEntry
	MAX-ACCESS not-accessible
	STATUS current
	DESCRIPTION
        "
        Row definition for the pmcryptoCntlocalLineTrscvPreSdFecBitCounter 
        table
        "
	INDEX   { pmcryptoCntlocalLineTrscvPreSdFecBitCounterIndex }
	::= { pmcryptoCntlocalLineTrscvPreSdFecBitCounterTable 1 }


PmcryptoCntlocalLineTrscvPreSdFecBitCounterEntry ::=
	SEQUENCE {
	pmcryptoCntlocalLineTrscvPreSdFecBitCounterIndex
		INTEGER,
	pmcryptoCntlocalLineTrscvPreSdFecBitCounterValuePortn
		Counter64,
	pmcryptoCntlocalLineTrscvPreSdFecBitCounterErrorPortn
		EkiOnOff,
	pmcryptoCntlocalLineTrscvPreSdFecBitCounterOverloadPortn
		EkiOnOff
	}


pmcryptoCntlocalLineTrscvPreSdFecBitCounterIndex OBJECT-TYPE
	SYNTAX  INTEGER(0..128)
	MAX-ACCESS  read-only
	STATUS current
	DESCRIPTION
        "
        Index definition for the pmcryptoCntlocalLineTrscvPreSdFecBitCounter 
        table
        "
	::= { pmcryptoCntlocalLineTrscvPreSdFecBitCounterEntry 1 }


pmcryptoCntlocalLineTrscvPreSdFecBitCounterValuePortn OBJECT-TYPE
	SYNTAX  Counter64
	MAX-ACCESS read-only
	STATUS current
	DESCRIPTION
        "
        Pre-SD FEC Bit Counter :This OID 
        gives the current Bit count before 
        the Soft Decision FEC  <Help> This 
        counter gives the current Bit Count 
        before the Soft Decision FEC
        "
	::= { pmcryptoCntlocalLineTrscvPreSdFecBitCounterEntry 2 }


pmcryptoCntlocalLineTrscvPreSdFecBitCounterErrorPortn OBJECT-TYPE
	SYNTAX  EkiOnOff
	MAX-ACCESS read-only
	STATUS current
	DESCRIPTION
        "
        Line Counter Error :This OID when 
        set indicates the deframer timer 
        counter value is invalid on Port
        "
	::= { pmcryptoCntlocalLineTrscvPreSdFecBitCounterEntry 3 }


pmcryptoCntlocalLineTrscvPreSdFecBitCounterOverloadPortn OBJECT-TYPE
	SYNTAX  EkiOnOff
	MAX-ACCESS read-only
	STATUS current
	DESCRIPTION
        "
        Line Counter Overload :This OID 
        when set indicates a deframer timer 
        counter overload on Port
        "
	::= { pmcryptoCntlocalLineTrscvPreSdFecBitCounterEntry 4 }


--- *********************************************************
---     TABLE for the pmcryptoCntlocalLineTrscvUncorrectedSdFecBitCounter articles
--- *********************************************************

pmcryptoCntlocalLineTrscvUncorrectedSdFecBitCounterTable OBJECT-TYPE
	SYNTAX  SEQUENCE OF PmcryptoCntlocalLineTrscvUncorrectedSdFecBitCounterEntry
	MAX-ACCESS not-accessible
	STATUS current
	DESCRIPTION
        "
        List of pmcryptoCntlocalLineTrscvUncorrectedSdFecBitCounter 
        Article
        "
	::= { pmcryptoCntLine 199 }


pmcryptoCntlocalLineTrscvUncorrectedSdFecBitCounterEntry OBJECT-TYPE
	SYNTAX PmcryptoCntlocalLineTrscvUncorrectedSdFecBitCounterEntry
	MAX-ACCESS not-accessible
	STATUS current
	DESCRIPTION
        "
        Row definition for the pmcryptoCntlocalLineTrscvUncorrectedSdFecBitCounter 
        table
        "
	INDEX   { pmcryptoCntlocalLineTrscvUncorrectedSdFecBitCounterIndex }
	::= { pmcryptoCntlocalLineTrscvUncorrectedSdFecBitCounterTable 1 }


PmcryptoCntlocalLineTrscvUncorrectedSdFecBitCounterEntry ::=
	SEQUENCE {
	pmcryptoCntlocalLineTrscvUncorrectedSdFecBitCounterIndex
		INTEGER,
	pmcryptoCntlocalLineTrscvUncorrectedSdFecBitCounterValuePortn
		Counter64,
	pmcryptoCntlocalLineTrscvUncorrectedSdFecBitCounterErrorPortn
		EkiOnOff,
	pmcryptoCntlocalLineTrscvUncorrectedSdFecBitCounterOverloadPortn
		EkiOnOff
	}


pmcryptoCntlocalLineTrscvUncorrectedSdFecBitCounterIndex OBJECT-TYPE
	SYNTAX  INTEGER(0..128)
	MAX-ACCESS  read-only
	STATUS current
	DESCRIPTION
        "
        Index definition for the pmcryptoCntlocalLineTrscvUncorrectedSdFecBitCounter 
        table
        "
	::= { pmcryptoCntlocalLineTrscvUncorrectedSdFecBitCounterEntry 1 }


pmcryptoCntlocalLineTrscvUncorrectedSdFecBitCounterValuePortn OBJECT-TYPE
	SYNTAX  Counter64
	MAX-ACCESS read-only
	STATUS current
	DESCRIPTION
        "
        Uncorrected SD FEC Bit Counter 
        :This OID gives the current Bit 
        count after the Soft Decision FEC 
        (residual)  <Help> This counter 
        gives the current Bit Count after 
        the Soft Decision FEC (residual)
        "
	::= { pmcryptoCntlocalLineTrscvUncorrectedSdFecBitCounterEntry 2 }


pmcryptoCntlocalLineTrscvUncorrectedSdFecBitCounterErrorPortn OBJECT-TYPE
	SYNTAX  EkiOnOff
	MAX-ACCESS read-only
	STATUS current
	DESCRIPTION
        "
        Line Counter Error :This OID when 
        set indicates the deframer timer 
        counter value is invalid on Port
        "
	::= { pmcryptoCntlocalLineTrscvUncorrectedSdFecBitCounterEntry 3 }


pmcryptoCntlocalLineTrscvUncorrectedSdFecBitCounterOverloadPortn OBJECT-TYPE
	SYNTAX  EkiOnOff
	MAX-ACCESS read-only
	STATUS current
	DESCRIPTION
        "
        Line Counter Overload :This OID 
        when set indicates a deframer timer 
        counter overload on Port
        "
	::= { pmcryptoCntlocalLineTrscvUncorrectedSdFecBitCounterEntry 4 }







--- *****************************************************
--- $$$$$$$$$$$$$$$$$$$$$$$$$$$$$$$$$$$$$$$$$$$$$$$$$$$$$
---     RMON - 64 bits COUNTERS
--- $$$$$$$$$$$$$$$$$$$$$$$$$$$$$$$$$$$$$$$$$$$$$$$$$$$$$
--- *****************************************************



--- *********************************************************
---     TABLE for the pmcryptoMonupRmonBytesCounterClientInput articles
--- *********************************************************

pmcryptoMonupRmonBytesCounterClientInputTable OBJECT-TYPE
	SYNTAX  SEQUENCE OF PmcryptoMonupRmonBytesCounterClientInputEntry
	MAX-ACCESS not-accessible
	STATUS current
	DESCRIPTION
        "
        List of pmcryptoMonupRmonBytesCounterClientInput 
        Article
        "
	::= { pmcryptoMonClientRmonCounter 16 }


pmcryptoMonupRmonBytesCounterClientInputEntry OBJECT-TYPE
	SYNTAX PmcryptoMonupRmonBytesCounterClientInputEntry
	MAX-ACCESS not-accessible
	STATUS current
	DESCRIPTION
        "
        Row definition for the pmcryptoMonupRmonBytesCounterClientInput 
        table
        "
	INDEX   { pmcryptoMonupRmonBytesCounterClientInputIndex }
	::= { pmcryptoMonupRmonBytesCounterClientInputTable 1 }


PmcryptoMonupRmonBytesCounterClientInputEntry ::=
	SEQUENCE {
	pmcryptoMonupRmonBytesCounterClientInputIndex
		INTEGER,
	pmcryptoMonupRmonBytesCounterClientInputValuePortn
		Counter64,
	pmcryptoMonupRmonBytesCounterClientInputErrorPortn
		EkiOnOff,
	pmcryptoMonupRmonBytesCounterClientInputOverloadPortn
		EkiOnOff
	}


pmcryptoMonupRmonBytesCounterClientInputIndex OBJECT-TYPE
	SYNTAX  INTEGER(0..128)
	MAX-ACCESS  read-only
	STATUS current
	DESCRIPTION
        "
        Index definition for the pmcryptoMonupRmonBytesCounterClientInput 
        table
        "
	::= { pmcryptoMonupRmonBytesCounterClientInputEntry 1 }


pmcryptoMonupRmonBytesCounterClientInputValuePortn OBJECT-TYPE
	SYNTAX  Counter64
	MAX-ACCESS read-only
	STATUS current
	DESCRIPTION
        "
        Client Input Bytes :This counter 
        is increased each time a data byte 
        is received on the client port
          <Help>  This counter gives the 
        number of bytes received on the 
        client port
        "
	::= { pmcryptoMonupRmonBytesCounterClientInputEntry 2 }


pmcryptoMonupRmonBytesCounterClientInputErrorPortn OBJECT-TYPE
	SYNTAX  EkiOnOff
	MAX-ACCESS read-only
	STATUS current
	DESCRIPTION
        "
        Bytes Counter Error :This OID
         when set indicates the Bytes counter 
        value is invalid on client port
        "
	::= { pmcryptoMonupRmonBytesCounterClientInputEntry 3 }


pmcryptoMonupRmonBytesCounterClientInputOverloadPortn OBJECT-TYPE
	SYNTAX  EkiOnOff
	MAX-ACCESS read-only
	STATUS current
	DESCRIPTION
        "
        Bytes Counter Overload :This OID 
        when set indicates a Bytes counter 
        overload on client port
        "
	::= { pmcryptoMonupRmonBytesCounterClientInputEntry 4 }


--- *********************************************************
---     TABLE for the pmcryptoMonupRmonCrcErrorsCounterClientInput articles
--- *********************************************************

pmcryptoMonupRmonCrcErrorsCounterClientInputTable OBJECT-TYPE
	SYNTAX  SEQUENCE OF PmcryptoMonupRmonCrcErrorsCounterClientInputEntry
	MAX-ACCESS not-accessible
	STATUS current
	DESCRIPTION
        "
        List of pmcryptoMonupRmonCrcErrorsCounterClientInput 
        Article
        "
	::= { pmcryptoMonClientRmonCounter 48 }


pmcryptoMonupRmonCrcErrorsCounterClientInputEntry OBJECT-TYPE
	SYNTAX PmcryptoMonupRmonCrcErrorsCounterClientInputEntry
	MAX-ACCESS not-accessible
	STATUS current
	DESCRIPTION
        "
        Row definition for the pmcryptoMonupRmonCrcErrorsCounterClientInput 
        table
        "
	INDEX   { pmcryptoMonupRmonCrcErrorsCounterClientInputIndex }
	::= { pmcryptoMonupRmonCrcErrorsCounterClientInputTable 1 }


PmcryptoMonupRmonCrcErrorsCounterClientInputEntry ::=
	SEQUENCE {
	pmcryptoMonupRmonCrcErrorsCounterClientInputIndex
		INTEGER,
	pmcryptoMonupRmonCrcErrorsCounterClientInputValuePortn
		Counter64,
	pmcryptoMonupRmonCrcErrorsCounterClientInputErrorPortn
		EkiOnOff,
	pmcryptoMonupRmonCrcErrorsCounterClientInputOverloadPortn
		EkiOnOff
	}


pmcryptoMonupRmonCrcErrorsCounterClientInputIndex OBJECT-TYPE
	SYNTAX  INTEGER(0..128)
	MAX-ACCESS  read-only
	STATUS current
	DESCRIPTION
        "
        Index definition for the pmcryptoMonupRmonCrcErrorsCounterClientInput 
        table
        "
	::= { pmcryptoMonupRmonCrcErrorsCounterClientInputEntry 1 }


pmcryptoMonupRmonCrcErrorsCounterClientInputValuePortn OBJECT-TYPE
	SYNTAX  Counter64
	MAX-ACCESS read-only
	STATUS current
	DESCRIPTION
        "
        Client Input CRC Errors :This
         counter is increased each time 
        a CRC error is detected on the
         client port<Help>  This counter 
        gives the number of CRC Errors
         received on the client port
        "
	::= { pmcryptoMonupRmonCrcErrorsCounterClientInputEntry 2 }


pmcryptoMonupRmonCrcErrorsCounterClientInputErrorPortn OBJECT-TYPE
	SYNTAX  EkiOnOff
	MAX-ACCESS read-only
	STATUS current
	DESCRIPTION
        "
        CRC Errors Counter Error :This 
        OID when set indicates the CRC
         Errors counter value is invalid 
        on client port
        "
	::= { pmcryptoMonupRmonCrcErrorsCounterClientInputEntry 3 }


pmcryptoMonupRmonCrcErrorsCounterClientInputOverloadPortn OBJECT-TYPE
	SYNTAX  EkiOnOff
	MAX-ACCESS read-only
	STATUS current
	DESCRIPTION
        "
        CRC Errors Counter Overload :This 
        OID when set indicates a CRC Errors 
        counter overload on client port
        "
	::= { pmcryptoMonupRmonCrcErrorsCounterClientInputEntry 4 }


--- *********************************************************
---     TABLE for the pmcryptoMonupRmonPacketsCounterClientInput articles
--- *********************************************************

pmcryptoMonupRmonPacketsCounterClientInputTable OBJECT-TYPE
	SYNTAX  SEQUENCE OF PmcryptoMonupRmonPacketsCounterClientInputEntry
	MAX-ACCESS not-accessible
	STATUS current
	DESCRIPTION
        "
        List of pmcryptoMonupRmonPacketsCounterClientInput 
        Article
        "
	::= { pmcryptoMonClientRmonCounter 80 }


pmcryptoMonupRmonPacketsCounterClientInputEntry OBJECT-TYPE
	SYNTAX PmcryptoMonupRmonPacketsCounterClientInputEntry
	MAX-ACCESS not-accessible
	STATUS current
	DESCRIPTION
        "
        Row definition for the pmcryptoMonupRmonPacketsCounterClientInput 
        table
        "
	INDEX   { pmcryptoMonupRmonPacketsCounterClientInputIndex }
	::= { pmcryptoMonupRmonPacketsCounterClientInputTable 1 }


PmcryptoMonupRmonPacketsCounterClientInputEntry ::=
	SEQUENCE {
	pmcryptoMonupRmonPacketsCounterClientInputIndex
		INTEGER,
	pmcryptoMonupRmonPacketsCounterClientInputValuePortn
		Counter64,
	pmcryptoMonupRmonPacketsCounterClientInputErrorPortn
		EkiOnOff,
	pmcryptoMonupRmonPacketsCounterClientInputOverloadPortn
		EkiOnOff
	}


pmcryptoMonupRmonPacketsCounterClientInputIndex OBJECT-TYPE
	SYNTAX  INTEGER(0..128)
	MAX-ACCESS  read-only
	STATUS current
	DESCRIPTION
        "
        Index definition for the pmcryptoMonupRmonPacketsCounterClientInput 
        table
        "
	::= { pmcryptoMonupRmonPacketsCounterClientInputEntry 1 }


pmcryptoMonupRmonPacketsCounterClientInputValuePortn OBJECT-TYPE
	SYNTAX  Counter64
	MAX-ACCESS read-only
	STATUS current
	DESCRIPTION
        "
        Client Input Packets :This counter 
        is increased each time a packet 
        is received on the client port
          <Help>  This counter gives the 
        number of packets received on the 
        client port
        "
	::= { pmcryptoMonupRmonPacketsCounterClientInputEntry 2 }


pmcryptoMonupRmonPacketsCounterClientInputErrorPortn OBJECT-TYPE
	SYNTAX  EkiOnOff
	MAX-ACCESS read-only
	STATUS current
	DESCRIPTION
        "
        Packets Counter Error :This OID 
        when set indicates the Packets
         counter value is invalid on client 
        port
        "
	::= { pmcryptoMonupRmonPacketsCounterClientInputEntry 3 }


pmcryptoMonupRmonPacketsCounterClientInputOverloadPortn OBJECT-TYPE
	SYNTAX  EkiOnOff
	MAX-ACCESS read-only
	STATUS current
	DESCRIPTION
        "
        Packets Counter Overload :This 
        OID when set indicates a Packets 
        counter overload on client port
        "
	::= { pmcryptoMonupRmonPacketsCounterClientInputEntry 4 }


--- *********************************************************
---     TABLE for the pmcryptoMonupRmonBroadcastCounterClientInput articles
--- *********************************************************

pmcryptoMonupRmonBroadcastCounterClientInputTable OBJECT-TYPE
	SYNTAX  SEQUENCE OF PmcryptoMonupRmonBroadcastCounterClientInputEntry
	MAX-ACCESS not-accessible
	STATUS current
	DESCRIPTION
        "
        List of pmcryptoMonupRmonBroadcastCounterClientInput 
        Article
        "
	::= { pmcryptoMonClientRmonCounter 112 }


pmcryptoMonupRmonBroadcastCounterClientInputEntry OBJECT-TYPE
	SYNTAX PmcryptoMonupRmonBroadcastCounterClientInputEntry
	MAX-ACCESS not-accessible
	STATUS current
	DESCRIPTION
        "
        Row definition for the pmcryptoMonupRmonBroadcastCounterClientInput 
        table
        "
	INDEX   { pmcryptoMonupRmonBroadcastCounterClientInputIndex }
	::= { pmcryptoMonupRmonBroadcastCounterClientInputTable 1 }


PmcryptoMonupRmonBroadcastCounterClientInputEntry ::=
	SEQUENCE {
	pmcryptoMonupRmonBroadcastCounterClientInputIndex
		INTEGER,
	pmcryptoMonupRmonBroadcastCounterClientInputValuePortn
		Counter64,
	pmcryptoMonupRmonBroadcastCounterClientInputErrorPortn
		EkiOnOff,
	pmcryptoMonupRmonBroadcastCounterClientInputOverloadPortn
		EkiOnOff
	}


pmcryptoMonupRmonBroadcastCounterClientInputIndex OBJECT-TYPE
	SYNTAX  INTEGER(0..128)
	MAX-ACCESS  read-only
	STATUS current
	DESCRIPTION
        "
        Index definition for the pmcryptoMonupRmonBroadcastCounterClientInput 
        table
        "
	::= { pmcryptoMonupRmonBroadcastCounterClientInputEntry 1 }


pmcryptoMonupRmonBroadcastCounterClientInputValuePortn OBJECT-TYPE
	SYNTAX  Counter64
	MAX-ACCESS read-only
	STATUS current
	DESCRIPTION
        "
        Client Input Broadcast Packets 
        :This counter is increased each 
        time a broadcast packet is received 
        on the client port  <Help>  This 
        counter gives the number of Broadcast 
        packets received on the client
         port
        "
	::= { pmcryptoMonupRmonBroadcastCounterClientInputEntry 2 }


pmcryptoMonupRmonBroadcastCounterClientInputErrorPortn OBJECT-TYPE
	SYNTAX  EkiOnOff
	MAX-ACCESS read-only
	STATUS current
	DESCRIPTION
        "
        Broadcast Counter Error :This
         OID when set indicates the Broadcast 
        counter value is invalid on client 
        port
        "
	::= { pmcryptoMonupRmonBroadcastCounterClientInputEntry 3 }


pmcryptoMonupRmonBroadcastCounterClientInputOverloadPortn OBJECT-TYPE
	SYNTAX  EkiOnOff
	MAX-ACCESS read-only
	STATUS current
	DESCRIPTION
        "
        Broadcast Counter Overload :This 
        OID when set indicates a Broadcast 
        counter overload on client port
        "
	::= { pmcryptoMonupRmonBroadcastCounterClientInputEntry 4 }


--- *********************************************************
---     TABLE for the pmcryptoMonupRmonMulticastCounterClientInput articles
--- *********************************************************

pmcryptoMonupRmonMulticastCounterClientInputTable OBJECT-TYPE
	SYNTAX  SEQUENCE OF PmcryptoMonupRmonMulticastCounterClientInputEntry
	MAX-ACCESS not-accessible
	STATUS current
	DESCRIPTION
        "
        List of pmcryptoMonupRmonMulticastCounterClientInput 
        Article
        "
	::= { pmcryptoMonClientRmonCounter 144 }


pmcryptoMonupRmonMulticastCounterClientInputEntry OBJECT-TYPE
	SYNTAX PmcryptoMonupRmonMulticastCounterClientInputEntry
	MAX-ACCESS not-accessible
	STATUS current
	DESCRIPTION
        "
        Row definition for the pmcryptoMonupRmonMulticastCounterClientInput 
        table
        "
	INDEX   { pmcryptoMonupRmonMulticastCounterClientInputIndex }
	::= { pmcryptoMonupRmonMulticastCounterClientInputTable 1 }


PmcryptoMonupRmonMulticastCounterClientInputEntry ::=
	SEQUENCE {
	pmcryptoMonupRmonMulticastCounterClientInputIndex
		INTEGER,
	pmcryptoMonupRmonMulticastCounterClientInputValuePortn
		Counter64,
	pmcryptoMonupRmonMulticastCounterClientInputErrorPortn
		EkiOnOff,
	pmcryptoMonupRmonMulticastCounterClientInputOverloadPortn
		EkiOnOff
	}


pmcryptoMonupRmonMulticastCounterClientInputIndex OBJECT-TYPE
	SYNTAX  INTEGER(0..128)
	MAX-ACCESS  read-only
	STATUS current
	DESCRIPTION
        "
        Index definition for the pmcryptoMonupRmonMulticastCounterClientInput 
        table
        "
	::= { pmcryptoMonupRmonMulticastCounterClientInputEntry 1 }


pmcryptoMonupRmonMulticastCounterClientInputValuePortn OBJECT-TYPE
	SYNTAX  Counter64
	MAX-ACCESS read-only
	STATUS current
	DESCRIPTION
        "
        Client Input Multicast Packets 
        :This counter is increased each 
        time a Multicast packet is received 
        on the client port  <Help>  This 
        counter gives the number of Multicast 
        packets received on the client
         port
        "
	::= { pmcryptoMonupRmonMulticastCounterClientInputEntry 2 }


pmcryptoMonupRmonMulticastCounterClientInputErrorPortn OBJECT-TYPE
	SYNTAX  EkiOnOff
	MAX-ACCESS read-only
	STATUS current
	DESCRIPTION
        "
        Multicast Counter Error :This
         OID when set indicates the Multicast 
        counter value is invalid on client 
        port
        "
	::= { pmcryptoMonupRmonMulticastCounterClientInputEntry 3 }


pmcryptoMonupRmonMulticastCounterClientInputOverloadPortn OBJECT-TYPE
	SYNTAX  EkiOnOff
	MAX-ACCESS read-only
	STATUS current
	DESCRIPTION
        "
        Multicast Counter Overload :This 
        OID when set indicates a Multicast 
        counter overload on client port
        "
	::= { pmcryptoMonupRmonMulticastCounterClientInputEntry 4 }


--- *********************************************************
---     TABLE for the pmcryptoMonupRmonPauseFrameCounterClientInput articles
--- *********************************************************

pmcryptoMonupRmonPauseFrameCounterClientInputTable OBJECT-TYPE
	SYNTAX  SEQUENCE OF PmcryptoMonupRmonPauseFrameCounterClientInputEntry
	MAX-ACCESS not-accessible
	STATUS current
	DESCRIPTION
        "
        List of pmcryptoMonupRmonPauseFrameCounterClientInput 
        Article
        "
	::= { pmcryptoMonClientRmonCounter 176 }


pmcryptoMonupRmonPauseFrameCounterClientInputEntry OBJECT-TYPE
	SYNTAX PmcryptoMonupRmonPauseFrameCounterClientInputEntry
	MAX-ACCESS not-accessible
	STATUS current
	DESCRIPTION
        "
        Row definition for the pmcryptoMonupRmonPauseFrameCounterClientInput 
        table
        "
	INDEX   { pmcryptoMonupRmonPauseFrameCounterClientInputIndex }
	::= { pmcryptoMonupRmonPauseFrameCounterClientInputTable 1 }


PmcryptoMonupRmonPauseFrameCounterClientInputEntry ::=
	SEQUENCE {
	pmcryptoMonupRmonPauseFrameCounterClientInputIndex
		INTEGER,
	pmcryptoMonupRmonPauseFrameCounterClientInputValuePortn
		Counter64,
	pmcryptoMonupRmonPauseFrameCounterClientInputErrorPortn
		EkiOnOff,
	pmcryptoMonupRmonPauseFrameCounterClientInputOverloadPortn
		EkiOnOff
	}


pmcryptoMonupRmonPauseFrameCounterClientInputIndex OBJECT-TYPE
	SYNTAX  INTEGER(0..128)
	MAX-ACCESS  read-only
	STATUS current
	DESCRIPTION
        "
        Index definition for the pmcryptoMonupRmonPauseFrameCounterClientInput 
        table
        "
	::= { pmcryptoMonupRmonPauseFrameCounterClientInputEntry 1 }


pmcryptoMonupRmonPauseFrameCounterClientInputValuePortn OBJECT-TYPE
	SYNTAX  Counter64
	MAX-ACCESS read-only
	STATUS current
	DESCRIPTION
        "
        Client Input Pause Frames :This 
        counter is increased each time
         a Pause frame is received on the 
        client port  <Help>  This counter 
        gives the number of Pause frames 
        received on the client port
        "
	::= { pmcryptoMonupRmonPauseFrameCounterClientInputEntry 2 }


pmcryptoMonupRmonPauseFrameCounterClientInputErrorPortn OBJECT-TYPE
	SYNTAX  EkiOnOff
	MAX-ACCESS read-only
	STATUS current
	DESCRIPTION
        "
        Pause Counter Error :This OID
         when set indicates the Pause counter 
        value is invalid on client port
        "
	::= { pmcryptoMonupRmonPauseFrameCounterClientInputEntry 3 }


pmcryptoMonupRmonPauseFrameCounterClientInputOverloadPortn OBJECT-TYPE
	SYNTAX  EkiOnOff
	MAX-ACCESS read-only
	STATUS current
	DESCRIPTION
        "
        Pause Counter Overload :This OID 
        when set indicates a Pause counter 
        overload on client port
        "
	::= { pmcryptoMonupRmonPauseFrameCounterClientInputEntry 4 }


--- *********************************************************
---     TABLE for the pmcryptoMonupRmonUnicastCounterClientInput articles
--- *********************************************************

pmcryptoMonupRmonUnicastCounterClientInputTable OBJECT-TYPE
	SYNTAX  SEQUENCE OF PmcryptoMonupRmonUnicastCounterClientInputEntry
	MAX-ACCESS not-accessible
	STATUS current
	DESCRIPTION
        "
        List of pmcryptoMonupRmonUnicastCounterClientInput 
        Article
        "
	::= { pmcryptoMonClientRmonCounter 304 }


pmcryptoMonupRmonUnicastCounterClientInputEntry OBJECT-TYPE
	SYNTAX PmcryptoMonupRmonUnicastCounterClientInputEntry
	MAX-ACCESS not-accessible
	STATUS current
	DESCRIPTION
        "
        Row definition for the pmcryptoMonupRmonUnicastCounterClientInput 
        table
        "
	INDEX   { pmcryptoMonupRmonUnicastCounterClientInputIndex }
	::= { pmcryptoMonupRmonUnicastCounterClientInputTable 1 }


PmcryptoMonupRmonUnicastCounterClientInputEntry ::=
	SEQUENCE {
	pmcryptoMonupRmonUnicastCounterClientInputIndex
		INTEGER,
	pmcryptoMonupRmonUnicastCounterClientInputValuePortn
		Counter64,
	pmcryptoMonupRmonUnicastCounterClientInputErrorPortn
		EkiOnOff,
	pmcryptoMonupRmonUnicastCounterClientInputOverloadPortn
		EkiOnOff
	}


pmcryptoMonupRmonUnicastCounterClientInputIndex OBJECT-TYPE
	SYNTAX  INTEGER(0..128)
	MAX-ACCESS  read-only
	STATUS current
	DESCRIPTION
        "
        Index definition for the pmcryptoMonupRmonUnicastCounterClientInput 
        table
        "
	::= { pmcryptoMonupRmonUnicastCounterClientInputEntry 1 }


pmcryptoMonupRmonUnicastCounterClientInputValuePortn OBJECT-TYPE
	SYNTAX  Counter64
	MAX-ACCESS read-only
	STATUS current
	DESCRIPTION
        "
        Client Input Unicast Packets :This 
        counter is increased each time
         a Unicast packet is received on 
        the client port  <Help>  This counter 
        gives the number of Unicast packets 
        received on the client port
        "
	::= { pmcryptoMonupRmonUnicastCounterClientInputEntry 2 }


pmcryptoMonupRmonUnicastCounterClientInputErrorPortn OBJECT-TYPE
	SYNTAX  EkiOnOff
	MAX-ACCESS read-only
	STATUS current
	DESCRIPTION
        "
        Unicast Counter Error :This OID 
        when set indicates the Unicast
         counter value is invalid on client 
        port
        "
	::= { pmcryptoMonupRmonUnicastCounterClientInputEntry 3 }


pmcryptoMonupRmonUnicastCounterClientInputOverloadPortn OBJECT-TYPE
	SYNTAX  EkiOnOff
	MAX-ACCESS read-only
	STATUS current
	DESCRIPTION
        "
        Unicast Counter Overload :This 
        OID when set indicates a Unicast 
        counter overload on client port
        "
	::= { pmcryptoMonupRmonUnicastCounterClientInputEntry 4 }


--- *********************************************************
---     TABLE for the pmcryptoMonupRmonNonunicastCounterClientInput articles
--- *********************************************************

pmcryptoMonupRmonNonunicastCounterClientInputTable OBJECT-TYPE
	SYNTAX  SEQUENCE OF PmcryptoMonupRmonNonunicastCounterClientInputEntry
	MAX-ACCESS not-accessible
	STATUS current
	DESCRIPTION
        "
        List of pmcryptoMonupRmonNonunicastCounterClientInput 
        Article
        "
	::= { pmcryptoMonClientRmonCounter 336 }


pmcryptoMonupRmonNonunicastCounterClientInputEntry OBJECT-TYPE
	SYNTAX PmcryptoMonupRmonNonunicastCounterClientInputEntry
	MAX-ACCESS not-accessible
	STATUS current
	DESCRIPTION
        "
        Row definition for the pmcryptoMonupRmonNonunicastCounterClientInput 
        table
        "
	INDEX   { pmcryptoMonupRmonNonunicastCounterClientInputIndex }
	::= { pmcryptoMonupRmonNonunicastCounterClientInputTable 1 }


PmcryptoMonupRmonNonunicastCounterClientInputEntry ::=
	SEQUENCE {
	pmcryptoMonupRmonNonunicastCounterClientInputIndex
		INTEGER,
	pmcryptoMonupRmonNonunicastCounterClientInputValuePortn
		Counter64,
	pmcryptoMonupRmonNonunicastCounterClientInputErrorPortn
		EkiOnOff,
	pmcryptoMonupRmonNonunicastCounterClientInputOverloadPortn
		EkiOnOff
	}


pmcryptoMonupRmonNonunicastCounterClientInputIndex OBJECT-TYPE
	SYNTAX  INTEGER(0..128)
	MAX-ACCESS  read-only
	STATUS current
	DESCRIPTION
        "
        Index definition for the pmcryptoMonupRmonNonunicastCounterClientInput 
        table
        "
	::= { pmcryptoMonupRmonNonunicastCounterClientInputEntry 1 }


pmcryptoMonupRmonNonunicastCounterClientInputValuePortn OBJECT-TYPE
	SYNTAX  Counter64
	MAX-ACCESS read-only
	STATUS current
	DESCRIPTION
        "
        Client Input Non Unicast Packets 
        :This counter is increased each 
        time a Non-Unicast packet is received 
        on the client port  <Help>  This 
        counter gives the number of Non-Unicast 
        packets received on the client
         port
        "
	::= { pmcryptoMonupRmonNonunicastCounterClientInputEntry 2 }


pmcryptoMonupRmonNonunicastCounterClientInputErrorPortn OBJECT-TYPE
	SYNTAX  EkiOnOff
	MAX-ACCESS read-only
	STATUS current
	DESCRIPTION
        "
        Non Unicast Counter Error :This 
        OID when set indicates the Non-Unicast 
        counter value is invalid on client 
        port
        "
	::= { pmcryptoMonupRmonNonunicastCounterClientInputEntry 3 }


pmcryptoMonupRmonNonunicastCounterClientInputOverloadPortn OBJECT-TYPE
	SYNTAX  EkiOnOff
	MAX-ACCESS read-only
	STATUS current
	DESCRIPTION
        "
        Non Unicast Counter Overload :This 
        OID when set indicates a Non-Unicast 
        counter overload on client port
        "
	::= { pmcryptoMonupRmonNonunicastCounterClientInputEntry 4 }


--- *********************************************************
---     TABLE for the pmcryptoMondownRmonBytesCounterClientOutput articles
--- *********************************************************

pmcryptoMondownRmonBytesCounterClientOutputTable OBJECT-TYPE
	SYNTAX  SEQUENCE OF PmcryptoMondownRmonBytesCounterClientOutputEntry
	MAX-ACCESS not-accessible
	STATUS current
	DESCRIPTION
        "
        List of pmcryptoMondownRmonBytesCounterClientOutput 
        Article
        "
	::= { pmcryptoMonClientRmonCounter 400 }


pmcryptoMondownRmonBytesCounterClientOutputEntry OBJECT-TYPE
	SYNTAX PmcryptoMondownRmonBytesCounterClientOutputEntry
	MAX-ACCESS not-accessible
	STATUS current
	DESCRIPTION
        "
        Row definition for the pmcryptoMondownRmonBytesCounterClientOutput 
        table
        "
	INDEX   { pmcryptoMondownRmonBytesCounterClientOutputIndex }
	::= { pmcryptoMondownRmonBytesCounterClientOutputTable 1 }


PmcryptoMondownRmonBytesCounterClientOutputEntry ::=
	SEQUENCE {
	pmcryptoMondownRmonBytesCounterClientOutputIndex
		INTEGER,
	pmcryptoMondownRmonBytesCounterClientOutputValuePortn
		Counter64,
	pmcryptoMondownRmonBytesCounterClientOutputErrorPortn
		EkiOnOff,
	pmcryptoMondownRmonBytesCounterClientOutputOverloadPortn
		EkiOnOff
	}


pmcryptoMondownRmonBytesCounterClientOutputIndex OBJECT-TYPE
	SYNTAX  INTEGER(0..128)
	MAX-ACCESS  read-only
	STATUS current
	DESCRIPTION
        "
        Index definition for the pmcryptoMondownRmonBytesCounterClientOutput 
        table
        "
	::= { pmcryptoMondownRmonBytesCounterClientOutputEntry 1 }


pmcryptoMondownRmonBytesCounterClientOutputValuePortn OBJECT-TYPE
	SYNTAX  Counter64
	MAX-ACCESS read-only
	STATUS current
	DESCRIPTION
        "
        Client Output Bytes :This counter 
        is increased each time a data byte 
        is transmitted on the client port 
        <Help> This counter gives the number 
        of bytes transmitted on the client 
        port
        "
	::= { pmcryptoMondownRmonBytesCounterClientOutputEntry 2 }


pmcryptoMondownRmonBytesCounterClientOutputErrorPortn OBJECT-TYPE
	SYNTAX  EkiOnOff
	MAX-ACCESS read-only
	STATUS current
	DESCRIPTION
        "
        Bytes Counter Error :This OID
         when set indicates the Bytes counter 
        value is invalid on client port
        "
	::= { pmcryptoMondownRmonBytesCounterClientOutputEntry 3 }


pmcryptoMondownRmonBytesCounterClientOutputOverloadPortn OBJECT-TYPE
	SYNTAX  EkiOnOff
	MAX-ACCESS read-only
	STATUS current
	DESCRIPTION
        "
        Bytes Counter Overload :This OID 
        when set indicates a Bytes counter 
        overload on client port

        "
	::= { pmcryptoMondownRmonBytesCounterClientOutputEntry 4 }


--- *********************************************************
---     TABLE for the pmcryptoMondownRmonCrcErrorsCounterClientOutput articles
--- *********************************************************

pmcryptoMondownRmonCrcErrorsCounterClientOutputTable OBJECT-TYPE
	SYNTAX  SEQUENCE OF PmcryptoMondownRmonCrcErrorsCounterClientOutputEntry
	MAX-ACCESS not-accessible
	STATUS current
	DESCRIPTION
        "
        List of pmcryptoMondownRmonCrcErrorsCounterClientOutput 
        Article
        "
	::= { pmcryptoMonClientRmonCounter 432 }


pmcryptoMondownRmonCrcErrorsCounterClientOutputEntry OBJECT-TYPE
	SYNTAX PmcryptoMondownRmonCrcErrorsCounterClientOutputEntry
	MAX-ACCESS not-accessible
	STATUS current
	DESCRIPTION
        "
        Row definition for the pmcryptoMondownRmonCrcErrorsCounterClientOutput 
        table
        "
	INDEX   { pmcryptoMondownRmonCrcErrorsCounterClientOutputIndex }
	::= { pmcryptoMondownRmonCrcErrorsCounterClientOutputTable 1 }


PmcryptoMondownRmonCrcErrorsCounterClientOutputEntry ::=
	SEQUENCE {
	pmcryptoMondownRmonCrcErrorsCounterClientOutputIndex
		INTEGER,
	pmcryptoMondownRmonCrcErrorsCounterClientOutputValuePortn
		Counter64,
	pmcryptoMondownRmonCrcErrorsCounterClientOutputErrorPortn
		EkiOnOff,
	pmcryptoMondownRmonCrcErrorsCounterClientOutputOverloadPortn
		EkiOnOff
	}


pmcryptoMondownRmonCrcErrorsCounterClientOutputIndex OBJECT-TYPE
	SYNTAX  INTEGER(0..128)
	MAX-ACCESS  read-only
	STATUS current
	DESCRIPTION
        "
        Index definition for the pmcryptoMondownRmonCrcErrorsCounterClientOutput 
        table
        "
	::= { pmcryptoMondownRmonCrcErrorsCounterClientOutputEntry 1 }


pmcryptoMondownRmonCrcErrorsCounterClientOutputValuePortn OBJECT-TYPE
	SYNTAX  Counter64
	MAX-ACCESS read-only
	STATUS current
	DESCRIPTION
        "
        Client Output CRC Errors :This 
        counter is increased each time
         a CRC error is detected on the 
        transmit client port  <Help>  This 
        counter gives the number of CRC 
        Errors transmitted on the client 
        port
        "
	::= { pmcryptoMondownRmonCrcErrorsCounterClientOutputEntry 2 }


pmcryptoMondownRmonCrcErrorsCounterClientOutputErrorPortn OBJECT-TYPE
	SYNTAX  EkiOnOff
	MAX-ACCESS read-only
	STATUS current
	DESCRIPTION
        "
        CRC Errors Counter Error :This 
        OID when set indicates the CRC
         Errors counter value is invalid 
        on client port
        "
	::= { pmcryptoMondownRmonCrcErrorsCounterClientOutputEntry 3 }


pmcryptoMondownRmonCrcErrorsCounterClientOutputOverloadPortn OBJECT-TYPE
	SYNTAX  EkiOnOff
	MAX-ACCESS read-only
	STATUS current
	DESCRIPTION
        "
        CRC Errors Counter Overload :This 
        OID when set indicates a CRC Errors 
        counter overload on client port
        "
	::= { pmcryptoMondownRmonCrcErrorsCounterClientOutputEntry 4 }


--- *********************************************************
---     TABLE for the pmcryptoMondownRmonPacketsCounterClientOutput articles
--- *********************************************************

pmcryptoMondownRmonPacketsCounterClientOutputTable OBJECT-TYPE
	SYNTAX  SEQUENCE OF PmcryptoMondownRmonPacketsCounterClientOutputEntry
	MAX-ACCESS not-accessible
	STATUS current
	DESCRIPTION
        "
        List of pmcryptoMondownRmonPacketsCounterClientOutput 
        Article
        "
	::= { pmcryptoMonClientRmonCounter 464 }


pmcryptoMondownRmonPacketsCounterClientOutputEntry OBJECT-TYPE
	SYNTAX PmcryptoMondownRmonPacketsCounterClientOutputEntry
	MAX-ACCESS not-accessible
	STATUS current
	DESCRIPTION
        "
        Row definition for the pmcryptoMondownRmonPacketsCounterClientOutput 
        table
        "
	INDEX   { pmcryptoMondownRmonPacketsCounterClientOutputIndex }
	::= { pmcryptoMondownRmonPacketsCounterClientOutputTable 1 }


PmcryptoMondownRmonPacketsCounterClientOutputEntry ::=
	SEQUENCE {
	pmcryptoMondownRmonPacketsCounterClientOutputIndex
		INTEGER,
	pmcryptoMondownRmonPacketsCounterClientOutputValuePortn
		Counter64,
	pmcryptoMondownRmonPacketsCounterClientOutputErrorPortn
		EkiOnOff,
	pmcryptoMondownRmonPacketsCounterClientOutputOverloadPortn
		EkiOnOff
	}


pmcryptoMondownRmonPacketsCounterClientOutputIndex OBJECT-TYPE
	SYNTAX  INTEGER(0..128)
	MAX-ACCESS  read-only
	STATUS current
	DESCRIPTION
        "
        Index definition for the pmcryptoMondownRmonPacketsCounterClientOutput 
        table
        "
	::= { pmcryptoMondownRmonPacketsCounterClientOutputEntry 1 }


pmcryptoMondownRmonPacketsCounterClientOutputValuePortn OBJECT-TYPE
	SYNTAX  Counter64
	MAX-ACCESS read-only
	STATUS current
	DESCRIPTION
        "
        Client Output Packets :This counter 
        is increased each time a packet 
        is transmitted on the client port 
         <Help>  This counter gives the 
        number of packets transmitted on 
        the client port
        "
	::= { pmcryptoMondownRmonPacketsCounterClientOutputEntry 2 }


pmcryptoMondownRmonPacketsCounterClientOutputErrorPortn OBJECT-TYPE
	SYNTAX  EkiOnOff
	MAX-ACCESS read-only
	STATUS current
	DESCRIPTION
        "
        Packets Counter Error :This OID 
        when set indicates the Packets
         counter value is invalid on client 
        port
        "
	::= { pmcryptoMondownRmonPacketsCounterClientOutputEntry 3 }


pmcryptoMondownRmonPacketsCounterClientOutputOverloadPortn OBJECT-TYPE
	SYNTAX  EkiOnOff
	MAX-ACCESS read-only
	STATUS current
	DESCRIPTION
        "
        Packets Counter Overload :This 
        OID when set indicates a Packets 
        counter overload on client port
        "
	::= { pmcryptoMondownRmonPacketsCounterClientOutputEntry 4 }


--- *********************************************************
---     TABLE for the pmcryptoMondownRmonBroadcastCounterClientOutput articles
--- *********************************************************

pmcryptoMondownRmonBroadcastCounterClientOutputTable OBJECT-TYPE
	SYNTAX  SEQUENCE OF PmcryptoMondownRmonBroadcastCounterClientOutputEntry
	MAX-ACCESS not-accessible
	STATUS current
	DESCRIPTION
        "
        List of pmcryptoMondownRmonBroadcastCounterClientOutput 
        Article
        "
	::= { pmcryptoMonClientRmonCounter 496 }


pmcryptoMondownRmonBroadcastCounterClientOutputEntry OBJECT-TYPE
	SYNTAX PmcryptoMondownRmonBroadcastCounterClientOutputEntry
	MAX-ACCESS not-accessible
	STATUS current
	DESCRIPTION
        "
        Row definition for the pmcryptoMondownRmonBroadcastCounterClientOutput 
        table
        "
	INDEX   { pmcryptoMondownRmonBroadcastCounterClientOutputIndex }
	::= { pmcryptoMondownRmonBroadcastCounterClientOutputTable 1 }


PmcryptoMondownRmonBroadcastCounterClientOutputEntry ::=
	SEQUENCE {
	pmcryptoMondownRmonBroadcastCounterClientOutputIndex
		INTEGER,
	pmcryptoMondownRmonBroadcastCounterClientOutputValuePortn
		Counter64,
	pmcryptoMondownRmonBroadcastCounterClientOutputErrorPortn
		EkiOnOff,
	pmcryptoMondownRmonBroadcastCounterClientOutputOverloadPortn
		EkiOnOff
	}


pmcryptoMondownRmonBroadcastCounterClientOutputIndex OBJECT-TYPE
	SYNTAX  INTEGER(0..128)
	MAX-ACCESS  read-only
	STATUS current
	DESCRIPTION
        "
        Index definition for the pmcryptoMondownRmonBroadcastCounterClientOutput 
        table
        "
	::= { pmcryptoMondownRmonBroadcastCounterClientOutputEntry 1 }


pmcryptoMondownRmonBroadcastCounterClientOutputValuePortn OBJECT-TYPE
	SYNTAX  Counter64
	MAX-ACCESS read-only
	STATUS current
	DESCRIPTION
        "
        Client Output Broadcast Packets 
        :This counter is increased each 
        time a broadcast packet is transmitted 
        on the client port  <Help>  This 
        counter gives the number of Broadcast 
        packets transmitted on the client 
        port
        "
	::= { pmcryptoMondownRmonBroadcastCounterClientOutputEntry 2 }


pmcryptoMondownRmonBroadcastCounterClientOutputErrorPortn OBJECT-TYPE
	SYNTAX  EkiOnOff
	MAX-ACCESS read-only
	STATUS current
	DESCRIPTION
        "
        Broadcast Counter Error :This
         OID when set indicates the Broadcast 
        counter value is invalid on client 
        port
        "
	::= { pmcryptoMondownRmonBroadcastCounterClientOutputEntry 3 }


pmcryptoMondownRmonBroadcastCounterClientOutputOverloadPortn OBJECT-TYPE
	SYNTAX  EkiOnOff
	MAX-ACCESS read-only
	STATUS current
	DESCRIPTION
        "
        Broadcast Counter Overload :This 
        OID when set indicates a Broadcast 
        counter overload on client port
        "
	::= { pmcryptoMondownRmonBroadcastCounterClientOutputEntry 4 }


--- *********************************************************
---     TABLE for the pmcryptoMondownRmonMulticastCounterClientOutput articles
--- *********************************************************

pmcryptoMondownRmonMulticastCounterClientOutputTable OBJECT-TYPE
	SYNTAX  SEQUENCE OF PmcryptoMondownRmonMulticastCounterClientOutputEntry
	MAX-ACCESS not-accessible
	STATUS current
	DESCRIPTION
        "
        List of pmcryptoMondownRmonMulticastCounterClientOutput 
        Article
        "
	::= { pmcryptoMonClientRmonCounter 528 }


pmcryptoMondownRmonMulticastCounterClientOutputEntry OBJECT-TYPE
	SYNTAX PmcryptoMondownRmonMulticastCounterClientOutputEntry
	MAX-ACCESS not-accessible
	STATUS current
	DESCRIPTION
        "
        Row definition for the pmcryptoMondownRmonMulticastCounterClientOutput 
        table
        "
	INDEX   { pmcryptoMondownRmonMulticastCounterClientOutputIndex }
	::= { pmcryptoMondownRmonMulticastCounterClientOutputTable 1 }


PmcryptoMondownRmonMulticastCounterClientOutputEntry ::=
	SEQUENCE {
	pmcryptoMondownRmonMulticastCounterClientOutputIndex
		INTEGER,
	pmcryptoMondownRmonMulticastCounterClientOutputValuePortn
		Counter64,
	pmcryptoMondownRmonMulticastCounterClientOutputErrorPortn
		EkiOnOff,
	pmcryptoMondownRmonMulticastCounterClientOutputOverloadPortn
		EkiOnOff
	}


pmcryptoMondownRmonMulticastCounterClientOutputIndex OBJECT-TYPE
	SYNTAX  INTEGER(0..128)
	MAX-ACCESS  read-only
	STATUS current
	DESCRIPTION
        "
        Index definition for the pmcryptoMondownRmonMulticastCounterClientOutput 
        table
        "
	::= { pmcryptoMondownRmonMulticastCounterClientOutputEntry 1 }


pmcryptoMondownRmonMulticastCounterClientOutputValuePortn OBJECT-TYPE
	SYNTAX  Counter64
	MAX-ACCESS read-only
	STATUS current
	DESCRIPTION
        "
        Client Output Multicast Packets 
        :This counter is increased each 
        time a Multicast packet is transmitted 
        on the client port  <Help>  This 
        counter gives the number of Multicast 
        packets transmitted on the client 
        port
        "
	::= { pmcryptoMondownRmonMulticastCounterClientOutputEntry 2 }


pmcryptoMondownRmonMulticastCounterClientOutputErrorPortn OBJECT-TYPE
	SYNTAX  EkiOnOff
	MAX-ACCESS read-only
	STATUS current
	DESCRIPTION
        "
        Multicast Counter Error :This
         OID when set indicates the Multicast 
        counter value is invalid on client 
        port
        "
	::= { pmcryptoMondownRmonMulticastCounterClientOutputEntry 3 }


pmcryptoMondownRmonMulticastCounterClientOutputOverloadPortn OBJECT-TYPE
	SYNTAX  EkiOnOff
	MAX-ACCESS read-only
	STATUS current
	DESCRIPTION
        "
        Multicast Counter Overload :This 
        OID when set indicates a Multicast 
        counter overload on client port
        "
	::= { pmcryptoMondownRmonMulticastCounterClientOutputEntry 4 }


--- *********************************************************
---     TABLE for the pmcryptoMondownRmonPauseFrameCounterClientOutput articles
--- *********************************************************

pmcryptoMondownRmonPauseFrameCounterClientOutputTable OBJECT-TYPE
	SYNTAX  SEQUENCE OF PmcryptoMondownRmonPauseFrameCounterClientOutputEntry
	MAX-ACCESS not-accessible
	STATUS current
	DESCRIPTION
        "
        List of pmcryptoMondownRmonPauseFrameCounterClientOutput 
        Article
        "
	::= { pmcryptoMonClientRmonCounter 560 }


pmcryptoMondownRmonPauseFrameCounterClientOutputEntry OBJECT-TYPE
	SYNTAX PmcryptoMondownRmonPauseFrameCounterClientOutputEntry
	MAX-ACCESS not-accessible
	STATUS current
	DESCRIPTION
        "
        Row definition for the pmcryptoMondownRmonPauseFrameCounterClientOutput 
        table
        "
	INDEX   { pmcryptoMondownRmonPauseFrameCounterClientOutputIndex }
	::= { pmcryptoMondownRmonPauseFrameCounterClientOutputTable 1 }


PmcryptoMondownRmonPauseFrameCounterClientOutputEntry ::=
	SEQUENCE {
	pmcryptoMondownRmonPauseFrameCounterClientOutputIndex
		INTEGER,
	pmcryptoMondownRmonPauseFrameCounterClientOutputValuePortn
		Counter64,
	pmcryptoMondownRmonPauseFrameCounterClientOutputErrorPortn
		EkiOnOff,
	pmcryptoMondownRmonPauseFrameCounterClientOutputOverloadPortn
		EkiOnOff
	}


pmcryptoMondownRmonPauseFrameCounterClientOutputIndex OBJECT-TYPE
	SYNTAX  INTEGER(0..128)
	MAX-ACCESS  read-only
	STATUS current
	DESCRIPTION
        "
        Index definition for the pmcryptoMondownRmonPauseFrameCounterClientOutput 
        table
        "
	::= { pmcryptoMondownRmonPauseFrameCounterClientOutputEntry 1 }


pmcryptoMondownRmonPauseFrameCounterClientOutputValuePortn OBJECT-TYPE
	SYNTAX  Counter64
	MAX-ACCESS read-only
	STATUS current
	DESCRIPTION
        "
        Client Output Pause Frames :This 
        counter is increased each time
         a Pause frame is transmitted on 
        the client port  <Help>  This counter 
        gives the number of Pause frames 
        transmitted on the client port
        "
	::= { pmcryptoMondownRmonPauseFrameCounterClientOutputEntry 2 }


pmcryptoMondownRmonPauseFrameCounterClientOutputErrorPortn OBJECT-TYPE
	SYNTAX  EkiOnOff
	MAX-ACCESS read-only
	STATUS current
	DESCRIPTION
        "
        Pause Counter Error :This OID
         when set indicates the Pause counter 
        value is invalid on client port
        "
	::= { pmcryptoMondownRmonPauseFrameCounterClientOutputEntry 3 }


pmcryptoMondownRmonPauseFrameCounterClientOutputOverloadPortn OBJECT-TYPE
	SYNTAX  EkiOnOff
	MAX-ACCESS read-only
	STATUS current
	DESCRIPTION
        "
        Pause Counter Overload :This OID 
        when set indicates a Pause counter 
        overload on client port
        "
	::= { pmcryptoMondownRmonPauseFrameCounterClientOutputEntry 4 }


--- *********************************************************
---     TABLE for the pmcryptoMondownRmonUnicastCounterClientOutput articles
--- *********************************************************

pmcryptoMondownRmonUnicastCounterClientOutputTable OBJECT-TYPE
	SYNTAX  SEQUENCE OF PmcryptoMondownRmonUnicastCounterClientOutputEntry
	MAX-ACCESS not-accessible
	STATUS current
	DESCRIPTION
        "
        List of pmcryptoMondownRmonUnicastCounterClientOutput 
        Article
        "
	::= { pmcryptoMonClientRmonCounter 688 }


pmcryptoMondownRmonUnicastCounterClientOutputEntry OBJECT-TYPE
	SYNTAX PmcryptoMondownRmonUnicastCounterClientOutputEntry
	MAX-ACCESS not-accessible
	STATUS current
	DESCRIPTION
        "
        Row definition for the pmcryptoMondownRmonUnicastCounterClientOutput 
        table
        "
	INDEX   { pmcryptoMondownRmonUnicastCounterClientOutputIndex }
	::= { pmcryptoMondownRmonUnicastCounterClientOutputTable 1 }


PmcryptoMondownRmonUnicastCounterClientOutputEntry ::=
	SEQUENCE {
	pmcryptoMondownRmonUnicastCounterClientOutputIndex
		INTEGER,
	pmcryptoMondownRmonUnicastCounterClientOutputValuePortn
		Counter64,
	pmcryptoMondownRmonUnicastCounterClientOutputErrorPortn
		EkiOnOff,
	pmcryptoMondownRmonUnicastCounterClientOutputOverloadPortn
		EkiOnOff
	}


pmcryptoMondownRmonUnicastCounterClientOutputIndex OBJECT-TYPE
	SYNTAX  INTEGER(0..128)
	MAX-ACCESS  read-only
	STATUS current
	DESCRIPTION
        "
        Index definition for the pmcryptoMondownRmonUnicastCounterClientOutput 
        table
        "
	::= { pmcryptoMondownRmonUnicastCounterClientOutputEntry 1 }


pmcryptoMondownRmonUnicastCounterClientOutputValuePortn OBJECT-TYPE
	SYNTAX  Counter64
	MAX-ACCESS read-only
	STATUS current
	DESCRIPTION
        "
        Client Output Unicast Packets
         :This counter is increased each 
        time a Unicast packet is transmitted 
        on the client port  <Help>  This 
        counter gives the number of Unicast 
        packets transmitted on the client 
        port
        "
	::= { pmcryptoMondownRmonUnicastCounterClientOutputEntry 2 }


pmcryptoMondownRmonUnicastCounterClientOutputErrorPortn OBJECT-TYPE
	SYNTAX  EkiOnOff
	MAX-ACCESS read-only
	STATUS current
	DESCRIPTION
        "
        Unicast Counter Error :This OID 
        when set indicates the Unicast
         counter value is invalid on client 
        port
        "
	::= { pmcryptoMondownRmonUnicastCounterClientOutputEntry 3 }


pmcryptoMondownRmonUnicastCounterClientOutputOverloadPortn OBJECT-TYPE
	SYNTAX  EkiOnOff
	MAX-ACCESS read-only
	STATUS current
	DESCRIPTION
        "
        Unicast Counter Overload :This 
        OID when set indicates a Unicast 
        counter overload on client port
        "
	::= { pmcryptoMondownRmonUnicastCounterClientOutputEntry 4 }


--- *********************************************************
---     TABLE for the pmcryptoMondownRmonNonunicastCounterClientOutput articles
--- *********************************************************

pmcryptoMondownRmonNonunicastCounterClientOutputTable OBJECT-TYPE
	SYNTAX  SEQUENCE OF PmcryptoMondownRmonNonunicastCounterClientOutputEntry
	MAX-ACCESS not-accessible
	STATUS current
	DESCRIPTION
        "
        List of pmcryptoMondownRmonNonunicastCounterClientOutput 
        Article
        "
	::= { pmcryptoMonClientRmonCounter 720 }


pmcryptoMondownRmonNonunicastCounterClientOutputEntry OBJECT-TYPE
	SYNTAX PmcryptoMondownRmonNonunicastCounterClientOutputEntry
	MAX-ACCESS not-accessible
	STATUS current
	DESCRIPTION
        "
        Row definition for the pmcryptoMondownRmonNonunicastCounterClientOutput 
        table
        "
	INDEX   { pmcryptoMondownRmonNonunicastCounterClientOutputIndex }
	::= { pmcryptoMondownRmonNonunicastCounterClientOutputTable 1 }


PmcryptoMondownRmonNonunicastCounterClientOutputEntry ::=
	SEQUENCE {
	pmcryptoMondownRmonNonunicastCounterClientOutputIndex
		INTEGER,
	pmcryptoMondownRmonNonunicastCounterClientOutputValuePortn
		Counter64,
	pmcryptoMondownRmonNonunicastCounterClientOutputErrorPortn
		EkiOnOff,
	pmcryptoMondownRmonNonunicastCounterClientOutputOverloadPortn
		EkiOnOff
	}


pmcryptoMondownRmonNonunicastCounterClientOutputIndex OBJECT-TYPE
	SYNTAX  INTEGER(0..128)
	MAX-ACCESS  read-only
	STATUS current
	DESCRIPTION
        "
        Index definition for the pmcryptoMondownRmonNonunicastCounterClientOutput 
        table
        "
	::= { pmcryptoMondownRmonNonunicastCounterClientOutputEntry 1 }


pmcryptoMondownRmonNonunicastCounterClientOutputValuePortn OBJECT-TYPE
	SYNTAX  Counter64
	MAX-ACCESS read-only
	STATUS current
	DESCRIPTION
        "
        Client Output Non Unicast Packets 
        :This counter is increased each 
        time a Non-Unicast packet is transmitted 
        on the client port  <Help>  This 
        counter gives the number of Non-Unicast 
        packets transmitted on the client 
        port
        "
	::= { pmcryptoMondownRmonNonunicastCounterClientOutputEntry 2 }


pmcryptoMondownRmonNonunicastCounterClientOutputErrorPortn OBJECT-TYPE
	SYNTAX  EkiOnOff
	MAX-ACCESS read-only
	STATUS current
	DESCRIPTION
        "
        Non Unicast Counter Error :This 
        OID when set indicates the Non-Unicast 
        counter value is invalid on client 
        port
        "
	::= { pmcryptoMondownRmonNonunicastCounterClientOutputEntry 3 }


pmcryptoMondownRmonNonunicastCounterClientOutputOverloadPortn OBJECT-TYPE
	SYNTAX  EkiOnOff
	MAX-ACCESS read-only
	STATUS current
	DESCRIPTION
        "
        Non Unicast Counter Overload :This 
        OID when set indicates a Non-Unicast 
        counter overload on client port
        "
	::= { pmcryptoMondownRmonNonunicastCounterClientOutputEntry 4 }







--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pmcryptoMesrsynth0 OBJECT-TYPE
	  SYNTAX EkiMeasureType
	  MAX-ACCESS read-only
	  STATUS deprecated
	  DESCRIPTION
        "
        Not Used :
        "
	  ::= { pmcryptoMesrOther 0 }



pmcryptoMesrsynth1 OBJECT-TYPE
	  SYNTAX EkiMeasureType
	  MAX-ACCESS read-only
	  STATUS deprecated
	  DESCRIPTION
        "
        Not Used :
        "
	  ::= { pmcryptoMesrOther 1 }



--- *****************************************************
---     LEAF for the pmIntervalNumber article
--- *****************************************************

pmcryptoMesrpmIntervalNumber OBJECT-TYPE
	  SYNTAX Unsigned32 (0..65535)
	  MAX-ACCESS read-only
	  STATUS current
	  DESCRIPTION
        "
        PM Interval Counter :
        "
	  ::= { pmcryptoMesrOther 7 }



--- *********************************************************
---     TABLE for the pmcryptoMesrclientTxTemp articles
--- *********************************************************

pmcryptoMesrclientTxTempTable OBJECT-TYPE
	SYNTAX  SEQUENCE OF PmcryptoMesrclientTxTempEntry
	MAX-ACCESS not-accessible
	STATUS current
	DESCRIPTION
        "
        List of pmcryptoMesrclientTxTemp 
        Article
        "
	::= { pmcryptoMesrClient 16 }


pmcryptoMesrclientTxTempEntry OBJECT-TYPE
	SYNTAX PmcryptoMesrclientTxTempEntry
	MAX-ACCESS not-accessible
	STATUS current
	DESCRIPTION
        "
        Row definition for the pmcryptoMesrclientTxTemp 
        table
        "
	INDEX   { pmcryptoMesrclientTxTempIndex }
	::= { pmcryptoMesrclientTxTempTable 1 }


PmcryptoMesrclientTxTempEntry ::=
	SEQUENCE {
	pmcryptoMesrclientTxTempIndex
		INTEGER,
	pmcryptoMesrclientTxTempPortn
		INTEGER 
	}


pmcryptoMesrclientTxTempIndex OBJECT-TYPE
	SYNTAX  INTEGER(0..128)
	MAX-ACCESS  read-only
	STATUS current
	DESCRIPTION
        "
        Index definition for the pmcryptoMesrclientTxTemp 
        table
        "
	::= { pmcryptoMesrclientTxTempEntry 1 }


pmcryptoMesrclientTxTempPortn OBJECT-TYPE
	SYNTAX  INTEGER (0..65535)
	MAX-ACCESS read-only
	STATUS current
	DESCRIPTION
        "
        Client Trscv Temperature :This 
        OID gives the Laser temperature 
        value of the Client Transceiver, 
        read from the DDM (Digital Diagnostic 
        Monitoring) (Temperature = AV_S16/256) 
        (Unit = C) <Help> This Measure
         gives the Laser temperature value 
        of the Client Transceiver
        "
	::= { pmcryptoMesrclientTxTempEntry 2 }


--- *********************************************************
---     TABLE for the pmcryptoMesrclientTxBias articles
--- *********************************************************

pmcryptoMesrclientTxBiasTable OBJECT-TYPE
	SYNTAX  SEQUENCE OF PmcryptoMesrclientTxBiasEntry
	MAX-ACCESS not-accessible
	STATUS current
	DESCRIPTION
        "
        List of pmcryptoMesrclientTxBias 
        Article
        "
	::= { pmcryptoMesrClient 48 }


pmcryptoMesrclientTxBiasEntry OBJECT-TYPE
	SYNTAX PmcryptoMesrclientTxBiasEntry
	MAX-ACCESS not-accessible
	STATUS current
	DESCRIPTION
        "
        Row definition for the pmcryptoMesrclientTxBias 
        table
        "
	INDEX   { pmcryptoMesrclientTxBiasIndex }
	::= { pmcryptoMesrclientTxBiasTable 1 }


PmcryptoMesrclientTxBiasEntry ::=
	SEQUENCE {
	pmcryptoMesrclientTxBiasIndex
		INTEGER,
	pmcryptoMesrclientTxBiasPortn
		INTEGER 
	}


pmcryptoMesrclientTxBiasIndex OBJECT-TYPE
	SYNTAX  INTEGER(0..128)
	MAX-ACCESS  read-only
	STATUS current
	DESCRIPTION
        "
        Index definition for the pmcryptoMesrclientTxBias 
        table
        "
	::= { pmcryptoMesrclientTxBiasEntry 1 }


pmcryptoMesrclientTxBiasPortn OBJECT-TYPE
	SYNTAX  INTEGER (0..65535)
	MAX-ACCESS read-only
	STATUS current
	DESCRIPTION
        "
        Client Trscv Laser Bias :This
         OID gives the Laser bias value 
        of the Client Transceiver, read 
        from the DDM (Digital Diagnostic 
        Monitoring) (Bias = AV_U16/500) 
        (Unit = mA) <Help> This Measure 
        gives the Laser bias value of the 
        Client Transceiver
        "
	::= { pmcryptoMesrclientTxBiasEntry 2 }


--- *********************************************************
---     TABLE for the pmcryptoMesrclientTxPwr articles
--- *********************************************************

pmcryptoMesrclientTxPwrTable OBJECT-TYPE
	SYNTAX  SEQUENCE OF PmcryptoMesrclientTxPwrEntry
	MAX-ACCESS not-accessible
	STATUS current
	DESCRIPTION
        "
        List of pmcryptoMesrclientTxPwr 
        Article
        "
	::= { pmcryptoMesrClient 80 }


pmcryptoMesrclientTxPwrEntry OBJECT-TYPE
	SYNTAX PmcryptoMesrclientTxPwrEntry
	MAX-ACCESS not-accessible
	STATUS current
	DESCRIPTION
        "
        Row definition for the pmcryptoMesrclientTxPwr 
        table
        "
	INDEX   { pmcryptoMesrclientTxPwrIndex }
	::= { pmcryptoMesrclientTxPwrTable 1 }


PmcryptoMesrclientTxPwrEntry ::=
	SEQUENCE {
	pmcryptoMesrclientTxPwrIndex
		INTEGER,
	pmcryptoMesrclientTxPwrPortn
		INTEGER 
	}


pmcryptoMesrclientTxPwrIndex OBJECT-TYPE
	SYNTAX  INTEGER(0..128)
	MAX-ACCESS  read-only
	STATUS current
	DESCRIPTION
        "
        Index definition for the pmcryptoMesrclientTxPwr 
        table
        "
	::= { pmcryptoMesrclientTxPwrEntry 1 }


pmcryptoMesrclientTxPwrPortn OBJECT-TYPE
	SYNTAX  INTEGER (0..65535)
	MAX-ACCESS read-only
	STATUS current
	DESCRIPTION
        "
        Client Trscv Tx Power :This OID 
        gives the transmit power value
         of the Client Transceiver, read 
        from the DDM (Digital Diagnostic 
        Monitoring) (Power = 10*log(AV_U16)-40) 
        (Unit = dBm) <Help> This Measure 
        gives the transmit power value
         of the Client Transceiver
        "
	::= { pmcryptoMesrclientTxPwrEntry 2 }


--- *********************************************************
---     TABLE for the pmcryptoMesrclientRxPwr articles
--- *********************************************************

pmcryptoMesrclientRxPwrTable OBJECT-TYPE
	SYNTAX  SEQUENCE OF PmcryptoMesrclientRxPwrEntry
	MAX-ACCESS not-accessible
	STATUS current
	DESCRIPTION
        "
        List of pmcryptoMesrclientRxPwr 
        Article
        "
	::= { pmcryptoMesrClient 112 }


pmcryptoMesrclientRxPwrEntry OBJECT-TYPE
	SYNTAX PmcryptoMesrclientRxPwrEntry
	MAX-ACCESS not-accessible
	STATUS current
	DESCRIPTION
        "
        Row definition for the pmcryptoMesrclientRxPwr 
        table
        "
	INDEX   { pmcryptoMesrclientRxPwrIndex }
	::= { pmcryptoMesrclientRxPwrTable 1 }


PmcryptoMesrclientRxPwrEntry ::=
	SEQUENCE {
	pmcryptoMesrclientRxPwrIndex
		INTEGER,
	pmcryptoMesrclientRxPwrPortn
		INTEGER 
	}


pmcryptoMesrclientRxPwrIndex OBJECT-TYPE
	SYNTAX  INTEGER(0..128)
	MAX-ACCESS  read-only
	STATUS current
	DESCRIPTION
        "
        Index definition for the pmcryptoMesrclientRxPwr 
        table
        "
	::= { pmcryptoMesrclientRxPwrEntry 1 }


pmcryptoMesrclientRxPwrPortn OBJECT-TYPE
	SYNTAX  INTEGER (0..65535)
	MAX-ACCESS read-only
	STATUS current
	DESCRIPTION
        "
        Client Trscv Rx Power :This OID 
        gives the receive power value of 
        the Client Transceiver, read in 
        the DDM (Digital Diagnostic Monitoring) 
        (Power = 10*log(AV_U16)-40) (Unit 
        = dBm) <Help> This Measure gives 
        the receive power value of the
         Client Transceiver
        "
	::= { pmcryptoMesrclientRxPwrEntry 2 }


--- *********************************************************
---     TABLE for the pmcryptoMesrlineTxPwrMin articles
--- *********************************************************

pmcryptoMesrlineTxPwrMinTable OBJECT-TYPE
	SYNTAX  SEQUENCE OF PmcryptoMesrlineTxPwrMinEntry
	MAX-ACCESS not-accessible
	STATUS current
	DESCRIPTION
        "
        List of pmcryptoMesrlineTxPwrMin 
        Article
        "
	::= { pmcryptoMesrLine 144 }


pmcryptoMesrlineTxPwrMinEntry OBJECT-TYPE
	SYNTAX PmcryptoMesrlineTxPwrMinEntry
	MAX-ACCESS not-accessible
	STATUS current
	DESCRIPTION
        "
        Row definition for the pmcryptoMesrlineTxPwrMin 
        table
        "
	INDEX   { pmcryptoMesrlineTxPwrMinIndex }
	::= { pmcryptoMesrlineTxPwrMinTable 1 }


PmcryptoMesrlineTxPwrMinEntry ::=
	SEQUENCE {
	pmcryptoMesrlineTxPwrMinIndex
		INTEGER,
	pmcryptoMesrlineTxPwrMinPortn
		INTEGER 
	}


pmcryptoMesrlineTxPwrMinIndex OBJECT-TYPE
	SYNTAX  INTEGER(0..128)
	MAX-ACCESS  read-only
	STATUS current
	DESCRIPTION
        "
        Index definition for the pmcryptoMesrlineTxPwrMin 
        table
        "
	::= { pmcryptoMesrlineTxPwrMinEntry 1 }


pmcryptoMesrlineTxPwrMinPortn OBJECT-TYPE
	SYNTAX  INTEGER (0..65535)
	MAX-ACCESS read-only
	STATUS current
	DESCRIPTION
        "
        Min Line Trscv Tx Power :This
         OID gives the minimum transmit 
        power value among the network lanes 
        of the Line Transceiver, read from 
        the DDM (Digital Diagnostic Monitoring) 
        (Power = 10*log(AV_U16)-40) (Unit 
        = dBm) <Help> This Measure gives 
        the minimum transmit power value 
        among the network lanes of the
         Line Transceiver
        "
	::= { pmcryptoMesrlineTxPwrMinEntry 2 }


--- *********************************************************
---     TABLE for the pmcryptoMesrlineTxCompositePwr articles
--- *********************************************************

pmcryptoMesrlineTxCompositePwrTable OBJECT-TYPE
	SYNTAX  SEQUENCE OF PmcryptoMesrlineTxCompositePwrEntry
	MAX-ACCESS not-accessible
	STATUS current
	DESCRIPTION
        "
        List of pmcryptoMesrlineTxCompositePwr 
        Article
        "
	::= { pmcryptoMesrLine 160 }


pmcryptoMesrlineTxCompositePwrEntry OBJECT-TYPE
	SYNTAX PmcryptoMesrlineTxCompositePwrEntry
	MAX-ACCESS not-accessible
	STATUS current
	DESCRIPTION
        "
        Row definition for the pmcryptoMesrlineTxCompositePwr 
        table
        "
	INDEX   { pmcryptoMesrlineTxCompositePwrIndex }
	::= { pmcryptoMesrlineTxCompositePwrTable 1 }


PmcryptoMesrlineTxCompositePwrEntry ::=
	SEQUENCE {
	pmcryptoMesrlineTxCompositePwrIndex
		INTEGER,
	pmcryptoMesrlineTxCompositePwrPortn
		INTEGER 
	}


pmcryptoMesrlineTxCompositePwrIndex OBJECT-TYPE
	SYNTAX  INTEGER(0..128)
	MAX-ACCESS  read-only
	STATUS current
	DESCRIPTION
        "
        Index definition for the pmcryptoMesrlineTxCompositePwr 
        table
        "
	::= { pmcryptoMesrlineTxCompositePwrEntry 1 }


pmcryptoMesrlineTxCompositePwrPortn OBJECT-TYPE
	SYNTAX  INTEGER (0..65535)
	MAX-ACCESS read-only
	STATUS current
	DESCRIPTION
        "
        Line Composite Tx Power (LR4/SR4) 
        :This OID gives the composite transmit 
        power (sum of the network lanes 
        transmit power) of the Line Transceiver, 
        read from the DDM (Digital Diagnostic 
        Monitoring) (Power = 10*log(AV_U16)-40) 
          (Unit = dBm) <Help> This Measure 
        gives the composite transmit power 
        (sum of the network lanes transmit 
        power) of the Line Transceiver
          (LR4/SR4 only)
        "
	::= { pmcryptoMesrlineTxCompositePwrEntry 2 }


--- *********************************************************
---     TABLE for the pmcryptoMesrlineRxPwrMin articles
--- *********************************************************

pmcryptoMesrlineRxPwrMinTable OBJECT-TYPE
	SYNTAX  SEQUENCE OF PmcryptoMesrlineRxPwrMinEntry
	MAX-ACCESS not-accessible
	STATUS current
	DESCRIPTION
        "
        List of pmcryptoMesrlineRxPwrMin 
        Article
        "
	::= { pmcryptoMesrLine 176 }


pmcryptoMesrlineRxPwrMinEntry OBJECT-TYPE
	SYNTAX PmcryptoMesrlineRxPwrMinEntry
	MAX-ACCESS not-accessible
	STATUS current
	DESCRIPTION
        "
        Row definition for the pmcryptoMesrlineRxPwrMin 
        table
        "
	INDEX   { pmcryptoMesrlineRxPwrMinIndex }
	::= { pmcryptoMesrlineRxPwrMinTable 1 }


PmcryptoMesrlineRxPwrMinEntry ::=
	SEQUENCE {
	pmcryptoMesrlineRxPwrMinIndex
		INTEGER,
	pmcryptoMesrlineRxPwrMinPortn
		INTEGER 
	}


pmcryptoMesrlineRxPwrMinIndex OBJECT-TYPE
	SYNTAX  INTEGER(0..128)
	MAX-ACCESS  read-only
	STATUS current
	DESCRIPTION
        "
        Index definition for the pmcryptoMesrlineRxPwrMin 
        table
        "
	::= { pmcryptoMesrlineRxPwrMinEntry 1 }


pmcryptoMesrlineRxPwrMinPortn OBJECT-TYPE
	SYNTAX  INTEGER (0..65535)
	MAX-ACCESS read-only
	STATUS current
	DESCRIPTION
        "
        Min Line Trscv Rx Power :This
         OID gives the minimum receive
         power value among the network
         lanes of the Line Transceiver, 
        read from the DDM (Digital Diagnostic 
        Monitoring) (Power = 10*log(AV_U16)-40) 
        (Unit = dBm) <Help> This Measure 
        gives the minimum receive power 
        value among the network lanes of 
        the Line Transceiver
        "
	::= { pmcryptoMesrlineRxPwrMinEntry 2 }


--- *********************************************************
---     TABLE for the pmcryptoMesrlineRxCompositePwr articles
--- *********************************************************

pmcryptoMesrlineRxCompositePwrTable OBJECT-TYPE
	SYNTAX  SEQUENCE OF PmcryptoMesrlineRxCompositePwrEntry
	MAX-ACCESS not-accessible
	STATUS current
	DESCRIPTION
        "
        List of pmcryptoMesrlineRxCompositePwr 
        Article
        "
	::= { pmcryptoMesrLine 192 }


pmcryptoMesrlineRxCompositePwrEntry OBJECT-TYPE
	SYNTAX PmcryptoMesrlineRxCompositePwrEntry
	MAX-ACCESS not-accessible
	STATUS current
	DESCRIPTION
        "
        Row definition for the pmcryptoMesrlineRxCompositePwr 
        table
        "
	INDEX   { pmcryptoMesrlineRxCompositePwrIndex }
	::= { pmcryptoMesrlineRxCompositePwrTable 1 }


PmcryptoMesrlineRxCompositePwrEntry ::=
	SEQUENCE {
	pmcryptoMesrlineRxCompositePwrIndex
		INTEGER,
	pmcryptoMesrlineRxCompositePwrPortn
		INTEGER 
	}


pmcryptoMesrlineRxCompositePwrIndex OBJECT-TYPE
	SYNTAX  INTEGER(0..128)
	MAX-ACCESS  read-only
	STATUS current
	DESCRIPTION
        "
        Index definition for the pmcryptoMesrlineRxCompositePwr 
        table
        "
	::= { pmcryptoMesrlineRxCompositePwrEntry 1 }


pmcryptoMesrlineRxCompositePwrPortn OBJECT-TYPE
	SYNTAX  INTEGER (0..65535)
	MAX-ACCESS read-only
	STATUS current
	DESCRIPTION
        "
        Line Composite Rx Power (LR4/SR4) 
        :This OID gives the composite receive 
        power (sum of the network lanes 
        receive power) of the Line Transceiver, 
        read from the DDM (Digital Diagnostic 
        Monitoring) (Power = 10*log(AV_U16)-40) 
         (Unit = dBm) <Help> This Measure 
        gives the composite receive power 
        (sum of the network lanes receive 
        power) of the Line Transceiver
         (LR4/SR4 only)
        "
	::= { pmcryptoMesrlineRxCompositePwrEntry 2 }


--- *********************************************************
---     TABLE for the pmcryptoMesrlineTxPwrMax articles
--- *********************************************************

pmcryptoMesrlineTxPwrMaxTable OBJECT-TYPE
	SYNTAX  SEQUENCE OF PmcryptoMesrlineTxPwrMaxEntry
	MAX-ACCESS not-accessible
	STATUS current
	DESCRIPTION
        "
        List of pmcryptoMesrlineTxPwrMax 
        Article
        "
	::= { pmcryptoMesrLine 208 }


pmcryptoMesrlineTxPwrMaxEntry OBJECT-TYPE
	SYNTAX PmcryptoMesrlineTxPwrMaxEntry
	MAX-ACCESS not-accessible
	STATUS current
	DESCRIPTION
        "
        Row definition for the pmcryptoMesrlineTxPwrMax 
        table
        "
	INDEX   { pmcryptoMesrlineTxPwrMaxIndex }
	::= { pmcryptoMesrlineTxPwrMaxTable 1 }


PmcryptoMesrlineTxPwrMaxEntry ::=
	SEQUENCE {
	pmcryptoMesrlineTxPwrMaxIndex
		INTEGER,
	pmcryptoMesrlineTxPwrMaxPortn
		INTEGER 
	}


pmcryptoMesrlineTxPwrMaxIndex OBJECT-TYPE
	SYNTAX  INTEGER(0..128)
	MAX-ACCESS  read-only
	STATUS current
	DESCRIPTION
        "
        Index definition for the pmcryptoMesrlineTxPwrMax 
        table
        "
	::= { pmcryptoMesrlineTxPwrMaxEntry 1 }


pmcryptoMesrlineTxPwrMaxPortn OBJECT-TYPE
	SYNTAX  INTEGER (0..65535)
	MAX-ACCESS read-only
	STATUS current
	DESCRIPTION
        "
        Max Line Trscv Tx Power :This
         OID gives the maximum transmit 
        power value among the network lanes 
        of the Line Transceiver, read from 
        the DDM (Digital Diagnostic Monitoring) 
        (Power =10*log(AV_U16)-40) (Unit 
        = dBm) <Help> This Measure gives 
        the maximum transmit power value 
        among the network lanes of the
         Line Transceiver
        "
	::= { pmcryptoMesrlineTxPwrMaxEntry 2 }


--- *********************************************************
---     TABLE for the pmcryptoMesrlineRxPwrMax articles
--- *********************************************************

pmcryptoMesrlineRxPwrMaxTable OBJECT-TYPE
	SYNTAX  SEQUENCE OF PmcryptoMesrlineRxPwrMaxEntry
	MAX-ACCESS not-accessible
	STATUS current
	DESCRIPTION
        "
        List of pmcryptoMesrlineRxPwrMax 
        Article
        "
	::= { pmcryptoMesrLine 240 }


pmcryptoMesrlineRxPwrMaxEntry OBJECT-TYPE
	SYNTAX PmcryptoMesrlineRxPwrMaxEntry
	MAX-ACCESS not-accessible
	STATUS current
	DESCRIPTION
        "
        Row definition for the pmcryptoMesrlineRxPwrMax 
        table
        "
	INDEX   { pmcryptoMesrlineRxPwrMaxIndex }
	::= { pmcryptoMesrlineRxPwrMaxTable 1 }


PmcryptoMesrlineRxPwrMaxEntry ::=
	SEQUENCE {
	pmcryptoMesrlineRxPwrMaxIndex
		INTEGER,
	pmcryptoMesrlineRxPwrMaxPortn
		INTEGER 
	}


pmcryptoMesrlineRxPwrMaxIndex OBJECT-TYPE
	SYNTAX  INTEGER(0..128)
	MAX-ACCESS  read-only
	STATUS current
	DESCRIPTION
        "
        Index definition for the pmcryptoMesrlineRxPwrMax 
        table
        "
	::= { pmcryptoMesrlineRxPwrMaxEntry 1 }


pmcryptoMesrlineRxPwrMaxPortn OBJECT-TYPE
	SYNTAX  INTEGER (0..65535)
	MAX-ACCESS read-only
	STATUS current
	DESCRIPTION
        "
        Max Line Trscv Rx Power :This
         OID gives the maximum receive
         power value among the network
         lanes of the Line Transceiver, 
        read in the DDM (Digital Diagnostic 
        Monitoring) (Power = 10*log(AV_U16)-40) 
        (Unit = dBm) <Help> This Measure 
        gives the maximum receive power 
        value among the network lanes of 
        the Line Transceiver
        "
	::= { pmcryptoMesrlineRxPwrMaxEntry 2 }


--- *****************************************************
---     LEAF for the lineTrscvTemp article
--- *****************************************************

pmcryptoMesrlineTrscvTemp OBJECT-TYPE
	  SYNTAX Unsigned32 (0..65535)
	  MAX-ACCESS read-only
	  STATUS current
	  DESCRIPTION
        "
        LineTrscv Temperature :This OID 
        gives the temperature value of
         the Transceiver, read from the 
        DDM (Digital Diagnostic Monitoring) 
        (Temperature = AV_S16/256) (Unit 
        = C) <Help> This Measure gives
         the temperature value of the Transceiver
        "
	  ::= { pmcryptoMesrOther 400 }



--- *****************************************************
---     LEAF for the lineTrscvVoltage article
--- *****************************************************

pmcryptoMesrlineTrscvVoltage OBJECT-TYPE
	  SYNTAX Unsigned32 (0..65535)
	  MAX-ACCESS read-only
	  STATUS current
	  DESCRIPTION
        "
        Line Trscv Voltage :This OID gives 
        the voltage value of the QSFP plugged 
        into the port, read from the DDM 
        (Digital Diagnostic Monitoring) 
        (Voltage = AV_U16/10000) (Unit
         = V)  <Help>  This measure gives 
        the power supply voltage of the 
        transceiver
        "
	  ::= { pmcryptoMesrOther 408 }








--- *****************************************************
--- $$$$$$$$$$$$$$$$$$$$$$$$$$$$$$$$$$$$$$$$$$$$$$$$$$$$$
---     PERFORMANCE
--- $$$$$$$$$$$$$$$$$$$$$$$$$$$$$$$$$$$$$$$$$$$$$$$$$$$$$
--- *****************************************************



--- *****************************************************
---     Leaf of the telecomInputClientCurrent15Stat
--- *****************************************************
--- *********************************************************
---     TABLE for the pmcryptoPerfTelecomInputClientCurrent15Stat articles
--- *********************************************************

pmcryptoPerfTelecomInputClientCurrent15StatTable OBJECT-TYPE
	SYNTAX  SEQUENCE OF PmcryptoPerfTelecomInputClientCurrent15StatEntry
	MAX-ACCESS not-accessible
	STATUS current
	DESCRIPTION
        "
        List of pmcryptoPerfTelecomInputClientCurrent15Stat 
        Article
        "
	::= { pmcryptoMonPerfClient 16 }


pmcryptoPerfTelecomInputClientCurrent15StatEntry OBJECT-TYPE
	SYNTAX PmcryptoPerfTelecomInputClientCurrent15StatEntry
	MAX-ACCESS not-accessible
	STATUS current
	DESCRIPTION
        "
        Row definition for the pmcryptoPerfTelecomInputClientCurrent15Stat 
        table
        "
	INDEX   { pmcryptoPerfTelecomInputClientCurrent15StatIndex }
	::= { pmcryptoPerfTelecomInputClientCurrent15StatTable 1 }


PmcryptoPerfTelecomInputClientCurrent15StatEntry ::=
	SEQUENCE {
	pmcryptoPerfTelecomInputClientCurrent15StatIndex
		INTEGER,
	pmcryptoPerfTelecomInputClientCurrent15StatInvCvPortn
		EkiOnOff,
	pmcryptoPerfTelecomInputClientCurrent15StatCvValuePortn
		Unsigned32,
	pmcryptoPerfTelecomInputClientCurrent15StatInvEsPortn
		EkiOnOff,
	pmcryptoPerfTelecomInputClientCurrent15StatEsValuePortn
		Unsigned32,
	pmcryptoPerfTelecomInputClientCurrent15StatInvSesPortn
		EkiOnOff,
	pmcryptoPerfTelecomInputClientCurrent15StatSesValuePortn
		Unsigned32,
	pmcryptoPerfTelecomInputClientCurrent15StatInvSefsPortn
		EkiOnOff,
	pmcryptoPerfTelecomInputClientCurrent15StatSefsValuePortn
		Unsigned32,
	pmcryptoPerfTelecomInputClientCurrent15StatInvUasPortn
		EkiOnOff,
	pmcryptoPerfTelecomInputClientCurrent15StatUasValuePortn
		Unsigned32
	}


pmcryptoPerfTelecomInputClientCurrent15StatIndex OBJECT-TYPE
	SYNTAX  INTEGER(0..128)
	MAX-ACCESS  read-only
	STATUS current
	DESCRIPTION
        "
        Index definition for the pmcryptoPerfTelecomInputClientCurrent15Stat 
        table
        "
	::= { pmcryptoPerfTelecomInputClientCurrent15StatEntry 1 }


pmcryptoPerfTelecomInputClientCurrent15StatInvCvPortn OBJECT-TYPE
	SYNTAX  EkiOnOff
	MAX-ACCESS read-only
	STATUS current
	DESCRIPTION
        "
        Current 15-min EBC counter inv. 
        :This OID indicates that the current 
        15-min Coding Violation counter 
        is invalid
        "
	::= { pmcryptoPerfTelecomInputClientCurrent15StatEntry 2 }


pmcryptoPerfTelecomInputClientCurrent15StatCvValuePortn OBJECT-TYPE
	SYNTAX  Unsigned32
	MAX-ACCESS read-only
	STATUS current
	DESCRIPTION
        "
        Current 15-min EBC counter :This 
        OID gives the current 15-min Coding 
        Violation counter value
        "
	::= { pmcryptoPerfTelecomInputClientCurrent15StatEntry 3 }


pmcryptoPerfTelecomInputClientCurrent15StatInvEsPortn OBJECT-TYPE
	SYNTAX  EkiOnOff
	MAX-ACCESS read-only
	STATUS current
	DESCRIPTION
        "
        Current 15-min ES counter inv. 
        :This OID indicates that the current 
        15-min Errored Second counter is 
        invalid
        "
	::= { pmcryptoPerfTelecomInputClientCurrent15StatEntry 4 }


pmcryptoPerfTelecomInputClientCurrent15StatEsValuePortn OBJECT-TYPE
	SYNTAX  Unsigned32
	MAX-ACCESS read-only
	STATUS current
	DESCRIPTION
        "
        Current 15-min ES counter :This 
        OID gives the current 15-min Errored 
        Second counter value
        "
	::= { pmcryptoPerfTelecomInputClientCurrent15StatEntry 5 }


pmcryptoPerfTelecomInputClientCurrent15StatInvSesPortn OBJECT-TYPE
	SYNTAX  EkiOnOff
	MAX-ACCESS read-only
	STATUS current
	DESCRIPTION
        "
        Current 15-min SES counter inv. 
        :This OID indicates that the current 
        15-min severely Errored Second
         counter is invalid
        "
	::= { pmcryptoPerfTelecomInputClientCurrent15StatEntry 6 }


pmcryptoPerfTelecomInputClientCurrent15StatSesValuePortn OBJECT-TYPE
	SYNTAX  Unsigned32
	MAX-ACCESS read-only
	STATUS current
	DESCRIPTION
        "
        Current 15-min SES counter :This 
        OID gives the current 15-min severely 
        Errored Second counter value
        "
	::= { pmcryptoPerfTelecomInputClientCurrent15StatEntry 7 }


pmcryptoPerfTelecomInputClientCurrent15StatInvSefsPortn OBJECT-TYPE
	SYNTAX  EkiOnOff
	MAX-ACCESS read-only
	STATUS current
	DESCRIPTION
        "
        Current 15-min SEFS counter inv. 
        :This OID indicates that the current 
        15-min severely Errored Framing 
        Second counter is invalid
        "
	::= { pmcryptoPerfTelecomInputClientCurrent15StatEntry 8 }


pmcryptoPerfTelecomInputClientCurrent15StatSefsValuePortn OBJECT-TYPE
	SYNTAX  Unsigned32
	MAX-ACCESS read-only
	STATUS current
	DESCRIPTION
        "
        Current 15-min SEFS counter :This 
        OID gives the current 15-min severely 
        Errored Framing Second counter
         value
        "
	::= { pmcryptoPerfTelecomInputClientCurrent15StatEntry 9 }


pmcryptoPerfTelecomInputClientCurrent15StatInvUasPortn OBJECT-TYPE
	SYNTAX  EkiOnOff
	MAX-ACCESS read-only
	STATUS current
	DESCRIPTION
        "
        Current 15-min UAS counter inv. 
        :This OID indicates that the current 
        15-min UnAvailable Second counter 
        is invalid
        "
	::= { pmcryptoPerfTelecomInputClientCurrent15StatEntry 10 }


pmcryptoPerfTelecomInputClientCurrent15StatUasValuePortn OBJECT-TYPE
	SYNTAX  Unsigned32
	MAX-ACCESS read-only
	STATUS current
	DESCRIPTION
        "
        Current 15-min UAS counter :This 
        OID gives the current 15-min UnAvailable 
        Second counter value
        "
	::= { pmcryptoPerfTelecomInputClientCurrent15StatEntry 11 }


--- *****************************************************
---     Leaf of the telecomInputClientPast15Stat
--- *****************************************************
--- *********************************************************
---     TABLE for the pmcryptoPerfTelecomInputClientPast15StatHistory articles
--- *********************************************************

pmcryptoPerfTelecomInputClientPast15StatHistoryPort1Table OBJECT-TYPE
	SYNTAX  SEQUENCE OF PmcryptoPerfTelecomInputClientPast15StatHistoryPort1Entry
	MAX-ACCESS not-accessible
	STATUS current
	DESCRIPTION
        "
        List of pmcryptoPerfTelecomInputClientPast15StatHistory 
        Article
        "
	::= { pmcryptoMonPerfClient 48 }


pmcryptoPerfTelecomInputClientPast15StatHistoryPort1Entry OBJECT-TYPE
	SYNTAX PmcryptoPerfTelecomInputClientPast15StatHistoryPort1Entry
	MAX-ACCESS not-accessible
	STATUS current
	DESCRIPTION
        "
        Row definition for the pmcryptoPerfTelecomInputClientPast15StatHistory 
        table
        "
	INDEX   { pmcryptoPerfTelecomInputClientPast15StatHistoryPort1Index }
	::= { pmcryptoPerfTelecomInputClientPast15StatHistoryPort1Table 1 }


PmcryptoPerfTelecomInputClientPast15StatHistoryPort1Entry ::=
	SEQUENCE {
	pmcryptoPerfTelecomInputClientPast15StatHistoryPort1Index
		INTEGER,
	pmcryptoPerfTelecomInputClientPast15StatHistoryInvCvPort1
		EkiOnOff,
	pmcryptoPerfTelecomInputClientPast15StatHistoryCvValuePort1
		Unsigned32,
	pmcryptoPerfTelecomInputClientPast15StatHistoryInvEsPort1
		EkiOnOff,
	pmcryptoPerfTelecomInputClientPast15StatHistoryEsValuePort1
		Unsigned32,
	pmcryptoPerfTelecomInputClientPast15StatHistoryInvSesPort1
		EkiOnOff,
	pmcryptoPerfTelecomInputClientPast15StatHistorySesValuePort1
		Unsigned32,
	pmcryptoPerfTelecomInputClientPast15StatHistoryInvSefsPort1
		EkiOnOff,
	pmcryptoPerfTelecomInputClientPast15StatHistorySefsValuePort1
		Unsigned32,
	pmcryptoPerfTelecomInputClientPast15StatHistoryInvUasPort1
		EkiOnOff,
	pmcryptoPerfTelecomInputClientPast15StatHistoryUasValuePort1
		Unsigned32
	}


pmcryptoPerfTelecomInputClientPast15StatHistoryPort1Index OBJECT-TYPE
	SYNTAX  INTEGER(0..128)
	MAX-ACCESS  read-only
	STATUS current
	DESCRIPTION
        "
        Index definition for the pmcryptoPerfTelecomInputClientPast15StatHistory 
        table
        "
	::= { pmcryptoPerfTelecomInputClientPast15StatHistoryPort1Entry 1 }


pmcryptoPerfTelecomInputClientPast15StatHistoryInvCvPort1 OBJECT-TYPE
	SYNTAX  EkiOnOff
	MAX-ACCESS read-only
	STATUS current
	DESCRIPTION
        "
        Previous 15-min EBC counter inv. 
        :This OID indicates that the previous 
        15-min Coding Violation counter 
        is invalid
        "
	::= { pmcryptoPerfTelecomInputClientPast15StatHistoryPort1Entry 2 }


pmcryptoPerfTelecomInputClientPast15StatHistoryCvValuePort1 OBJECT-TYPE
	SYNTAX  Unsigned32
	MAX-ACCESS read-only
	STATUS current
	DESCRIPTION
        "
        Previous 15-min EBC counter :This 
        OID gives the previous 15-min Coding 
        Violation counter value
        "
	::= { pmcryptoPerfTelecomInputClientPast15StatHistoryPort1Entry 3 }


pmcryptoPerfTelecomInputClientPast15StatHistoryInvEsPort1 OBJECT-TYPE
	SYNTAX  EkiOnOff
	MAX-ACCESS read-only
	STATUS current
	DESCRIPTION
        "
        Previous 15-min ES counter inv. 
        :This OID indicates that the previous 
        15-min Errored Second counter is 
        invalid
        "
	::= { pmcryptoPerfTelecomInputClientPast15StatHistoryPort1Entry 4 }


pmcryptoPerfTelecomInputClientPast15StatHistoryEsValuePort1 OBJECT-TYPE
	SYNTAX  Unsigned32
	MAX-ACCESS read-only
	STATUS current
	DESCRIPTION
        "
        Previous 15-min ES counter :This 
        OID gives the previous 15-min Errored 
        Second counter value
        "
	::= { pmcryptoPerfTelecomInputClientPast15StatHistoryPort1Entry 5 }


pmcryptoPerfTelecomInputClientPast15StatHistoryInvSesPort1 OBJECT-TYPE
	SYNTAX  EkiOnOff
	MAX-ACCESS read-only
	STATUS current
	DESCRIPTION
        "
        Previous 15-min SES counter inv. 
        :This OID indicates that the previous 
        15-min severely Errored Second
         counter is invalid
        "
	::= { pmcryptoPerfTelecomInputClientPast15StatHistoryPort1Entry 6 }


pmcryptoPerfTelecomInputClientPast15StatHistorySesValuePort1 OBJECT-TYPE
	SYNTAX  Unsigned32
	MAX-ACCESS read-only
	STATUS current
	DESCRIPTION
        "
        Previous 15-min SES counter :This 
        OID gives the previous 15-min severely 
        Errored Second counter value
        "
	::= { pmcryptoPerfTelecomInputClientPast15StatHistoryPort1Entry 7 }


pmcryptoPerfTelecomInputClientPast15StatHistoryInvSefsPort1 OBJECT-TYPE
	SYNTAX  EkiOnOff
	MAX-ACCESS read-only
	STATUS current
	DESCRIPTION
        "
        Previous 15-min SEFS counter inv. 
        :This OID indicates that the previous 
        15-min severely Errored Framing 
        Second counter is invalid
        "
	::= { pmcryptoPerfTelecomInputClientPast15StatHistoryPort1Entry 8 }


pmcryptoPerfTelecomInputClientPast15StatHistorySefsValuePort1 OBJECT-TYPE
	SYNTAX  Unsigned32
	MAX-ACCESS read-only
	STATUS current
	DESCRIPTION
        "
        Previous 15-min SEFS counter :This 
        OID gives the previous 15-min severely 
        Errored Framing Second counter
         value
        "
	::= { pmcryptoPerfTelecomInputClientPast15StatHistoryPort1Entry 9 }


pmcryptoPerfTelecomInputClientPast15StatHistoryInvUasPort1 OBJECT-TYPE
	SYNTAX  EkiOnOff
	MAX-ACCESS read-only
	STATUS current
	DESCRIPTION
        "
        Previous 15-min UAS counter inv. 
        :This OID indicates that the previous 
        15-min UnAvailable Second counter 
        is invalid
        "
	::= { pmcryptoPerfTelecomInputClientPast15StatHistoryPort1Entry 10 }


pmcryptoPerfTelecomInputClientPast15StatHistoryUasValuePort1 OBJECT-TYPE
	SYNTAX  Unsigned32
	MAX-ACCESS read-only
	STATUS current
	DESCRIPTION
        "
        Previous 15-min UAS counter :This 
        OID gives the previous 15-min UnAvailable 
        Second counter value
        "
	::= { pmcryptoPerfTelecomInputClientPast15StatHistoryPort1Entry 11 }


--- *****************************************************
---     Leaf of the telecomInputClientCurrent24Stat
--- *****************************************************
--- *********************************************************
---     TABLE for the pmcryptoPerfTelecomInputClientCurrent24Stat articles
--- *********************************************************

pmcryptoPerfTelecomInputClientCurrent24StatTable OBJECT-TYPE
	SYNTAX  SEQUENCE OF PmcryptoPerfTelecomInputClientCurrent24StatEntry
	MAX-ACCESS not-accessible
	STATUS current
	DESCRIPTION
        "
        List of pmcryptoPerfTelecomInputClientCurrent24Stat 
        Article
        "
	::= { pmcryptoMonPerfClient 80 }


pmcryptoPerfTelecomInputClientCurrent24StatEntry OBJECT-TYPE
	SYNTAX PmcryptoPerfTelecomInputClientCurrent24StatEntry
	MAX-ACCESS not-accessible
	STATUS current
	DESCRIPTION
        "
        Row definition for the pmcryptoPerfTelecomInputClientCurrent24Stat 
        table
        "
	INDEX   { pmcryptoPerfTelecomInputClientCurrent24StatIndex }
	::= { pmcryptoPerfTelecomInputClientCurrent24StatTable 1 }


PmcryptoPerfTelecomInputClientCurrent24StatEntry ::=
	SEQUENCE {
	pmcryptoPerfTelecomInputClientCurrent24StatIndex
		INTEGER,
	pmcryptoPerfTelecomInputClientCurrent24StatInvCvPortn
		EkiOnOff,
	pmcryptoPerfTelecomInputClientCurrent24StatCvValuePortn
		Unsigned32,
	pmcryptoPerfTelecomInputClientCurrent24StatInvEsPortn
		EkiOnOff,
	pmcryptoPerfTelecomInputClientCurrent24StatEsValuePortn
		Unsigned32,
	pmcryptoPerfTelecomInputClientCurrent24StatInvSesPortn
		EkiOnOff,
	pmcryptoPerfTelecomInputClientCurrent24StatSesValuePortn
		Unsigned32,
	pmcryptoPerfTelecomInputClientCurrent24StatInvSefsPortn
		EkiOnOff,
	pmcryptoPerfTelecomInputClientCurrent24StatSefsValuePortn
		Unsigned32,
	pmcryptoPerfTelecomInputClientCurrent24StatInvUasPortn
		EkiOnOff,
	pmcryptoPerfTelecomInputClientCurrent24StatUasValuePortn
		Unsigned32
	}


pmcryptoPerfTelecomInputClientCurrent24StatIndex OBJECT-TYPE
	SYNTAX  INTEGER(0..128)
	MAX-ACCESS  read-only
	STATUS current
	DESCRIPTION
        "
        Index definition for the pmcryptoPerfTelecomInputClientCurrent24Stat 
        table
        "
	::= { pmcryptoPerfTelecomInputClientCurrent24StatEntry 1 }


pmcryptoPerfTelecomInputClientCurrent24StatInvCvPortn OBJECT-TYPE
	SYNTAX  EkiOnOff
	MAX-ACCESS read-only
	STATUS current
	DESCRIPTION
        "
        Current 24-hours EBC counter inv. 
        :This OID indicates that the current 
        24-hours Coding Violation counter 
        is invalid
        "
	::= { pmcryptoPerfTelecomInputClientCurrent24StatEntry 2 }


pmcryptoPerfTelecomInputClientCurrent24StatCvValuePortn OBJECT-TYPE
	SYNTAX  Unsigned32
	MAX-ACCESS read-only
	STATUS current
	DESCRIPTION
        "
        Current 24-hours EBC counter :This 
        OID gives the current 24-hours
         Coding Violation counter value
        "
	::= { pmcryptoPerfTelecomInputClientCurrent24StatEntry 3 }


pmcryptoPerfTelecomInputClientCurrent24StatInvEsPortn OBJECT-TYPE
	SYNTAX  EkiOnOff
	MAX-ACCESS read-only
	STATUS current
	DESCRIPTION
        "
        Current 24-hours ES counter inv. 
        :This OID indicates that the current 
        24-hours Errored Second counter 
        is invalid
        "
	::= { pmcryptoPerfTelecomInputClientCurrent24StatEntry 4 }


pmcryptoPerfTelecomInputClientCurrent24StatEsValuePortn OBJECT-TYPE
	SYNTAX  Unsigned32
	MAX-ACCESS read-only
	STATUS current
	DESCRIPTION
        "
        Current 24-hours ES counter :This 
        OID gives the current 24-hours
         Errored Second counter value
        "
	::= { pmcryptoPerfTelecomInputClientCurrent24StatEntry 5 }


pmcryptoPerfTelecomInputClientCurrent24StatInvSesPortn OBJECT-TYPE
	SYNTAX  EkiOnOff
	MAX-ACCESS read-only
	STATUS current
	DESCRIPTION
        "
        Current 24-hours SES counter inv. 
        :This OID indicates that the current 
        24-hours severely Errored Second 
        counter is invalid
        "
	::= { pmcryptoPerfTelecomInputClientCurrent24StatEntry 6 }


pmcryptoPerfTelecomInputClientCurrent24StatSesValuePortn OBJECT-TYPE
	SYNTAX  Unsigned32
	MAX-ACCESS read-only
	STATUS current
	DESCRIPTION
        "
        Current 24-hours SES counter :This 
        OID gives the current 24-hours
         severely Errored Second counter 
        value
        "
	::= { pmcryptoPerfTelecomInputClientCurrent24StatEntry 7 }


pmcryptoPerfTelecomInputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter 
        is invalid
        "
	::= { pmcryptoPerfTelecomInputClientCurrent24StatEntry 8 }


pmcryptoPerfTelecomInputClientCurrent24StatSefsValuePortn OBJECT-TYPE
	SYNTAX  Unsigned32
	MAX-ACCESS read-only
	STATUS current
	DESCRIPTION
        "
        Current 24-hours SEFS counter
         :This OID gives the current 24-hours 
        severely Errored Framing Second 
        counter value
        "
	::= { pmcryptoPerfTelecomInputClientCurrent24StatEntry 9 }


pmcryptoPerfTelecomInputClientCurrent24StatInvUasPortn OBJECT-TYPE
	SYNTAX  EkiOnOff
	MAX-ACCESS read-only
	STATUS current
	DESCRIPTION
        "
        Current 24-hours UAS counter inv. 
        :This OID indicates that the current 
        24-hours UnAvailable Second counter 
        is invalid
        "
	::= { pmcryptoPerfTelecomInputClientCurrent24StatEntry 10 }


pmcryptoPerfTelecomInputClientCurrent24StatUasValuePortn OBJECT-TYPE
	SYNTAX  Unsigned32
	MAX-ACCESS read-only
	STATUS current
	DESCRIPTION
        "
        Current 24-hours UAS counter :This 
        OID gives the current 24-hours
         UnAvailable Second counter value
        "
	::= { pmcryptoPerfTelecomInputClientCurrent24StatEntry 11 }


--- *****************************************************
---     Leaf of the telecomInputClientPast24Stat
--- *****************************************************
--- *********************************************************
---     TABLE for the pmcryptoPerfTelecomInputClientPast24StatHistory articles
--- *********************************************************

pmcryptoPerfTelecomInputClientPast24StatHistoryPort1Table OBJECT-TYPE
	SYNTAX  SEQUENCE OF PmcryptoPerfTelecomInputClientPast24StatHistoryPort1Entry
	MAX-ACCESS not-accessible
	STATUS current
	DESCRIPTION
        "
        List of pmcryptoPerfTelecomInputClientPast24StatHistory 
        Article
        "
	::= { pmcryptoMonPerfClient 112 }


pmcryptoPerfTelecomInputClientPast24StatHistoryPort1Entry OBJECT-TYPE
	SYNTAX PmcryptoPerfTelecomInputClientPast24StatHistoryPort1Entry
	MAX-ACCESS not-accessible
	STATUS current
	DESCRIPTION
        "
        Row definition for the pmcryptoPerfTelecomInputClientPast24StatHistory 
        table
        "
	INDEX   { pmcryptoPerfTelecomInputClientPast24StatHistoryPort1Index }
	::= { pmcryptoPerfTelecomInputClientPast24StatHistoryPort1Table 1 }


PmcryptoPerfTelecomInputClientPast24StatHistoryPort1Entry ::=
	SEQUENCE {
	pmcryptoPerfTelecomInputClientPast24StatHistoryPort1Index
		INTEGER,
	pmcryptoPerfTelecomInputClientPast24StatHistoryInvCvPort1
		EkiOnOff,
	pmcryptoPerfTelecomInputClientPast24StatHistoryCvValuePort1
		Unsigned32,
	pmcryptoPerfTelecomInputClientPast24StatHistoryInvEsPort1
		EkiOnOff,
	pmcryptoPerfTelecomInputClientPast24StatHistoryEsValuePort1
		Unsigned32,
	pmcryptoPerfTelecomInputClientPast24StatHistoryInvSesPort1
		EkiOnOff,
	pmcryptoPerfTelecomInputClientPast24StatHistorySesValuePort1
		Unsigned32,
	pmcryptoPerfTelecomInputClientPast24StatHistoryInvSefsPort1
		EkiOnOff,
	pmcryptoPerfTelecomInputClientPast24StatHistorySefsValuePort1
		Unsigned32,
	pmcryptoPerfTelecomInputClientPast24StatHistoryInvUasPort1
		EkiOnOff,
	pmcryptoPerfTelecomInputClientPast24StatHistoryUasValuePort1
		Unsigned32
	}


pmcryptoPerfTelecomInputClientPast24StatHistoryPort1Index OBJECT-TYPE
	SYNTAX  INTEGER(0..128)
	MAX-ACCESS  read-only
	STATUS current
	DESCRIPTION
        "
        Index definition for the pmcryptoPerfTelecomInputClientPast24StatHistory 
        table
        "
	::= { pmcryptoPerfTelecomInputClientPast24StatHistoryPort1Entry 1 }


pmcryptoPerfTelecomInputClientPast24StatHistoryInvCvPort1 OBJECT-TYPE
	SYNTAX  EkiOnOff
	MAX-ACCESS read-only
	STATUS current
	DESCRIPTION
        "
        Previous 24-hours EBC counter
         inv. :This OID indicates that
         the previous 24-hours Coding Violation 
        counter is invalid
        "
	::= { pmcryptoPerfTelecomInputClientPast24StatHistoryPort1Entry 2 }


pmcryptoPerfTelecomInputClientPast24StatHistoryCvValuePort1 OBJECT-TYPE
	SYNTAX  Unsigned32
	MAX-ACCESS read-only
	STATUS current
	DESCRIPTION
        "
        Previous 24-hours EBC counter
         :This OID gives the previous 24-hours 
        Coding Violation counter value
        "
	::= { pmcryptoPerfTelecomInputClientPast24StatHistoryPort1Entry 3 }


pmcryptoPerfTelecomInputClientPast24StatHistoryInvEsPort1 OBJECT-TYPE
	SYNTAX  EkiOnOff
	MAX-ACCESS read-only
	STATUS current
	DESCRIPTION
        "
        Previous 24-hours ES counter inv. 
        :This OID indicates that the previous 
        24-hours Errored Second counter 
        is invalid
        "
	::= { pmcryptoPerfTelecomInputClientPast24StatHistoryPort1Entry 4 }


pmcryptoPerfTelecomInputClientPast24StatHistoryEsValuePort1 OBJECT-TYPE
	SYNTAX  Unsigned32
	MAX-ACCESS read-only
	STATUS current
	DESCRIPTION
        "
        Previous 24-hours ES counter :This 
        OID gives the previous 24-hours 
        Errored Second counter value
        "
	::= { pmcryptoPerfTelecomInputClientPast24StatHistoryPort1Entry 5 }


pmcryptoPerfTelecomInputClientPast24StatHistoryInvSesPort1 OBJECT-TYPE
	SYNTAX  EkiOnOff
	MAX-ACCESS read-only
	STATUS current
	DESCRIPTION
        "
        Previous 24-hours SES counter
         inv. :This OID indicates that
         the previous 24-hours severely 
        Errored Second counter is invalid
        "
	::= { pmcryptoPerfTelecomInputClientPast24StatHistoryPort1Entry 6 }


pmcryptoPerfTelecomInputClientPast24StatHistorySesValuePort1 OBJECT-TYPE
	SYNTAX  Unsigned32
	MAX-ACCESS read-only
	STATUS current
	DESCRIPTION
        "
        Previous 24-hours SES counter
         :This OID gives the previous 24-hours 
        severely Errored Second counter 
        value
        "
	::= { pmcryptoPerfTelecomInputClientPast24StatHistoryPort1Entry 7 }


pmcryptoPerfTelecomInputClientPast24StatHistoryInvSefsPort1 OBJECT-TYPE
	SYNTAX  EkiOnOff
	MAX-ACCESS read-only
	STATUS current
	DESCRIPTION
        "
        Previous 24-hours SEFS counter 
        inv. :This OID indicates that the 
        previous 24-hours severely Errored 
        Framing Second counter is invalid
        "
	::= { pmcryptoPerfTelecomInputClientPast24StatHistoryPort1Entry 8 }


pmcryptoPerfTelecomInputClientPast24StatHistorySefsValuePort1 OBJECT-TYPE
	SYNTAX  Unsigned32
	MAX-ACCESS read-only
	STATUS current
	DESCRIPTION
        "
        Previous 24-hours SEFS counter 
        :This OID gives the previous 24-hours 
        severely Errored Framing Second 
        counter value
        "
	::= { pmcryptoPerfTelecomInputClientPast24StatHistoryPort1Entry 9 }


pmcryptoPerfTelecomInputClientPast24StatHistoryInvUasPort1 OBJECT-TYPE
	SYNTAX  EkiOnOff
	MAX-ACCESS read-only
	STATUS current
	DESCRIPTION
        "
        Previous 24-hours UAS counter
         inv. :This OID indicates that
         the previous 24-hours UnAvailable 
        Second counter is invalid
        "
	::= { pmcryptoPerfTelecomInputClientPast24StatHistoryPort1Entry 10 }


pmcryptoPerfTelecomInputClientPast24StatHistoryUasValuePort1 OBJECT-TYPE
	SYNTAX  Unsigned32
	MAX-ACCESS read-only
	STATUS current
	DESCRIPTION
        "
        Previous 24-hours UAS counter
         :This OID gives the previous 24-hours 
        UnAvailable Second counter value
        "
	::= { pmcryptoPerfTelecomInputClientPast24StatHistoryPort1Entry 11 }


--- *****************************************************
---     Leaf of the telecomOutputClientCurrent15Stat
--- *****************************************************
--- *********************************************************
---     TABLE for the pmcryptoPerfTelecomOutputClientCurrent15Stat articles
--- *********************************************************

pmcryptoPerfTelecomOutputClientCurrent15StatTable OBJECT-TYPE
	SYNTAX  SEQUENCE OF PmcryptoPerfTelecomOutputClientCurrent15StatEntry
	MAX-ACCESS not-accessible
	STATUS current
	DESCRIPTION
        "
        List of pmcryptoPerfTelecomOutputClientCurrent15Stat 
        Article
        "
	::= { pmcryptoMonPerfClient 144 }


pmcryptoPerfTelecomOutputClientCurrent15StatEntry OBJECT-TYPE
	SYNTAX PmcryptoPerfTelecomOutputClientCurrent15StatEntry
	MAX-ACCESS not-accessible
	STATUS current
	DESCRIPTION
        "
        Row definition for the pmcryptoPerfTelecomOutputClientCurrent15Stat 
        table
        "
	INDEX   { pmcryptoPerfTelecomOutputClientCurrent15StatIndex }
	::= { pmcryptoPerfTelecomOutputClientCurrent15StatTable 1 }


PmcryptoPerfTelecomOutputClientCurrent15StatEntry ::=
	SEQUENCE {
	pmcryptoPerfTelecomOutputClientCurrent15StatIndex
		INTEGER,
	pmcryptoPerfTelecomOutputClientCurrent15StatInvCvPortn
		EkiOnOff,
	pmcryptoPerfTelecomOutputClientCurrent15StatCvValuePortn
		Unsigned32,
	pmcryptoPerfTelecomOutputClientCurrent15StatInvEsPortn
		EkiOnOff,
	pmcryptoPerfTelecomOutputClientCurrent15StatEsValuePortn
		Unsigned32,
	pmcryptoPerfTelecomOutputClientCurrent15StatInvSesPortn
		EkiOnOff,
	pmcryptoPerfTelecomOutputClientCurrent15StatSesValuePortn
		Unsigned32,
	pmcryptoPerfTelecomOutputClientCurrent15StatInvSefsPortn
		EkiOnOff,
	pmcryptoPerfTelecomOutputClientCurrent15StatSefsValuePortn
		Unsigned32,
	pmcryptoPerfTelecomOutputClientCurrent15StatInvUasPortn
		EkiOnOff,
	pmcryptoPerfTelecomOutputClientCurrent15StatUasValuePortn
		Unsigned32
	}


pmcryptoPerfTelecomOutputClientCurrent15StatIndex OBJECT-TYPE
	SYNTAX  INTEGER(0..128)
	MAX-ACCESS  read-only
	STATUS current
	DESCRIPTION
        "
        Index definition for the pmcryptoPerfTelecomOutputClientCurrent15Stat 
        table
        "
	::= { pmcryptoPerfTelecomOutputClientCurrent15StatEntry 1 }


pmcryptoPerfTelecomOutputClientCurrent15StatInvCvPortn OBJECT-TYPE
	SYNTAX  EkiOnOff
	MAX-ACCESS read-only
	STATUS current
	DESCRIPTION
        "
        Current 15-min EBC counter inv. 
        :This OID indicates that the current 
        15-min Coding Violation counter 
        is invalid
        "
	::= { pmcryptoPerfTelecomOutputClientCurrent15StatEntry 2 }


pmcryptoPerfTelecomOutputClientCurrent15StatCvValuePortn OBJECT-TYPE
	SYNTAX  Unsigned32
	MAX-ACCESS read-only
	STATUS current
	DESCRIPTION
        "
        Current 15-min EBC counter :This 
        OID gives the current 15-min Coding 
        Violation counter value
        "
	::= { pmcryptoPerfTelecomOutputClientCurrent15StatEntry 3 }


pmcryptoPerfTelecomOutputClientCurrent15StatInvEsPortn OBJECT-TYPE
	SYNTAX  EkiOnOff
	MAX-ACCESS read-only
	STATUS current
	DESCRIPTION
        "
        Current 15-min ES counter inv. 
        :This OID indicates that the current 
        15-min Errored Second counter is 
        invalid
        "
	::= { pmcryptoPerfTelecomOutputClientCurrent15StatEntry 4 }


pmcryptoPerfTelecomOutputClientCurrent15StatEsValuePortn OBJECT-TYPE
	SYNTAX  Unsigned32
	MAX-ACCESS read-only
	STATUS current
	DESCRIPTION
        "
        Current 15-min ES counter :This 
        OID gives the current 15-min Errored 
        Second counter value
        "
	::= { pmcryptoPerfTelecomOutputClientCurrent15StatEntry 5 }


pmcryptoPerfTelecomOutputClientCurrent15StatInvSesPortn OBJECT-TYPE
	SYNTAX  EkiOnOff
	MAX-ACCESS read-only
	STATUS current
	DESCRIPTION
        "
        Current 15-min SES counter inv. 
        :This OID indicates that the current 
        15-min severely Errored Second
         counter is invalid
        "
	::= { pmcryptoPerfTelecomOutputClientCurrent15StatEntry 6 }


pmcryptoPerfTelecomOutputClientCurrent15StatSesValuePortn OBJECT-TYPE
	SYNTAX  Unsigned32
	MAX-ACCESS read-only
	STATUS current
	DESCRIPTION
        "
        Current 15-min SES counter :This 
        OID gives the current 15-min severely 
        Errored Second counter value
        "
	::= { pmcryptoPerfTelecomOutputClientCurrent15StatEntry 7 }


pmcryptoPerfTelecomOutputClientCurrent15StatInvSefsPortn OBJECT-TYPE
	SYNTAX  EkiOnOff
	MAX-ACCESS read-only
	STATUS current
	DESCRIPTION
        "
        Current 15-min SEFS counter inv. 
        :This OID indicates that the current 
        15-min severely Errored Framing 
        Second counter is invalid
        "
	::= { pmcryptoPerfTelecomOutputClientCurrent15StatEntry 8 }


pmcryptoPerfTelecomOutputClientCurrent15StatSefsValuePortn OBJECT-TYPE
	SYNTAX  Unsigned32
	MAX-ACCESS read-only
	STATUS current
	DESCRIPTION
        "
        Current 15-min SEFS counter :This 
        OID gives the current 15-min severely 
        Errored Framing Second counter
         value
        "
	::= { pmcryptoPerfTelecomOutputClientCurrent15StatEntry 9 }


pmcryptoPerfTelecomOutputClientCurrent15StatInvUasPortn OBJECT-TYPE
	SYNTAX  EkiOnOff
	MAX-ACCESS read-only
	STATUS current
	DESCRIPTION
        "
        Current 15-min UAS counter inv. 
        :This OID indicates that the current 
        15-min UnAvailable Second counter 
        is invalid
        "
	::= { pmcryptoPerfTelecomOutputClientCurrent15StatEntry 10 }


pmcryptoPerfTelecomOutputClientCurrent15StatUasValuePortn OBJECT-TYPE
	SYNTAX  Unsigned32
	MAX-ACCESS read-only
	STATUS current
	DESCRIPTION
        "
        Current 15-min UAS counter :This 
        OID gives the current 15-min UnAvailable 
        Second counter value
        "
	::= { pmcryptoPerfTelecomOutputClientCurrent15StatEntry 11 }


--- *****************************************************
---     Leaf of the telecomOutputClientPast15Stat
--- *****************************************************
--- *********************************************************
---     TABLE for the pmcryptoPerfTelecomOutputClientPast15StatHistory articles
--- *********************************************************

pmcryptoPerfTelecomOutputClientPast15StatHistoryPort1Table OBJECT-TYPE
	SYNTAX  SEQUENCE OF PmcryptoPerfTelecomOutputClientPast15StatHistoryPort1Entry
	MAX-ACCESS not-accessible
	STATUS current
	DESCRIPTION
        "
        List of pmcryptoPerfTelecomOutputClientPast15StatHistory 
        Article
        "
	::= { pmcryptoMonPerfClient 176 }


pmcryptoPerfTelecomOutputClientPast15StatHistoryPort1Entry OBJECT-TYPE
	SYNTAX PmcryptoPerfTelecomOutputClientPast15StatHistoryPort1Entry
	MAX-ACCESS not-accessible
	STATUS current
	DESCRIPTION
        "
        Row definition for the pmcryptoPerfTelecomOutputClientPast15StatHistory 
        table
        "
	INDEX   { pmcryptoPerfTelecomOutputClientPast15StatHistoryPort1Index }
	::= { pmcryptoPerfTelecomOutputClientPast15StatHistoryPort1Table 1 }


PmcryptoPerfTelecomOutputClientPast15StatHistoryPort1Entry ::=
	SEQUENCE {
	pmcryptoPerfTelecomOutputClientPast15StatHistoryPort1Index
		INTEGER,
	pmcryptoPerfTelecomOutputClientPast15StatHistoryInvCvPort1
		EkiOnOff,
	pmcryptoPerfTelecomOutputClientPast15StatHistoryCvValuePort1
		Unsigned32,
	pmcryptoPerfTelecomOutputClientPast15StatHistoryInvEsPort1
		EkiOnOff,
	pmcryptoPerfTelecomOutputClientPast15StatHistoryEsValuePort1
		Unsigned32,
	pmcryptoPerfTelecomOutputClientPast15StatHistoryInvSesPort1
		EkiOnOff,
	pmcryptoPerfTelecomOutputClientPast15StatHistorySesValuePort1
		Unsigned32,
	pmcryptoPerfTelecomOutputClientPast15StatHistoryInvSefsPort1
		EkiOnOff,
	pmcryptoPerfTelecomOutputClientPast15StatHistorySefsValuePort1
		Unsigned32,
	pmcryptoPerfTelecomOutputClientPast15StatHistoryInvUasPort1
		EkiOnOff,
	pmcryptoPerfTelecomOutputClientPast15StatHistoryUasValuePort1
		Unsigned32
	}


pmcryptoPerfTelecomOutputClientPast15StatHistoryPort1Index OBJECT-TYPE
	SYNTAX  INTEGER(0..128)
	MAX-ACCESS  read-only
	STATUS current
	DESCRIPTION
        "
        Index definition for the pmcryptoPerfTelecomOutputClientPast15StatHistory 
        table
        "
	::= { pmcryptoPerfTelecomOutputClientPast15StatHistoryPort1Entry 1 }


pmcryptoPerfTelecomOutputClientPast15StatHistoryInvCvPort1 OBJECT-TYPE
	SYNTAX  EkiOnOff
	MAX-ACCESS read-only
	STATUS current
	DESCRIPTION
        "
        Previous 15-min EBC counter inv. 
        :This OID indicates that the previous 
        15-min Coding Violation counter 
        is invalid
        "
	::= { pmcryptoPerfTelecomOutputClientPast15StatHistoryPort1Entry 2 }


pmcryptoPerfTelecomOutputClientPast15StatHistoryCvValuePort1 OBJECT-TYPE
	SYNTAX  Unsigned32
	MAX-ACCESS read-only
	STATUS current
	DESCRIPTION
        "
        Previous 15-min EBC counter :This 
        OID gives the previous 15-min Coding 
        Violation counter value
        "
	::= { pmcryptoPerfTelecomOutputClientPast15StatHistoryPort1Entry 3 }


pmcryptoPerfTelecomOutputClientPast15StatHistoryInvEsPort1 OBJECT-TYPE
	SYNTAX  EkiOnOff
	MAX-ACCESS read-only
	STATUS current
	DESCRIPTION
        "
        Previous 15-min ES counter inv. 
        :This OID indicates that the previous 
        15-min Errored Second counter is 
        invalid
        "
	::= { pmcryptoPerfTelecomOutputClientPast15StatHistoryPort1Entry 4 }


pmcryptoPerfTelecomOutputClientPast15StatHistoryEsValuePort1 OBJECT-TYPE
	SYNTAX  Unsigned32
	MAX-ACCESS read-only
	STATUS current
	DESCRIPTION
        "
        Previous 15-min ES counter :This 
        OID gives the previous 15-min Errored 
        Second counter value
        "
	::= { pmcryptoPerfTelecomOutputClientPast15StatHistoryPort1Entry 5 }


pmcryptoPerfTelecomOutputClientPast15StatHistoryInvSesPort1 OBJECT-TYPE
	SYNTAX  EkiOnOff
	MAX-ACCESS read-only
	STATUS current
	DESCRIPTION
        "
        Previous 15-min SES counter inv. 
        :This OID indicates that the previous 
        15-min severely Errored Second
         counter is invalid
        "
	::= { pmcryptoPerfTelecomOutputClientPast15StatHistoryPort1Entry 6 }


pmcryptoPerfTelecomOutputClientPast15StatHistorySesValuePort1 OBJECT-TYPE
	SYNTAX  Unsigned32
	MAX-ACCESS read-only
	STATUS current
	DESCRIPTION
        "
        Previous 15-min SES counter :This 
        OID gives the previous 15-min severely 
        Errored Second counter value
        "
	::= { pmcryptoPerfTelecomOutputClientPast15StatHistoryPort1Entry 7 }


pmcryptoPerfTelecomOutputClientPast15StatHistoryInvSefsPort1 OBJECT-TYPE
	SYNTAX  EkiOnOff
	MAX-ACCESS read-only
	STATUS current
	DESCRIPTION
        "
        Previous 15-min SEFS counter inv. 
        :This OID indicates that the previous 
        15-min severely Errored Framing 
        Second counter is invalid
        "
	::= { pmcryptoPerfTelecomOutputClientPast15StatHistoryPort1Entry 8 }


pmcryptoPerfTelecomOutputClientPast15StatHistorySefsValuePort1 OBJECT-TYPE
	SYNTAX  Unsigned32
	MAX-ACCESS read-only
	STATUS current
	DESCRIPTION
        "
        Previous 15-min SEFS counter :This 
        OID gives the previous 15-min severely 
        Errored Framing Second counter
         value
        "
	::= { pmcryptoPerfTelecomOutputClientPast15StatHistoryPort1Entry 9 }


pmcryptoPerfTelecomOutputClientPast15StatHistoryInvUasPort1 OBJECT-TYPE
	SYNTAX  EkiOnOff
	MAX-ACCESS read-only
	STATUS current
	DESCRIPTION
        "
        Previous 15-min UAS counter inv. 
        :This OID indicates that the previous 
        15-min UnAvailable Second counter 
        is invalid
        "
	::= { pmcryptoPerfTelecomOutputClientPast15StatHistoryPort1Entry 10 }


pmcryptoPerfTelecomOutputClientPast15StatHistoryUasValuePort1 OBJECT-TYPE
	SYNTAX  Unsigned32
	MAX-ACCESS read-only
	STATUS current
	DESCRIPTION
        "
        Previous 15-min UAS counter :This 
        OID gives the previous 15-min UnAvailable 
        Second counter value
        "
	::= { pmcryptoPerfTelecomOutputClientPast15StatHistoryPort1Entry 11 }


--- *****************************************************
---     Leaf of the telecomOutputClientCurrent24Stat
--- *****************************************************
--- *********************************************************
---     TABLE for the pmcryptoPerfTelecomOutputClientCurrent24Stat articles
--- *********************************************************

pmcryptoPerfTelecomOutputClientCurrent24StatTable OBJECT-TYPE
	SYNTAX  SEQUENCE OF PmcryptoPerfTelecomOutputClientCurrent24StatEntry
	MAX-ACCESS not-accessible
	STATUS current
	DESCRIPTION
        "
        List of pmcryptoPerfTelecomOutputClientCurrent24Stat 
        Article
        "
	::= { pmcryptoMonPerfClient 208 }


pmcryptoPerfTelecomOutputClientCurrent24StatEntry OBJECT-TYPE
	SYNTAX PmcryptoPerfTelecomOutputClientCurrent24StatEntry
	MAX-ACCESS not-accessible
	STATUS current
	DESCRIPTION
        "
        Row definition for the pmcryptoPerfTelecomOutputClientCurrent24Stat 
        table
        "
	INDEX   { pmcryptoPerfTelecomOutputClientCurrent24StatIndex }
	::= { pmcryptoPerfTelecomOutputClientCurrent24StatTable 1 }


PmcryptoPerfTelecomOutputClientCurrent24StatEntry ::=
	SEQUENCE {
	pmcryptoPerfTelecomOutputClientCurrent24StatIndex
		INTEGER,
	pmcryptoPerfTelecomOutputClientCurrent24StatInvCvPortn
		EkiOnOff,
	pmcryptoPerfTelecomOutputClientCurrent24StatCvValuePortn
		Unsigned32,
	pmcryptoPerfTelecomOutputClientCurrent24StatInvEsPortn
		EkiOnOff,
	pmcryptoPerfTelecomOutputClientCurrent24StatEsValuePortn
		Unsigned32,
	pmcryptoPerfTelecomOutputClientCurrent24StatInvSesPortn
		EkiOnOff,
	pmcryptoPerfTelecomOutputClientCurrent24StatSesValuePortn
		Unsigned32,
	pmcryptoPerfTelecomOutputClientCurrent24StatInvSefsPortn
		EkiOnOff,
	pmcryptoPerfTelecomOutputClientCurrent24StatSefsValuePortn
		Unsigned32,
	pmcryptoPerfTelecomOutputClientCurrent24StatInvUasPortn
		EkiOnOff,
	pmcryptoPerfTelecomOutputClientCurrent24StatUasValuePortn
		Unsigned32
	}


pmcryptoPerfTelecomOutputClientCurrent24StatIndex OBJECT-TYPE
	SYNTAX  INTEGER(0..128)
	MAX-ACCESS  read-only
	STATUS current
	DESCRIPTION
        "
        Index definition for the pmcryptoPerfTelecomOutputClientCurrent24Stat 
        table
        "
	::= { pmcryptoPerfTelecomOutputClientCurrent24StatEntry 1 }


pmcryptoPerfTelecomOutputClientCurrent24StatInvCvPortn OBJECT-TYPE
	SYNTAX  EkiOnOff
	MAX-ACCESS read-only
	STATUS current
	DESCRIPTION
        "
        Current 24-hours EBC counter inv. 
        :This OID indicates that the current 
        24-hours Coding Violation counter 
        is invalid
        "
	::= { pmcryptoPerfTelecomOutputClientCurrent24StatEntry 2 }


pmcryptoPerfTelecomOutputClientCurrent24StatCvValuePortn OBJECT-TYPE
	SYNTAX  Unsigned32
	MAX-ACCESS read-only
	STATUS current
	DESCRIPTION
        "
        Current 24-hours EBC counter :This 
        OID gives the current 24-hours
         Coding Violation counter value
        "
	::= { pmcryptoPerfTelecomOutputClientCurrent24StatEntry 3 }


pmcryptoPerfTelecomOutputClientCurrent24StatInvEsPortn OBJECT-TYPE
	SYNTAX  EkiOnOff
	MAX-ACCESS read-only
	STATUS current
	DESCRIPTION
        "
        Current 24-hours ES counter inv. 
        :This OID indicates that the current 
        24-hours Errored Second counter 
        is invalid
        "
	::= { pmcryptoPerfTelecomOutputClientCurrent24StatEntry 4 }


pmcryptoPerfTelecomOutputClientCurrent24StatEsValuePortn OBJECT-TYPE
	SYNTAX  Unsigned32
	MAX-ACCESS read-only
	STATUS current
	DESCRIPTION
        "
        Current 24-hours ES counter :This 
        OID gives the current 24-hours
         Errored Second counter value
        "
	::= { pmcryptoPerfTelecomOutputClientCurrent24StatEntry 5 }


pmcryptoPerfTelecomOutputClientCurrent24StatInvSesPortn OBJECT-TYPE
	SYNTAX  EkiOnOff
	MAX-ACCESS read-only
	STATUS current
	DESCRIPTION
        "
        Current 24-hours SES counter inv. 
        :This OID indicates that the current 
        24-hours severely Errored Second 
        counter is invalid
        "
	::= { pmcryptoPerfTelecomOutputClientCurrent24StatEntry 6 }


pmcryptoPerfTelecomOutputClientCurrent24StatSesValuePortn OBJECT-TYPE
	SYNTAX  Unsigned32
	MAX-ACCESS read-only
	STATUS current
	DESCRIPTION
        "
        Current 24-hours SES counter :This 
        OID gives the current 24-hours
         severely Errored Second counter 
        value
        "
	::= { pmcryptoPerfTelecomOutputClientCurrent24StatEntry 7 }


pmcryptoPerfTelecomOutputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter 
        is invalid
        "
	::= { pmcryptoPerfTelecomOutputClientCurrent24StatEntry 8 }


pmcryptoPerfTelecomOutputClientCurrent24StatSefsValuePortn OBJECT-TYPE
	SYNTAX  Unsigned32
	MAX-ACCESS read-only
	STATUS current
	DESCRIPTION
        "
        Current 24-hours SEFS counter
         :This OID gives the current 24-hours 
        severely Errored Framing Second 
        counter value
        "
	::= { pmcryptoPerfTelecomOutputClientCurrent24StatEntry 9 }


pmcryptoPerfTelecomOutputClientCurrent24StatInvUasPortn OBJECT-TYPE
	SYNTAX  EkiOnOff
	MAX-ACCESS read-only
	STATUS current
	DESCRIPTION
        "
        Current 24-hours UAS counter inv. 
        :This OID indicates that the current 
        24-hours UnAvailable Second counter 
        is invalid
        "
	::= { pmcryptoPerfTelecomOutputClientCurrent24StatEntry 10 }


pmcryptoPerfTelecomOutputClientCurrent24StatUasValuePortn OBJECT-TYPE
	SYNTAX  Unsigned32
	MAX-ACCESS read-only
	STATUS current
	DESCRIPTION
        "
        Current 24-hours UAS counter :This 
        OID gives the current 24-hours
         UnAvailable Second counter value
        "
	::= { pmcryptoPerfTelecomOutputClientCurrent24StatEntry 11 }


--- *****************************************************
---     Leaf of the telecomOutputClientPast24Stat
--- *****************************************************
--- *********************************************************
---     TABLE for the pmcryptoPerfTelecomOutputClientPast24StatHistory articles
--- *********************************************************

pmcryptoPerfTelecomOutputClientPast24StatHistoryPort1Table OBJECT-TYPE
	SYNTAX  SEQUENCE OF PmcryptoPerfTelecomOutputClientPast24StatHistoryPort1Entry
	MAX-ACCESS not-accessible
	STATUS current
	DESCRIPTION
        "
        List of pmcryptoPerfTelecomOutputClientPast24StatHistory 
        Article
        "
	::= { pmcryptoMonPerfClient 240 }


pmcryptoPerfTelecomOutputClientPast24StatHistoryPort1Entry OBJECT-TYPE
	SYNTAX PmcryptoPerfTelecomOutputClientPast24StatHistoryPort1Entry
	MAX-ACCESS not-accessible
	STATUS current
	DESCRIPTION
        "
        Row definition for the pmcryptoPerfTelecomOutputClientPast24StatHistory 
        table
        "
	INDEX   { pmcryptoPerfTelecomOutputClientPast24StatHistoryPort1Index }
	::= { pmcryptoPerfTelecomOutputClientPast24StatHistoryPort1Table 1 }


PmcryptoPerfTelecomOutputClientPast24StatHistoryPort1Entry ::=
	SEQUENCE {
	pmcryptoPerfTelecomOutputClientPast24StatHistoryPort1Index
		INTEGER,
	pmcryptoPerfTelecomOutputClientPast24StatHistoryInvCvPort1
		EkiOnOff,
	pmcryptoPerfTelecomOutputClientPast24StatHistoryCvValuePort1
		Unsigned32,
	pmcryptoPerfTelecomOutputClientPast24StatHistoryInvEsPort1
		EkiOnOff,
	pmcryptoPerfTelecomOutputClientPast24StatHistoryEsValuePort1
		Unsigned32,
	pmcryptoPerfTelecomOutputClientPast24StatHistoryInvSesPort1
		EkiOnOff,
	pmcryptoPerfTelecomOutputClientPast24StatHistorySesValuePort1
		Unsigned32,
	pmcryptoPerfTelecomOutputClientPast24StatHistoryInvSefsPort1
		EkiOnOff,
	pmcryptoPerfTelecomOutputClientPast24StatHistorySefsValuePort1
		Unsigned32,
	pmcryptoPerfTelecomOutputClientPast24StatHistoryInvUasPort1
		EkiOnOff,
	pmcryptoPerfTelecomOutputClientPast24StatHistoryUasValuePort1
		Unsigned32
	}


pmcryptoPerfTelecomOutputClientPast24StatHistoryPort1Index OBJECT-TYPE
	SYNTAX  INTEGER(0..128)
	MAX-ACCESS  read-only
	STATUS current
	DESCRIPTION
        "
        Index definition for the pmcryptoPerfTelecomOutputClientPast24StatHistory 
        table
        "
	::= { pmcryptoPerfTelecomOutputClientPast24StatHistoryPort1Entry 1 }


pmcryptoPerfTelecomOutputClientPast24StatHistoryInvCvPort1 OBJECT-TYPE
	SYNTAX  EkiOnOff
	MAX-ACCESS read-only
	STATUS current
	DESCRIPTION
        "
        Previous 24-hours EBC counter
         inv. :This OID indicates that
         the previous 24-hours Coding Violation 
        counter is invalid
        "
	::= { pmcryptoPerfTelecomOutputClientPast24StatHistoryPort1Entry 2 }


pmcryptoPerfTelecomOutputClientPast24StatHistoryCvValuePort1 OBJECT-TYPE
	SYNTAX  Unsigned32
	MAX-ACCESS read-only
	STATUS current
	DESCRIPTION
        "
        Previous 24-hours EBC counter
         :This OID gives the previous 24-hours 
        Coding Violation counter value
        "
	::= { pmcryptoPerfTelecomOutputClientPast24StatHistoryPort1Entry 3 }


pmcryptoPerfTelecomOutputClientPast24StatHistoryInvEsPort1 OBJECT-TYPE
	SYNTAX  EkiOnOff
	MAX-ACCESS read-only
	STATUS current
	DESCRIPTION
        "
        Previous 24-hours ES counter inv. 
        :This OID indicates that the previous 
        24-hours Errored Second counter 
        is invalid
        "
	::= { pmcryptoPerfTelecomOutputClientPast24StatHistoryPort1Entry 4 }


pmcryptoPerfTelecomOutputClientPast24StatHistoryEsValuePort1 OBJECT-TYPE
	SYNTAX  Unsigned32
	MAX-ACCESS read-only
	STATUS current
	DESCRIPTION
        "
        Previous 24-hours ES counter :This 
        OID gives the previous 24-hours 
        Errored Second counter value
        "
	::= { pmcryptoPerfTelecomOutputClientPast24StatHistoryPort1Entry 5 }


pmcryptoPerfTelecomOutputClientPast24StatHistoryInvSesPort1 OBJECT-TYPE
	SYNTAX  EkiOnOff
	MAX-ACCESS read-only
	STATUS current
	DESCRIPTION
        "
        Previous 24-hours SES counter
         inv. :This OID indicates that
         the previous 24-hours severely 
        Errored Second counter is invalid
        "
	::= { pmcryptoPerfTelecomOutputClientPast24StatHistoryPort1Entry 6 }


pmcryptoPerfTelecomOutputClientPast24StatHistorySesValuePort1 OBJECT-TYPE
	SYNTAX  Unsigned32
	MAX-ACCESS read-only
	STATUS current
	DESCRIPTION
        "
        Previous 24-hours SES counter
         :This OID gives the previous 24-hours 
        severely Errored Second counter 
        value
        "
	::= { pmcryptoPerfTelecomOutputClientPast24StatHistoryPort1Entry 7 }


pmcryptoPerfTelecomOutputClientPast24StatHistoryInvSefsPort1 OBJECT-TYPE
	SYNTAX  EkiOnOff
	MAX-ACCESS read-only
	STATUS current
	DESCRIPTION
        "
        Previous 24-hours SEFS counter 
        inv. :This OID indicates that the 
        previous 24-hours severely Errored 
        Framing Second counter is invalid
        "
	::= { pmcryptoPerfTelecomOutputClientPast24StatHistoryPort1Entry 8 }


pmcryptoPerfTelecomOutputClientPast24StatHistorySefsValuePort1 OBJECT-TYPE
	SYNTAX  Unsigned32
	MAX-ACCESS read-only
	STATUS current
	DESCRIPTION
        "
        Previous 24-hours SEFS counter 
        :This OID gives the previous 24-hours 
        severely Errored Framing Second 
        counter value
        "
	::= { pmcryptoPerfTelecomOutputClientPast24StatHistoryPort1Entry 9 }


pmcryptoPerfTelecomOutputClientPast24StatHistoryInvUasPort1 OBJECT-TYPE
	SYNTAX  EkiOnOff
	MAX-ACCESS read-only
	STATUS current
	DESCRIPTION
        "
        Previous 24-hours UAS counter
         inv. :This OID indicates that
         the previous 24-hours UnAvailable 
        Second counter is invalid
        "
	::= { pmcryptoPerfTelecomOutputClientPast24StatHistoryPort1Entry 10 }


pmcryptoPerfTelecomOutputClientPast24StatHistoryUasValuePort1 OBJECT-TYPE
	SYNTAX  Unsigned32
	MAX-ACCESS read-only
	STATUS current
	DESCRIPTION
        "
        Previous 24-hours UAS counter
         :This OID gives the previous 24-hours 
        UnAvailable Second counter value
        "
	::= { pmcryptoPerfTelecomOutputClientPast24StatHistoryPort1Entry 11 }


--- *****************************************************
---     Leaf of the telecomLinePostFecCurrent15Stat
--- *****************************************************
--- *********************************************************
---     TABLE for the pmcryptoPerfTelecomLinePostFecCurrent15Stat articles
--- *********************************************************

pmcryptoPerfTelecomLinePostFecCurrent15StatTable OBJECT-TYPE
	SYNTAX  SEQUENCE OF PmcryptoPerfTelecomLinePostFecCurrent15StatEntry
	MAX-ACCESS not-accessible
	STATUS current
	DESCRIPTION
        "
        List of pmcryptoPerfTelecomLinePostFecCurrent15Stat 
        Article
        "
	::= { pmcryptoMonPerfLine 336 }


pmcryptoPerfTelecomLinePostFecCurrent15StatEntry OBJECT-TYPE
	SYNTAX PmcryptoPerfTelecomLinePostFecCurrent15StatEntry
	MAX-ACCESS not-accessible
	STATUS current
	DESCRIPTION
        "
        Row definition for the pmcryptoPerfTelecomLinePostFecCurrent15Stat 
        table
        "
	INDEX   { pmcryptoPerfTelecomLinePostFecCurrent15StatIndex }
	::= { pmcryptoPerfTelecomLinePostFecCurrent15StatTable 1 }


PmcryptoPerfTelecomLinePostFecCurrent15StatEntry ::=
	SEQUENCE {
	pmcryptoPerfTelecomLinePostFecCurrent15StatIndex
		INTEGER,
	pmcryptoPerfTelecomLinePostFecCurrent15StatInvCvPortn
		EkiOnOff,
	pmcryptoPerfTelecomLinePostFecCurrent15StatCvValuePortn
		Unsigned32,
	pmcryptoPerfTelecomLinePostFecCurrent15StatInvEsPortn
		EkiOnOff,
	pmcryptoPerfTelecomLinePostFecCurrent15StatEsValuePortn
		Unsigned32,
	pmcryptoPerfTelecomLinePostFecCurrent15StatInvSesPortn
		EkiOnOff,
	pmcryptoPerfTelecomLinePostFecCurrent15StatSesValuePortn
		Unsigned32,
	pmcryptoPerfTelecomLinePostFecCurrent15StatInvSefsPortn
		EkiOnOff,
	pmcryptoPerfTelecomLinePostFecCurrent15StatSefsValuePortn
		Unsigned32,
	pmcryptoPerfTelecomLinePostFecCurrent15StatInvUasPortn
		EkiOnOff,
	pmcryptoPerfTelecomLinePostFecCurrent15StatUasValuePortn
		Unsigned32
	}


pmcryptoPerfTelecomLinePostFecCurrent15StatIndex OBJECT-TYPE
	SYNTAX  INTEGER(0..128)
	MAX-ACCESS  read-only
	STATUS current
	DESCRIPTION
        "
        Index definition for the pmcryptoPerfTelecomLinePostFecCurrent15Stat 
        table
        "
	::= { pmcryptoPerfTelecomLinePostFecCurrent15StatEntry 1 }


pmcryptoPerfTelecomLinePostFecCurrent15StatInvCvPortn OBJECT-TYPE
	SYNTAX  EkiOnOff
	MAX-ACCESS read-only
	STATUS current
	DESCRIPTION
        "
        Current 15-min EBC counter inv. 
        :This OID indicates that the current 
        15-min Coding Violation counter 
        is invalid
        "
	::= { pmcryptoPerfTelecomLinePostFecCurrent15StatEntry 2 }


pmcryptoPerfTelecomLinePostFecCurrent15StatCvValuePortn OBJECT-TYPE
	SYNTAX  Unsigned32
	MAX-ACCESS read-only
	STATUS current
	DESCRIPTION
        "
        Current 15-min EBC counter :This 
        OID gives the current 15-min Coding 
        Violation counter value
        "
	::= { pmcryptoPerfTelecomLinePostFecCurrent15StatEntry 3 }


pmcryptoPerfTelecomLinePostFecCurrent15StatInvEsPortn OBJECT-TYPE
	SYNTAX  EkiOnOff
	MAX-ACCESS read-only
	STATUS current
	DESCRIPTION
        "
        Current 15-min ES counter inv. 
        :This OID indicates that the current 
        15-min Errored Second counter is 
        invalid
        "
	::= { pmcryptoPerfTelecomLinePostFecCurrent15StatEntry 4 }


pmcryptoPerfTelecomLinePostFecCurrent15StatEsValuePortn OBJECT-TYPE
	SYNTAX  Unsigned32
	MAX-ACCESS read-only
	STATUS current
	DESCRIPTION
        "
        Current 15-min ES counter :This 
        OID gives the current 15-min Errored 
        Second counter value
        "
	::= { pmcryptoPerfTelecomLinePostFecCurrent15StatEntry 5 }


pmcryptoPerfTelecomLinePostFecCurrent15StatInvSesPortn OBJECT-TYPE
	SYNTAX  EkiOnOff
	MAX-ACCESS read-only
	STATUS current
	DESCRIPTION
        "
        Current 15-min SES counter inv. 
        :This OID indicates that the current 
        15-min severely Errored Second
         counter is invalid
        "
	::= { pmcryptoPerfTelecomLinePostFecCurrent15StatEntry 6 }


pmcryptoPerfTelecomLinePostFecCurrent15StatSesValuePortn OBJECT-TYPE
	SYNTAX  Unsigned32
	MAX-ACCESS read-only
	STATUS current
	DESCRIPTION
        "
        Current 15-min SES counter :This 
        OID gives the current 15-min severely 
        Errored Second counter value
        "
	::= { pmcryptoPerfTelecomLinePostFecCurrent15StatEntry 7 }


pmcryptoPerfTelecomLinePostFecCurrent15StatInvSefsPortn OBJECT-TYPE
	SYNTAX  EkiOnOff
	MAX-ACCESS read-only
	STATUS current
	DESCRIPTION
        "
        Current 15-min SEFS counter inv. 
        :This OID indicates that the current 
        15-min severely Errored Framing 
        Second counter is invalid
        "
	::= { pmcryptoPerfTelecomLinePostFecCurrent15StatEntry 8 }


pmcryptoPerfTelecomLinePostFecCurrent15StatSefsValuePortn OBJECT-TYPE
	SYNTAX  Unsigned32
	MAX-ACCESS read-only
	STATUS current
	DESCRIPTION
        "
        Current 15-min SEFS counter :This 
        OID gives the current 15-min severely 
        Errored Framing Second counter
         value
        "
	::= { pmcryptoPerfTelecomLinePostFecCurrent15StatEntry 9 }


pmcryptoPerfTelecomLinePostFecCurrent15StatInvUasPortn OBJECT-TYPE
	SYNTAX  EkiOnOff
	MAX-ACCESS read-only
	STATUS current
	DESCRIPTION
        "
        Current 15-min UAS counter inv. 
        :This OID indicates that the current 
        15-min UnAvailable Second counter 
        is invalid
        "
	::= { pmcryptoPerfTelecomLinePostFecCurrent15StatEntry 10 }


pmcryptoPerfTelecomLinePostFecCurrent15StatUasValuePortn OBJECT-TYPE
	SYNTAX  Unsigned32
	MAX-ACCESS read-only
	STATUS current
	DESCRIPTION
        "
        Current 15-min UAS counter :This 
        OID gives the current 15-min UnAvailable 
        Second counter value
        "
	::= { pmcryptoPerfTelecomLinePostFecCurrent15StatEntry 11 }


--- *****************************************************
---     Leaf of the telecomLinePostFecPast15Stat
--- *****************************************************
--- *********************************************************
---     TABLE for the pmcryptoPerfTelecomLinePostFecPast15StatHistory articles
--- *********************************************************

pmcryptoPerfTelecomLinePostFecPast15StatHistoryPort1Table OBJECT-TYPE
	SYNTAX  SEQUENCE OF PmcryptoPerfTelecomLinePostFecPast15StatHistoryPort1Entry
	MAX-ACCESS not-accessible
	STATUS current
	DESCRIPTION
        "
        List of pmcryptoPerfTelecomLinePostFecPast15StatHistory 
        Article
        "
	::= { pmcryptoMonPerfLine 337 }


pmcryptoPerfTelecomLinePostFecPast15StatHistoryPort1Entry OBJECT-TYPE
	SYNTAX PmcryptoPerfTelecomLinePostFecPast15StatHistoryPort1Entry
	MAX-ACCESS not-accessible
	STATUS current
	DESCRIPTION
        "
        Row definition for the pmcryptoPerfTelecomLinePostFecPast15StatHistory 
        table
        "
	INDEX   { pmcryptoPerfTelecomLinePostFecPast15StatHistoryPort1Index }
	::= { pmcryptoPerfTelecomLinePostFecPast15StatHistoryPort1Table 1 }


PmcryptoPerfTelecomLinePostFecPast15StatHistoryPort1Entry ::=
	SEQUENCE {
	pmcryptoPerfTelecomLinePostFecPast15StatHistoryPort1Index
		INTEGER,
	pmcryptoPerfTelecomLinePostFecPast15StatHistoryInvCvPort1
		EkiOnOff,
	pmcryptoPerfTelecomLinePostFecPast15StatHistoryCvValuePort1
		Unsigned32,
	pmcryptoPerfTelecomLinePostFecPast15StatHistoryInvEsPort1
		EkiOnOff,
	pmcryptoPerfTelecomLinePostFecPast15StatHistoryEsValuePort1
		Unsigned32,
	pmcryptoPerfTelecomLinePostFecPast15StatHistoryInvSesPort1
		EkiOnOff,
	pmcryptoPerfTelecomLinePostFecPast15StatHistorySesValuePort1
		Unsigned32,
	pmcryptoPerfTelecomLinePostFecPast15StatHistoryInvSefsPort1
		EkiOnOff,
	pmcryptoPerfTelecomLinePostFecPast15StatHistorySefsValuePort1
		Unsigned32,
	pmcryptoPerfTelecomLinePostFecPast15StatHistoryInvUasPort1
		EkiOnOff,
	pmcryptoPerfTelecomLinePostFecPast15StatHistoryUasValuePort1
		Unsigned32
	}


pmcryptoPerfTelecomLinePostFecPast15StatHistoryPort1Index OBJECT-TYPE
	SYNTAX  INTEGER(0..128)
	MAX-ACCESS  read-only
	STATUS current
	DESCRIPTION
        "
        Index definition for the pmcryptoPerfTelecomLinePostFecPast15StatHistory 
        table
        "
	::= { pmcryptoPerfTelecomLinePostFecPast15StatHistoryPort1Entry 1 }


pmcryptoPerfTelecomLinePostFecPast15StatHistoryInvCvPort1 OBJECT-TYPE
	SYNTAX  EkiOnOff
	MAX-ACCESS read-only
	STATUS current
	DESCRIPTION
        "
        Previous 15-min EBC counter inv. 
        :This OID indicates that the previous 
        15-min Coding Violation counter 
        is invalid
        "
	::= { pmcryptoPerfTelecomLinePostFecPast15StatHistoryPort1Entry 2 }


pmcryptoPerfTelecomLinePostFecPast15StatHistoryCvValuePort1 OBJECT-TYPE
	SYNTAX  Unsigned32
	MAX-ACCESS read-only
	STATUS current
	DESCRIPTION
        "
        Previous 15-min EBC counter :This 
        OID gives the previous 15-min Coding 
        Violation counter value
        "
	::= { pmcryptoPerfTelecomLinePostFecPast15StatHistoryPort1Entry 3 }


pmcryptoPerfTelecomLinePostFecPast15StatHistoryInvEsPort1 OBJECT-TYPE
	SYNTAX  EkiOnOff
	MAX-ACCESS read-only
	STATUS current
	DESCRIPTION
        "
        Previous 15-min ES counter inv. 
        :This OID indicates that the previous 
        15-min Errored Second counter is 
        invalid
        "
	::= { pmcryptoPerfTelecomLinePostFecPast15StatHistoryPort1Entry 4 }


pmcryptoPerfTelecomLinePostFecPast15StatHistoryEsValuePort1 OBJECT-TYPE
	SYNTAX  Unsigned32
	MAX-ACCESS read-only
	STATUS current
	DESCRIPTION
        "
        Previous 15-min ES counter :This 
        OID gives the previous 15-min Errored 
        Second counter value
        "
	::= { pmcryptoPerfTelecomLinePostFecPast15StatHistoryPort1Entry 5 }


pmcryptoPerfTelecomLinePostFecPast15StatHistoryInvSesPort1 OBJECT-TYPE
	SYNTAX  EkiOnOff
	MAX-ACCESS read-only
	STATUS current
	DESCRIPTION
        "
        Previous 15-min SES counter inv. 
        :This OID indicates that the previous 
        15-min severely Errored Second
         counter is invalid
        "
	::= { pmcryptoPerfTelecomLinePostFecPast15StatHistoryPort1Entry 6 }


pmcryptoPerfTelecomLinePostFecPast15StatHistorySesValuePort1 OBJECT-TYPE
	SYNTAX  Unsigned32
	MAX-ACCESS read-only
	STATUS current
	DESCRIPTION
        "
        Previous 15-min SES counter :This 
        OID gives the previous 15-min severely 
        Errored Second counter value
        "
	::= { pmcryptoPerfTelecomLinePostFecPast15StatHistoryPort1Entry 7 }


pmcryptoPerfTelecomLinePostFecPast15StatHistoryInvSefsPort1 OBJECT-TYPE
	SYNTAX  EkiOnOff
	MAX-ACCESS read-only
	STATUS current
	DESCRIPTION
        "
        Previous 15-min SEFS counter inv. 
        :This OID indicates that the previous 
        15-min severely Errored Framing 
        Second counter is invalid
        "
	::= { pmcryptoPerfTelecomLinePostFecPast15StatHistoryPort1Entry 8 }


pmcryptoPerfTelecomLinePostFecPast15StatHistorySefsValuePort1 OBJECT-TYPE
	SYNTAX  Unsigned32
	MAX-ACCESS read-only
	STATUS current
	DESCRIPTION
        "
        Previous 15-min SEFS counter :This 
        OID gives the previous 15-min severely 
        Errored Framing Second counter
         value
        "
	::= { pmcryptoPerfTelecomLinePostFecPast15StatHistoryPort1Entry 9 }


pmcryptoPerfTelecomLinePostFecPast15StatHistoryInvUasPort1 OBJECT-TYPE
	SYNTAX  EkiOnOff
	MAX-ACCESS read-only
	STATUS current
	DESCRIPTION
        "
        Previous 15-min UAS counter inv. 
        :This OID indicates that the previous 
        15-min UnAvailable Second counter 
        is invalid
        "
	::= { pmcryptoPerfTelecomLinePostFecPast15StatHistoryPort1Entry 10 }


pmcryptoPerfTelecomLinePostFecPast15StatHistoryUasValuePort1 OBJECT-TYPE
	SYNTAX  Unsigned32
	MAX-ACCESS read-only
	STATUS current
	DESCRIPTION
        "
        Previous 15-min UAS counter :This 
        OID gives the previous 15-min UnAvailable 
        Second counter value
        "
	::= { pmcryptoPerfTelecomLinePostFecPast15StatHistoryPort1Entry 11 }


--- *****************************************************
---     Leaf of the telecomLinePostFecCurrent24Stat
--- *****************************************************
--- *********************************************************
---     TABLE for the pmcryptoPerfTelecomLinePostFecCurrent24Stat articles
--- *********************************************************

pmcryptoPerfTelecomLinePostFecCurrent24StatTable OBJECT-TYPE
	SYNTAX  SEQUENCE OF PmcryptoPerfTelecomLinePostFecCurrent24StatEntry
	MAX-ACCESS not-accessible
	STATUS current
	DESCRIPTION
        "
        List of pmcryptoPerfTelecomLinePostFecCurrent24Stat 
        Article
        "
	::= { pmcryptoMonPerfLine 338 }


pmcryptoPerfTelecomLinePostFecCurrent24StatEntry OBJECT-TYPE
	SYNTAX PmcryptoPerfTelecomLinePostFecCurrent24StatEntry
	MAX-ACCESS not-accessible
	STATUS current
	DESCRIPTION
        "
        Row definition for the pmcryptoPerfTelecomLinePostFecCurrent24Stat 
        table
        "
	INDEX   { pmcryptoPerfTelecomLinePostFecCurrent24StatIndex }
	::= { pmcryptoPerfTelecomLinePostFecCurrent24StatTable 1 }


PmcryptoPerfTelecomLinePostFecCurrent24StatEntry ::=
	SEQUENCE {
	pmcryptoPerfTelecomLinePostFecCurrent24StatIndex
		INTEGER,
	pmcryptoPerfTelecomLinePostFecCurrent24StatInvCvPortn
		EkiOnOff,
	pmcryptoPerfTelecomLinePostFecCurrent24StatCvValuePortn
		Unsigned32,
	pmcryptoPerfTelecomLinePostFecCurrent24StatInvEsPortn
		EkiOnOff,
	pmcryptoPerfTelecomLinePostFecCurrent24StatEsValuePortn
		Unsigned32,
	pmcryptoPerfTelecomLinePostFecCurrent24StatInvSesPortn
		EkiOnOff,
	pmcryptoPerfTelecomLinePostFecCurrent24StatSesValuePortn
		Unsigned32,
	pmcryptoPerfTelecomLinePostFecCurrent24StatInvSefsPortn
		EkiOnOff,
	pmcryptoPerfTelecomLinePostFecCurrent24StatSefsValuePortn
		Unsigned32,
	pmcryptoPerfTelecomLinePostFecCurrent24StatInvUasPortn
		EkiOnOff,
	pmcryptoPerfTelecomLinePostFecCurrent24StatUasValuePortn
		Unsigned32
	}


pmcryptoPerfTelecomLinePostFecCurrent24StatIndex OBJECT-TYPE
	SYNTAX  INTEGER(0..128)
	MAX-ACCESS  read-only
	STATUS current
	DESCRIPTION
        "
        Index definition for the pmcryptoPerfTelecomLinePostFecCurrent24Stat 
        table
        "
	::= { pmcryptoPerfTelecomLinePostFecCurrent24StatEntry 1 }


pmcryptoPerfTelecomLinePostFecCurrent24StatInvCvPortn OBJECT-TYPE
	SYNTAX  EkiOnOff
	MAX-ACCESS read-only
	STATUS current
	DESCRIPTION
        "
        Current 24-hours EBC counter inv. 
        :This OID indicates that the current 
        24-hours Coding Violation counter 
        is invalid
        "
	::= { pmcryptoPerfTelecomLinePostFecCurrent24StatEntry 2 }


pmcryptoPerfTelecomLinePostFecCurrent24StatCvValuePortn OBJECT-TYPE
	SYNTAX  Unsigned32
	MAX-ACCESS read-only
	STATUS current
	DESCRIPTION
        "
        Current 24-hours EBC counter :This 
        OID gives the current 24-hours
         Coding Violation counter value
        "
	::= { pmcryptoPerfTelecomLinePostFecCurrent24StatEntry 3 }


pmcryptoPerfTelecomLinePostFecCurrent24StatInvEsPortn OBJECT-TYPE
	SYNTAX  EkiOnOff
	MAX-ACCESS read-only
	STATUS current
	DESCRIPTION
        "
        Current 24-hours ES counter inv. 
        :This OID indicates that the current 
        24-hours Errored Second counter 
        is invalid
        "
	::= { pmcryptoPerfTelecomLinePostFecCurrent24StatEntry 4 }


pmcryptoPerfTelecomLinePostFecCurrent24StatEsValuePortn OBJECT-TYPE
	SYNTAX  Unsigned32
	MAX-ACCESS read-only
	STATUS current
	DESCRIPTION
        "
        Current 24-hours ES counter :This 
        OID gives the current 24-hours
         Errored Second counter value
        "
	::= { pmcryptoPerfTelecomLinePostFecCurrent24StatEntry 5 }


pmcryptoPerfTelecomLinePostFecCurrent24StatInvSesPortn OBJECT-TYPE
	SYNTAX  EkiOnOff
	MAX-ACCESS read-only
	STATUS current
	DESCRIPTION
        "
        Current 24-hours SES counter inv. 
        :This OID indicates that the current 
        24-hours severely Errored Second 
        counter is invalid
        "
	::= { pmcryptoPerfTelecomLinePostFecCurrent24StatEntry 6 }


pmcryptoPerfTelecomLinePostFecCurrent24StatSesValuePortn OBJECT-TYPE
	SYNTAX  Unsigned32
	MAX-ACCESS read-only
	STATUS current
	DESCRIPTION
        "
        Current 24-hours SES counter :This 
        OID gives the current 24-hours
         severely Errored Second counter 
        value
        "
	::= { pmcryptoPerfTelecomLinePostFecCurrent24StatEntry 7 }


pmcryptoPerfTelecomLinePostFecCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter 
        is invalid
        "
	::= { pmcryptoPerfTelecomLinePostFecCurrent24StatEntry 8 }


pmcryptoPerfTelecomLinePostFecCurrent24StatSefsValuePortn OBJECT-TYPE
	SYNTAX  Unsigned32
	MAX-ACCESS read-only
	STATUS current
	DESCRIPTION
        "
        Current 24-hours SEFS counter
         :This OID gives the current 24-hours 
        severely Errored Framing Second 
        counter value
        "
	::= { pmcryptoPerfTelecomLinePostFecCurrent24StatEntry 9 }


pmcryptoPerfTelecomLinePostFecCurrent24StatInvUasPortn OBJECT-TYPE
	SYNTAX  EkiOnOff
	MAX-ACCESS read-only
	STATUS current
	DESCRIPTION
        "
        Current 24-hours UAS counter inv. 
        :This OID indicates that the current 
        24-hours UnAvailable Second counter 
        is invalid
        "
	::= { pmcryptoPerfTelecomLinePostFecCurrent24StatEntry 10 }


pmcryptoPerfTelecomLinePostFecCurrent24StatUasValuePortn OBJECT-TYPE
	SYNTAX  Unsigned32
	MAX-ACCESS read-only
	STATUS current
	DESCRIPTION
        "
        Current 24-hours UAS counter :This 
        OID gives the current 24-hours
         UnAvailable Second counter value
        "
	::= { pmcryptoPerfTelecomLinePostFecCurrent24StatEntry 11 }


--- *****************************************************
---     Leaf of the telecomLinePostFecPast24Stat
--- *****************************************************
--- *********************************************************
---     TABLE for the pmcryptoPerfTelecomLinePostFecPast24StatHistory articles
--- *********************************************************

pmcryptoPerfTelecomLinePostFecPast24StatHistoryPort1Table OBJECT-TYPE
	SYNTAX  SEQUENCE OF PmcryptoPerfTelecomLinePostFecPast24StatHistoryPort1Entry
	MAX-ACCESS not-accessible
	STATUS current
	DESCRIPTION
        "
        List of pmcryptoPerfTelecomLinePostFecPast24StatHistory 
        Article
        "
	::= { pmcryptoMonPerfLine 339 }


pmcryptoPerfTelecomLinePostFecPast24StatHistoryPort1Entry OBJECT-TYPE
	SYNTAX PmcryptoPerfTelecomLinePostFecPast24StatHistoryPort1Entry
	MAX-ACCESS not-accessible
	STATUS current
	DESCRIPTION
        "
        Row definition for the pmcryptoPerfTelecomLinePostFecPast24StatHistory 
        table
        "
	INDEX   { pmcryptoPerfTelecomLinePostFecPast24StatHistoryPort1Index }
	::= { pmcryptoPerfTelecomLinePostFecPast24StatHistoryPort1Table 1 }


PmcryptoPerfTelecomLinePostFecPast24StatHistoryPort1Entry ::=
	SEQUENCE {
	pmcryptoPerfTelecomLinePostFecPast24StatHistoryPort1Index
		INTEGER,
	pmcryptoPerfTelecomLinePostFecPast24StatHistoryInvCvPort1
		EkiOnOff,
	pmcryptoPerfTelecomLinePostFecPast24StatHistoryCvValuePort1
		Unsigned32,
	pmcryptoPerfTelecomLinePostFecPast24StatHistoryInvEsPort1
		EkiOnOff,
	pmcryptoPerfTelecomLinePostFecPast24StatHistoryEsValuePort1
		Unsigned32,
	pmcryptoPerfTelecomLinePostFecPast24StatHistoryInvSesPort1
		EkiOnOff,
	pmcryptoPerfTelecomLinePostFecPast24StatHistorySesValuePort1
		Unsigned32,
	pmcryptoPerfTelecomLinePostFecPast24StatHistoryInvSefsPort1
		EkiOnOff,
	pmcryptoPerfTelecomLinePostFecPast24StatHistorySefsValuePort1
		Unsigned32,
	pmcryptoPerfTelecomLinePostFecPast24StatHistoryInvUasPort1
		EkiOnOff,
	pmcryptoPerfTelecomLinePostFecPast24StatHistoryUasValuePort1
		Unsigned32
	}


pmcryptoPerfTelecomLinePostFecPast24StatHistoryPort1Index OBJECT-TYPE
	SYNTAX  INTEGER(0..128)
	MAX-ACCESS  read-only
	STATUS current
	DESCRIPTION
        "
        Index definition for the pmcryptoPerfTelecomLinePostFecPast24StatHistory 
        table
        "
	::= { pmcryptoPerfTelecomLinePostFecPast24StatHistoryPort1Entry 1 }


pmcryptoPerfTelecomLinePostFecPast24StatHistoryInvCvPort1 OBJECT-TYPE
	SYNTAX  EkiOnOff
	MAX-ACCESS read-only
	STATUS current
	DESCRIPTION
        "
        Previous 24-hours EBC counter
         inv. :This OID indicates that
         the previous 24-hours Coding Violation 
        counter is invalid
        "
	::= { pmcryptoPerfTelecomLinePostFecPast24StatHistoryPort1Entry 2 }


pmcryptoPerfTelecomLinePostFecPast24StatHistoryCvValuePort1 OBJECT-TYPE
	SYNTAX  Unsigned32
	MAX-ACCESS read-only
	STATUS current
	DESCRIPTION
        "
        Previous 24-hours EBC counter
         :This OID gives the previous 24-hours 
        Coding Violation counter value
        "
	::= { pmcryptoPerfTelecomLinePostFecPast24StatHistoryPort1Entry 3 }


pmcryptoPerfTelecomLinePostFecPast24StatHistoryInvEsPort1 OBJECT-TYPE
	SYNTAX  EkiOnOff
	MAX-ACCESS read-only
	STATUS current
	DESCRIPTION
        "
        Previous 24-hours ES counter inv. 
        :This OID indicates that the previous 
        24-hours Errored Second counter 
        is invalid
        "
	::= { pmcryptoPerfTelecomLinePostFecPast24StatHistoryPort1Entry 4 }


pmcryptoPerfTelecomLinePostFecPast24StatHistoryEsValuePort1 OBJECT-TYPE
	SYNTAX  Unsigned32
	MAX-ACCESS read-only
	STATUS current
	DESCRIPTION
        "
        Previous 24-hours ES counter :This 
        OID gives the previous 24-hours 
        Errored Second counter value
        "
	::= { pmcryptoPerfTelecomLinePostFecPast24StatHistoryPort1Entry 5 }


pmcryptoPerfTelecomLinePostFecPast24StatHistoryInvSesPort1 OBJECT-TYPE
	SYNTAX  EkiOnOff
	MAX-ACCESS read-only
	STATUS current
	DESCRIPTION
        "
        Previous 24-hours SES counter
         inv. :This OID indicates that
         the previous 24-hours severely 
        Errored Second counter is invalid
        "
	::= { pmcryptoPerfTelecomLinePostFecPast24StatHistoryPort1Entry 6 }


pmcryptoPerfTelecomLinePostFecPast24StatHistorySesValuePort1 OBJECT-TYPE
	SYNTAX  Unsigned32
	MAX-ACCESS read-only
	STATUS current
	DESCRIPTION
        "
        Previous 24-hours SES counter
         :This OID gives the previous 24-hours 
        severely Errored Second counter 
        value
        "
	::= { pmcryptoPerfTelecomLinePostFecPast24StatHistoryPort1Entry 7 }


pmcryptoPerfTelecomLinePostFecPast24StatHistoryInvSefsPort1 OBJECT-TYPE
	SYNTAX  EkiOnOff
	MAX-ACCESS read-only
	STATUS current
	DESCRIPTION
        "
        Previous 24-hours SEFS counter 
        inv. :This OID indicates that the 
        previous 24-hours severely Errored 
        Framing Second counter is invalid
        "
	::= { pmcryptoPerfTelecomLinePostFecPast24StatHistoryPort1Entry 8 }


pmcryptoPerfTelecomLinePostFecPast24StatHistorySefsValuePort1 OBJECT-TYPE
	SYNTAX  Unsigned32
	MAX-ACCESS read-only
	STATUS current
	DESCRIPTION
        "
        Previous 24-hours SEFS counter 
        :This OID gives the previous 24-hours 
        severely Errored Framing Second 
        counter value
        "
	::= { pmcryptoPerfTelecomLinePostFecPast24StatHistoryPort1Entry 9 }


pmcryptoPerfTelecomLinePostFecPast24StatHistoryInvUasPort1 OBJECT-TYPE
	SYNTAX  EkiOnOff
	MAX-ACCESS read-only
	STATUS current
	DESCRIPTION
        "
        Previous 24-hours UAS counter
         inv. :This OID indicates that
         the previous 24-hours UnAvailable 
        Second counter is invalid
        "
	::= { pmcryptoPerfTelecomLinePostFecPast24StatHistoryPort1Entry 10 }


pmcryptoPerfTelecomLinePostFecPast24StatHistoryUasValuePort1 OBJECT-TYPE
	SYNTAX  Unsigned32
	MAX-ACCESS read-only
	STATUS current
	DESCRIPTION
        "
        Previous 24-hours UAS counter
         :This OID gives the previous 24-hours 
        UnAvailable Second counter value
        "
	::= { pmcryptoPerfTelecomLinePostFecPast24StatHistoryPort1Entry 11 }


--- *****************************************************
---     Leaf of the telecomBerLinePreFecCurrent15Stat
--- *****************************************************
--- *********************************************************
---     TABLE for the pmcryptoPerfTelecomBerLinePreFecCurrent15Stat articles
--- *********************************************************

pmcryptoPerfTelecomBerLinePreFecCurrent15StatTable OBJECT-TYPE
	SYNTAX  SEQUENCE OF PmcryptoPerfTelecomBerLinePreFecCurrent15StatEntry
	MAX-ACCESS not-accessible
	STATUS current
	DESCRIPTION
        "
        List of pmcryptoPerfTelecomBerLinePreFecCurrent15Stat 
        Article
        "
	::= { pmcryptoMonPerfLine 352 }


pmcryptoPerfTelecomBerLinePreFecCurrent15StatEntry OBJECT-TYPE
	SYNTAX PmcryptoPerfTelecomBerLinePreFecCurrent15StatEntry
	MAX-ACCESS not-accessible
	STATUS current
	DESCRIPTION
        "
        Row definition for the pmcryptoPerfTelecomBerLinePreFecCurrent15Stat 
        table
        "
	INDEX   { pmcryptoPerfTelecomBerLinePreFecCurrent15StatIndex }
	::= { pmcryptoPerfTelecomBerLinePreFecCurrent15StatTable 1 }


PmcryptoPerfTelecomBerLinePreFecCurrent15StatEntry ::=
	SEQUENCE {
	pmcryptoPerfTelecomBerLinePreFecCurrent15StatIndex
		INTEGER,
	pmcryptoPerfTelecomBerLinePreFecCurrent15StatInvBerPortn
		EkiOnOff,
	pmcryptoPerfTelecomBerLinePreFecCurrent15StatBerValuePortn
		Unsigned32,
	pmcryptoPerfTelecomBerLinePreFecCurrent15StatInvMinBerPortn
		EkiOnOff,
	pmcryptoPerfTelecomBerLinePreFecCurrent15StatMinBerValuePortn
		Unsigned32,
	pmcryptoPerfTelecomBerLinePreFecCurrent15StatInvMaxBerPortn
		EkiOnOff,
	pmcryptoPerfTelecomBerLinePreFecCurrent15StatMaxBerValuePortn
		Unsigned32
	}


pmcryptoPerfTelecomBerLinePreFecCurrent15StatIndex OBJECT-TYPE
	SYNTAX  INTEGER(0..128)
	MAX-ACCESS  read-only
	STATUS current
	DESCRIPTION
        "
        Index definition for the pmcryptoPerfTelecomBerLinePreFecCurrent15Stat 
        table
        "
	::= { pmcryptoPerfTelecomBerLinePreFecCurrent15StatEntry 1 }


pmcryptoPerfTelecomBerLinePreFecCurrent15StatInvBerPortn OBJECT-TYPE
	SYNTAX  EkiOnOff
	MAX-ACCESS read-only
	STATUS current
	DESCRIPTION
        "
        Current 15-min BER counter inv. 
        :This OID indicates that the current 
        15-min Coding Violation counter 
        is invalid
        "
	::= { pmcryptoPerfTelecomBerLinePreFecCurrent15StatEntry 2 }


pmcryptoPerfTelecomBerLinePreFecCurrent15StatBerValuePortn OBJECT-TYPE
	SYNTAX  Unsigned32
	MAX-ACCESS read-only
	STATUS current
	DESCRIPTION
        "
        Current 15-min BER counter :This 
        OID gives the current 15-min Coding 
        Violation counter value
        "
	::= { pmcryptoPerfTelecomBerLinePreFecCurrent15StatEntry 3 }


pmcryptoPerfTelecomBerLinePreFecCurrent15StatInvMinBerPortn OBJECT-TYPE
	SYNTAX  EkiOnOff
	MAX-ACCESS read-only
	STATUS current
	DESCRIPTION
        "
        Current 15-min MinBER counter
         inv. :This OID indicates that
         the current 15-min Errored Second 
        counter is invalid
        "
	::= { pmcryptoPerfTelecomBerLinePreFecCurrent15StatEntry 4 }


pmcryptoPerfTelecomBerLinePreFecCurrent15StatMinBerValuePortn OBJECT-TYPE
	SYNTAX  Unsigned32
	MAX-ACCESS read-only
	STATUS current
	DESCRIPTION
        "
        Current 15-min MinBER counter
         :This OID gives the current 15-min 
        Errored Second counter value
        "
	::= { pmcryptoPerfTelecomBerLinePreFecCurrent15StatEntry 5 }


pmcryptoPerfTelecomBerLinePreFecCurrent15StatInvMaxBerPortn OBJECT-TYPE
	SYNTAX  EkiOnOff
	MAX-ACCESS read-only
	STATUS current
	DESCRIPTION
        "
        Current 15-min MaxBER counter
         inv. :This OID indicates that
         the current 15-min severely Errored 
        Second counter is invalid
        "
	::= { pmcryptoPerfTelecomBerLinePreFecCurrent15StatEntry 6 }


pmcryptoPerfTelecomBerLinePreFecCurrent15StatMaxBerValuePortn OBJECT-TYPE
	SYNTAX  Unsigned32
	MAX-ACCESS read-only
	STATUS current
	DESCRIPTION
        "
        Current 15-min MaxBER counter
         :This OID gives the current 15-min 
        severely Errored Second counter 
        value
        "
	::= { pmcryptoPerfTelecomBerLinePreFecCurrent15StatEntry 7 }


--- *****************************************************
---     Leaf of the telecomBerLinePreFecPast15Stat
--- *****************************************************
--- *********************************************************
---     TABLE for the pmcryptoPerfTelecomBerLinePreFecPast15StatHistory articles
--- *********************************************************

pmcryptoPerfTelecomBerLinePreFecPast15StatHistoryPort1Table OBJECT-TYPE
	SYNTAX  SEQUENCE OF PmcryptoPerfTelecomBerLinePreFecPast15StatHistoryPort1Entry
	MAX-ACCESS not-accessible
	STATUS current
	DESCRIPTION
        "
        List of pmcryptoPerfTelecomBerLinePreFecPast15StatHistory 
        Article
        "
	::= { pmcryptoMonPerfLine 353 }


pmcryptoPerfTelecomBerLinePreFecPast15StatHistoryPort1Entry OBJECT-TYPE
	SYNTAX PmcryptoPerfTelecomBerLinePreFecPast15StatHistoryPort1Entry
	MAX-ACCESS not-accessible
	STATUS current
	DESCRIPTION
        "
        Row definition for the pmcryptoPerfTelecomBerLinePreFecPast15StatHistory 
        table
        "
	INDEX   { pmcryptoPerfTelecomBerLinePreFecPast15StatHistoryPort1Index }
	::= { pmcryptoPerfTelecomBerLinePreFecPast15StatHistoryPort1Table 1 }


PmcryptoPerfTelecomBerLinePreFecPast15StatHistoryPort1Entry ::=
	SEQUENCE {
	pmcryptoPerfTelecomBerLinePreFecPast15StatHistoryPort1Index
		INTEGER,
	pmcryptoPerfTelecomBerLinePreFecPast15StatHistoryInvBerPort1
		EkiOnOff,
	pmcryptoPerfTelecomBerLinePreFecPast15StatHistoryBerValuePort1
		Unsigned32,
	pmcryptoPerfTelecomBerLinePreFecPast15StatHistoryInvMinBerPort1
		EkiOnOff,
	pmcryptoPerfTelecomBerLinePreFecPast15StatHistoryMinBerValuePort1
		Unsigned32,
	pmcryptoPerfTelecomBerLinePreFecPast15StatHistoryInvMaxBerPort1
		EkiOnOff,
	pmcryptoPerfTelecomBerLinePreFecPast15StatHistoryMaxBerValuePort1
		Unsigned32
	}


pmcryptoPerfTelecomBerLinePreFecPast15StatHistoryPort1Index OBJECT-TYPE
	SYNTAX  INTEGER(0..128)
	MAX-ACCESS  read-only
	STATUS current
	DESCRIPTION
        "
        Index definition for the pmcryptoPerfTelecomBerLinePreFecPast15StatHistory 
        table
        "
	::= { pmcryptoPerfTelecomBerLinePreFecPast15StatHistoryPort1Entry 1 }


pmcryptoPerfTelecomBerLinePreFecPast15StatHistoryInvBerPort1 OBJECT-TYPE
	SYNTAX  EkiOnOff
	MAX-ACCESS read-only
	STATUS current
	DESCRIPTION
        "
        Previous 15-min BER counter inv. 
        :This OID indicates that the previous 
        15-min Coding Violation counter 
        is invalid
        "
	::= { pmcryptoPerfTelecomBerLinePreFecPast15StatHistoryPort1Entry 2 }


pmcryptoPerfTelecomBerLinePreFecPast15StatHistoryBerValuePort1 OBJECT-TYPE
	SYNTAX  Unsigned32
	MAX-ACCESS read-only
	STATUS current
	DESCRIPTION
        "
        Previous 15-min BER counter :This 
        OID gives the previous 15-min Coding 
        Violation counter value
        "
	::= { pmcryptoPerfTelecomBerLinePreFecPast15StatHistoryPort1Entry 3 }


pmcryptoPerfTelecomBerLinePreFecPast15StatHistoryInvMinBerPort1 OBJECT-TYPE
	SYNTAX  EkiOnOff
	MAX-ACCESS read-only
	STATUS current
	DESCRIPTION
        "
        Previous 15-min MinBER counter 
        inv. :This OID indicates that the 
        previous 15-min Errored Second
         counter is invalid
        "
	::= { pmcryptoPerfTelecomBerLinePreFecPast15StatHistoryPort1Entry 4 }


pmcryptoPerfTelecomBerLinePreFecPast15StatHistoryMinBerValuePort1 OBJECT-TYPE
	SYNTAX  Unsigned32
	MAX-ACCESS read-only
	STATUS current
	DESCRIPTION
        "
        Previous 15-min MinBER counter 
        :This OID gives the previous 15-min 
        Errored Second counter value
        "
	::= { pmcryptoPerfTelecomBerLinePreFecPast15StatHistoryPort1Entry 5 }


pmcryptoPerfTelecomBerLinePreFecPast15StatHistoryInvMaxBerPort1 OBJECT-TYPE
	SYNTAX  EkiOnOff
	MAX-ACCESS read-only
	STATUS current
	DESCRIPTION
        "
        Previous 15-min MaxBER counter 
        inv. :This OID indicates that the 
        previous 15-min severely Errored 
        Second counter is invalid
        "
	::= { pmcryptoPerfTelecomBerLinePreFecPast15StatHistoryPort1Entry 6 }


pmcryptoPerfTelecomBerLinePreFecPast15StatHistoryMaxBerValuePort1 OBJECT-TYPE
	SYNTAX  Unsigned32
	MAX-ACCESS read-only
	STATUS current
	DESCRIPTION
        "
        Previous 15-min MaxBER counter 
        :This OID gives the previous 15-min 
        severely Errored Second counter 
        value
        "
	::= { pmcryptoPerfTelecomBerLinePreFecPast15StatHistoryPort1Entry 7 }


--- *****************************************************
---     Leaf of the telecomBerLinePreFecCurrent24Stat
--- *****************************************************
--- *********************************************************
---     TABLE for the pmcryptoPerfTelecomBerLinePreFecCurrent24Stat articles
--- *********************************************************

pmcryptoPerfTelecomBerLinePreFecCurrent24StatTable OBJECT-TYPE
	SYNTAX  SEQUENCE OF PmcryptoPerfTelecomBerLinePreFecCurrent24StatEntry
	MAX-ACCESS not-accessible
	STATUS current
	DESCRIPTION
        "
        List of pmcryptoPerfTelecomBerLinePreFecCurrent24Stat 
        Article
        "
	::= { pmcryptoMonPerfLine 354 }


pmcryptoPerfTelecomBerLinePreFecCurrent24StatEntry OBJECT-TYPE
	SYNTAX PmcryptoPerfTelecomBerLinePreFecCurrent24StatEntry
	MAX-ACCESS not-accessible
	STATUS current
	DESCRIPTION
        "
        Row definition for the pmcryptoPerfTelecomBerLinePreFecCurrent24Stat 
        table
        "
	INDEX   { pmcryptoPerfTelecomBerLinePreFecCurrent24StatIndex }
	::= { pmcryptoPerfTelecomBerLinePreFecCurrent24StatTable 1 }


PmcryptoPerfTelecomBerLinePreFecCurrent24StatEntry ::=
	SEQUENCE {
	pmcryptoPerfTelecomBerLinePreFecCurrent24StatIndex
		INTEGER,
	pmcryptoPerfTelecomBerLinePreFecCurrent24StatInvBerPortn
		EkiOnOff,
	pmcryptoPerfTelecomBerLinePreFecCurrent24StatBerValuePortn
		Unsigned32,
	pmcryptoPerfTelecomBerLinePreFecCurrent24StatInvMinBerPortn
		EkiOnOff,
	pmcryptoPerfTelecomBerLinePreFecCurrent24StatMinBerValuePortn
		Unsigned32,
	pmcryptoPerfTelecomBerLinePreFecCurrent24StatInvMaxBerPortn
		EkiOnOff,
	pmcryptoPerfTelecomBerLinePreFecCurrent24StatMaxBerValuePortn
		Unsigned32
	}


pmcryptoPerfTelecomBerLinePreFecCurrent24StatIndex OBJECT-TYPE
	SYNTAX  INTEGER(0..128)
	MAX-ACCESS  read-only
	STATUS current
	DESCRIPTION
        "
        Index definition for the pmcryptoPerfTelecomBerLinePreFecCurrent24Stat 
        table
        "
	::= { pmcryptoPerfTelecomBerLinePreFecCurrent24StatEntry 1 }


pmcryptoPerfTelecomBerLinePreFecCurrent24StatInvBerPortn OBJECT-TYPE
	SYNTAX  EkiOnOff
	MAX-ACCESS read-only
	STATUS current
	DESCRIPTION
        "
        Current 24-hours BER counter inv. 
        :This OID indicates that the current 
        24-hours Coding Violation counter 
        is invalid
        "
	::= { pmcryptoPerfTelecomBerLinePreFecCurrent24StatEntry 2 }


pmcryptoPerfTelecomBerLinePreFecCurrent24StatBerValuePortn OBJECT-TYPE
	SYNTAX  Unsigned32
	MAX-ACCESS read-only
	STATUS current
	DESCRIPTION
        "
        Current 24-hours BER counter :This 
        OID gives the current 24-hours
         Coding Violation counter value
        "
	::= { pmcryptoPerfTelecomBerLinePreFecCurrent24StatEntry 3 }


pmcryptoPerfTelecomBerLinePreFecCurrent24StatInvMinBerPortn OBJECT-TYPE
	SYNTAX  EkiOnOff
	MAX-ACCESS read-only
	STATUS current
	DESCRIPTION
        "
        Current 24-hoursMinBER counter 
        inv. :This OID indicates that the 
        current 24-hours Errored Second 
        counter is invalid
        "
	::= { pmcryptoPerfTelecomBerLinePreFecCurrent24StatEntry 4 }


pmcryptoPerfTelecomBerLinePreFecCurrent24StatMinBerValuePortn OBJECT-TYPE
	SYNTAX  Unsigned32
	MAX-ACCESS read-only
	STATUS current
	DESCRIPTION
        "
        Current 24-hours MinBER counter 
        :This OID gives the current 24-hours 
        Errored Second counter value
        "
	::= { pmcryptoPerfTelecomBerLinePreFecCurrent24StatEntry 5 }


pmcryptoPerfTelecomBerLinePreFecCurrent24StatInvMaxBerPortn OBJECT-TYPE
	SYNTAX  EkiOnOff
	MAX-ACCESS read-only
	STATUS current
	DESCRIPTION
        "
        Current 24-hours MaxBER counter 
        inv. :This OID indicates that the 
        current 24-hours severely Errored 
        Second counter is invalid
        "
	::= { pmcryptoPerfTelecomBerLinePreFecCurrent24StatEntry 6 }


pmcryptoPerfTelecomBerLinePreFecCurrent24StatMaxBerValuePortn OBJECT-TYPE
	SYNTAX  Unsigned32
	MAX-ACCESS read-only
	STATUS current
	DESCRIPTION
        "
        Current 24-hours MaxBER counter 
        :This OID gives the current 24-hours 
        severely Errored Second counter 
        value
        "
	::= { pmcryptoPerfTelecomBerLinePreFecCurrent24StatEntry 7 }


--- *****************************************************
---     Leaf of the telecomBerLinePreFecPast24Stat
--- *****************************************************
--- *********************************************************
---     TABLE for the pmcryptoPerfTelecomBerLinePreFecPast24StatHistory articles
--- *********************************************************

pmcryptoPerfTelecomBerLinePreFecPast24StatHistoryPort1Table OBJECT-TYPE
	SYNTAX  SEQUENCE OF PmcryptoPerfTelecomBerLinePreFecPast24StatHistoryPort1Entry
	MAX-ACCESS not-accessible
	STATUS current
	DESCRIPTION
        "
        List of pmcryptoPerfTelecomBerLinePreFecPast24StatHistory 
        Article
        "
	::= { pmcryptoMonPerfLine 355 }


pmcryptoPerfTelecomBerLinePreFecPast24StatHistoryPort1Entry OBJECT-TYPE
	SYNTAX PmcryptoPerfTelecomBerLinePreFecPast24StatHistoryPort1Entry
	MAX-ACCESS not-accessible
	STATUS current
	DESCRIPTION
        "
        Row definition for the pmcryptoPerfTelecomBerLinePreFecPast24StatHistory 
        table
        "
	INDEX   { pmcryptoPerfTelecomBerLinePreFecPast24StatHistoryPort1Index }
	::= { pmcryptoPerfTelecomBerLinePreFecPast24StatHistoryPort1Table 1 }


PmcryptoPerfTelecomBerLinePreFecPast24StatHistoryPort1Entry ::=
	SEQUENCE {
	pmcryptoPerfTelecomBerLinePreFecPast24StatHistoryPort1Index
		INTEGER,
	pmcryptoPerfTelecomBerLinePreFecPast24StatHistoryInvBerPort1
		EkiOnOff,
	pmcryptoPerfTelecomBerLinePreFecPast24StatHistoryBerValuePort1
		Unsigned32,
	pmcryptoPerfTelecomBerLinePreFecPast24StatHistoryInvMinBerPort1
		EkiOnOff,
	pmcryptoPerfTelecomBerLinePreFecPast24StatHistoryMinBerValuePort1
		Unsigned32,
	pmcryptoPerfTelecomBerLinePreFecPast24StatHistoryInvMaxBerPort1
		EkiOnOff,
	pmcryptoPerfTelecomBerLinePreFecPast24StatHistoryMaxBerValuePort1
		Unsigned32
	}


pmcryptoPerfTelecomBerLinePreFecPast24StatHistoryPort1Index OBJECT-TYPE
	SYNTAX  INTEGER(0..128)
	MAX-ACCESS  read-only
	STATUS current
	DESCRIPTION
        "
        Index definition for the pmcryptoPerfTelecomBerLinePreFecPast24StatHistory 
        table
        "
	::= { pmcryptoPerfTelecomBerLinePreFecPast24StatHistoryPort1Entry 1 }


pmcryptoPerfTelecomBerLinePreFecPast24StatHistoryInvBerPort1 OBJECT-TYPE
	SYNTAX  EkiOnOff
	MAX-ACCESS read-only
	STATUS current
	DESCRIPTION
        "
        Previous 24-hours BER counter
         inv. :This OID indicates that
         the previous 24-hours Coding Violation 
        counter is invalid
        "
	::= { pmcryptoPerfTelecomBerLinePreFecPast24StatHistoryPort1Entry 2 }


pmcryptoPerfTelecomBerLinePreFecPast24StatHistoryBerValuePort1 OBJECT-TYPE
	SYNTAX  Unsigned32
	MAX-ACCESS read-only
	STATUS current
	DESCRIPTION
        "
        Previous 24-hours BER counter
         :This OID gives the previous 24-hours 
        Coding Violation counter value
        "
	::= { pmcryptoPerfTelecomBerLinePreFecPast24StatHistoryPort1Entry 3 }


pmcryptoPerfTelecomBerLinePreFecPast24StatHistoryInvMinBerPort1 OBJECT-TYPE
	SYNTAX  EkiOnOff
	MAX-ACCESS read-only
	STATUS current
	DESCRIPTION
        "
        Previous 24-hours MinBER counter 
        inv. :This OID indicates that the 
        previous 24-hours Errored Second 
        counter is invalid
        "
	::= { pmcryptoPerfTelecomBerLinePreFecPast24StatHistoryPort1Entry 4 }


pmcryptoPerfTelecomBerLinePreFecPast24StatHistoryMinBerValuePort1 OBJECT-TYPE
	SYNTAX  Unsigned32
	MAX-ACCESS read-only
	STATUS current
	DESCRIPTION
        "
        Previous 24-hours MinBER counter 
        :This OID gives the previous 24-hours 
        Errored Second counter value
        "
	::= { pmcryptoPerfTelecomBerLinePreFecPast24StatHistoryPort1Entry 5 }


pmcryptoPerfTelecomBerLinePreFecPast24StatHistoryInvMaxBerPort1 OBJECT-TYPE
	SYNTAX  EkiOnOff
	MAX-ACCESS read-only
	STATUS current
	DESCRIPTION
        "
        Previous 24-hours MaxBER counter 
        inv. :This OID indicates that the 
        previous 24-hours severely Errored 
        Second counter is invalid
        "
	::= { pmcryptoPerfTelecomBerLinePreFecPast24StatHistoryPort1Entry 6 }


pmcryptoPerfTelecomBerLinePreFecPast24StatHistoryMaxBerValuePort1 OBJECT-TYPE
	SYNTAX  Unsigned32
	MAX-ACCESS read-only
	STATUS current
	DESCRIPTION
        "
        Previous 24-hours MaxBER counter 
        :This OID gives the previous 24-hours 
        severely Errored Second counter 
        value
        "
	::= { pmcryptoPerfTelecomBerLinePreFecPast24StatHistoryPort1Entry 7 }


--- *****************************************************
---     Leaf of the datacomClientCurrent15Stat
--- *****************************************************
--- *********************************************************
---     TABLE for the pmcryptoPerfDatacomClientCurrent15Stat articles
--- *********************************************************

pmcryptoPerfDatacomClientCurrent15StatTable OBJECT-TYPE
	SYNTAX  SEQUENCE OF PmcryptoPerfDatacomClientCurrent15StatEntry
	MAX-ACCESS not-accessible
	STATUS current
	DESCRIPTION
        "
        List of pmcryptoPerfDatacomClientCurrent15Stat 
        Article
        "
	::= { pmcryptoMonPerfClient 848 }


pmcryptoPerfDatacomClientCurrent15StatEntry OBJECT-TYPE
	SYNTAX PmcryptoPerfDatacomClientCurrent15StatEntry
	MAX-ACCESS not-accessible
	STATUS current
	DESCRIPTION
        "
        Row definition for the pmcryptoPerfDatacomClientCurrent15Stat 
        table
        "
	INDEX   { pmcryptoPerfDatacomClientCurrent15StatIndex }
	::= { pmcryptoPerfDatacomClientCurrent15StatTable 1 }


PmcryptoPerfDatacomClientCurrent15StatEntry ::=
	SEQUENCE {
	pmcryptoPerfDatacomClientCurrent15StatIndex
		INTEGER,
	pmcryptoperfdatacomclientCurrent15StatOutPacketCountInvPortn
		EkiOnOff,
	pmcryptoperfdatacomclientCurrent15StatOutPacketCountPortn
		Counter64,
	pmcryptoperfdatacomclientCurrent15StatOutCrcCountInvPortn
		EkiOnOff,
	pmcryptoperfdatacomclientCurrent15StatOutCrcCountPortn
		Counter64,
	pmcryptoperfdatacomclientCurrent15StatInPacketCountInvPortn
		EkiOnOff,
	pmcryptoperfdatacomclientCurrent15StatInPacketCountPortn
		Counter64,
	pmcryptoperfdatacomclientCurrent15StatInCrcCountInvPortn
		EkiOnOff,
	pmcryptoperfdatacomclientCurrent15StatInCrcCountPortn
		Counter64
	}


pmcryptoPerfDatacomClientCurrent15StatIndex OBJECT-TYPE
	SYNTAX  INTEGER(0..128)
	MAX-ACCESS  read-only
	STATUS current
	DESCRIPTION
        "
        Index definition for the pmcryptoPerfDatacomClientCurrent15Stat 
        table
        "
	::= { pmcryptoPerfDatacomClientCurrent15StatEntry 1 }


pmcryptoperfdatacomclientCurrent15StatOutPacketCountInvPortn OBJECT-TYPE
	SYNTAX  EkiOnOff
	MAX-ACCESS read-only
	STATUS current
	DESCRIPTION
        "
        Client Current 15-min Output Packet 
        counter inv. :This OID indicates 
        that the current 15-min Output
         Packets counter is invalid
        "
	::= { pmcryptoPerfDatacomClientCurrent15StatEntry 30 }


pmcryptoperfdatacomclientCurrent15StatOutPacketCountPortn OBJECT-TYPE
	SYNTAX  Counter64
	MAX-ACCESS read-only
	STATUS current
	DESCRIPTION
        "
        Client Current 15-min Output Packet 
        counter :This OID gives the current 
        15-min Output Packets counter value
        "
	::= { pmcryptoPerfDatacomClientCurrent15StatEntry 31 }


pmcryptoperfdatacomclientCurrent15StatOutCrcCountInvPortn OBJECT-TYPE
	SYNTAX  EkiOnOff
	MAX-ACCESS read-only
	STATUS current
	DESCRIPTION
        "
        Client Current 15-min Output CRC 
        counter inv. :This OID indicates 
        that the current 15-min Output
         CRC counter is invalid
        "
	::= { pmcryptoPerfDatacomClientCurrent15StatEntry 28 }


pmcryptoperfdatacomclientCurrent15StatOutCrcCountPortn OBJECT-TYPE
	SYNTAX  Counter64
	MAX-ACCESS read-only
	STATUS current
	DESCRIPTION
        "
        Client Current 15-min Output CRC 
        counter :This OID gives the current 
        15-min Output CRC counter value
        "
	::= { pmcryptoPerfDatacomClientCurrent15StatEntry 29 }


pmcryptoperfdatacomclientCurrent15StatInPacketCountInvPortn OBJECT-TYPE
	SYNTAX  EkiOnOff
	MAX-ACCESS read-only
	STATUS current
	DESCRIPTION
        "
        Client Current 15-min Input Packet 
        counter inv. :This OID indicates 
        that the current 15-min Input Packet 
        counter is invalid
        "
	::= { pmcryptoPerfDatacomClientCurrent15StatEntry 6 }


pmcryptoperfdatacomclientCurrent15StatInPacketCountPortn OBJECT-TYPE
	SYNTAX  Counter64
	MAX-ACCESS read-only
	STATUS current
	DESCRIPTION
        "
        Client Current 15-min Input Packet 
        counter :This OID gives the current 
        15-min Input Packet counter value
        "
	::= { pmcryptoPerfDatacomClientCurrent15StatEntry 7 }


pmcryptoperfdatacomclientCurrent15StatInCrcCountInvPortn OBJECT-TYPE
	SYNTAX  EkiOnOff
	MAX-ACCESS read-only
	STATUS current
	DESCRIPTION
        "
        Client Current 15-min Input CRC 
        counter inv. :This OID indicates 
        that the current 15-min Input CRC 
        counter is invalid
        "
	::= { pmcryptoPerfDatacomClientCurrent15StatEntry 4 }


pmcryptoperfdatacomclientCurrent15StatInCrcCountPortn OBJECT-TYPE
	SYNTAX  Counter64
	MAX-ACCESS read-only
	STATUS current
	DESCRIPTION
        "
        Client Current 15-min Input CRC 
        counter :This OID gives the current 
        15-min Input CRC counter value
        "
	::= { pmcryptoPerfDatacomClientCurrent15StatEntry 5 }


--- *****************************************************
---     Leaf of the datacomClientPast15Stat
--- *****************************************************
--- *********************************************************
---     TABLE for the pmcryptoPerfDatacomClientPast15StatHistory articles
--- *********************************************************

pmcryptoPerfDatacomClientPast15StatHistoryPort1Table OBJECT-TYPE
	SYNTAX  SEQUENCE OF PmcryptoPerfDatacomClientPast15StatHistoryPort1Entry
	MAX-ACCESS not-accessible
	STATUS current
	DESCRIPTION
        "
        List of pmcryptoPerfDatacomClientPast15StatHistory 
        Article
        "
	::= { pmcryptoMonPerfClient 880 }


pmcryptoPerfDatacomClientPast15StatHistoryPort1Entry OBJECT-TYPE
	SYNTAX PmcryptoPerfDatacomClientPast15StatHistoryPort1Entry
	MAX-ACCESS not-accessible
	STATUS current
	DESCRIPTION
        "
        Row definition for the pmcryptoPerfDatacomClientPast15StatHistory 
        table
        "
	INDEX   { pmcryptoPerfDatacomClientPast15StatHistoryPort1Index }
	::= { pmcryptoPerfDatacomClientPast15StatHistoryPort1Table 1 }


PmcryptoPerfDatacomClientPast15StatHistoryPort1Entry ::=
	SEQUENCE {
	pmcryptoPerfDatacomClientPast15StatHistoryPort1Index
		INTEGER,
	pmcryptoperfdatacomclientPast15StatOutPacketCountInvPort1
		EkiOnOff,
	pmcryptoperfdatacomclientPast15StatOutPacketCountPort1
		Counter64,
	pmcryptoperfdatacomclientPast15StatOutCrcCountInvPort1
		EkiOnOff,
	pmcryptoperfdatacomclientPast15StatOutCrcCountPort1
		Counter64,
	pmcryptoperfdatacomclientPast15StatInPacketCountInvPort1
		EkiOnOff,
	pmcryptoperfdatacomclientPast15StatInPacketCountPort1
		Counter64,
	pmcryptoperfdatacomclientPast15StatInCrcCountInvPort1
		EkiOnOff,
	pmcryptoperfdatacomclientPast15StatInCrcCountPort1
		Counter64
	}


pmcryptoPerfDatacomClientPast15StatHistoryPort1Index OBJECT-TYPE
	SYNTAX  INTEGER(0..128)
	MAX-ACCESS  read-only
	STATUS current
	DESCRIPTION
        "
        Index definition for the pmcryptoPerfDatacomClientPast15StatHistory 
        table
        "
	::= { pmcryptoPerfDatacomClientPast15StatHistoryPort1Entry 1 }


pmcryptoperfdatacomclientPast15StatOutPacketCountInvPort1 OBJECT-TYPE
	SYNTAX  EkiOnOff
	MAX-ACCESS read-only
	STATUS current
	DESCRIPTION
        "
        Client Past 15-min Output Packet 
        counter inv. :This OID indicates 
        that the past 15-min Output Packets 
        counter is invalid
        "
	::= { pmcryptoPerfDatacomClientPast15StatHistoryPort1Entry 30 }


pmcryptoperfdatacomclientPast15StatOutPacketCountPort1 OBJECT-TYPE
	SYNTAX  Counter64
	MAX-ACCESS read-only
	STATUS current
	DESCRIPTION
        "
        Client Past 15-min Output Packet 
        counter :This OID gives the past 
        15-min Output Packets counter value
        "
	::= { pmcryptoPerfDatacomClientPast15StatHistoryPort1Entry 31 }


pmcryptoperfdatacomclientPast15StatOutCrcCountInvPort1 OBJECT-TYPE
	SYNTAX  EkiOnOff
	MAX-ACCESS read-only
	STATUS current
	DESCRIPTION
        "
        Client Past 15-min Output CRC
         counter inv. :This OID indicates 
        that the past 15-min Output CRC 
        counter is invalid
        "
	::= { pmcryptoPerfDatacomClientPast15StatHistoryPort1Entry 28 }


pmcryptoperfdatacomclientPast15StatOutCrcCountPort1 OBJECT-TYPE
	SYNTAX  Counter64
	MAX-ACCESS read-only
	STATUS current
	DESCRIPTION
        "
        Client Past 15-min Output CRC
         counter :This OID gives the past 
        15-min Output CRC counter value
        "
	::= { pmcryptoPerfDatacomClientPast15StatHistoryPort1Entry 29 }


pmcryptoperfdatacomclientPast15StatInPacketCountInvPort1 OBJECT-TYPE
	SYNTAX  EkiOnOff
	MAX-ACCESS read-only
	STATUS current
	DESCRIPTION
        "
        Client Past 15-min Input Packet 
        counter inv. :This OID indicates 
        that the past 15-min Input Packet 
        counter is invalid
        "
	::= { pmcryptoPerfDatacomClientPast15StatHistoryPort1Entry 6 }


pmcryptoperfdatacomclientPast15StatInPacketCountPort1 OBJECT-TYPE
	SYNTAX  Counter64
	MAX-ACCESS read-only
	STATUS current
	DESCRIPTION
        "
        Client Past 15-min Input Packet 
        counter :This OID gives the past 
        15-min Input Packet counter value
        "
	::= { pmcryptoPerfDatacomClientPast15StatHistoryPort1Entry 7 }


pmcryptoperfdatacomclientPast15StatInCrcCountInvPort1 OBJECT-TYPE
	SYNTAX  EkiOnOff
	MAX-ACCESS read-only
	STATUS current
	DESCRIPTION
        "
        Client Past 15-min Input CRC counter 
        inv. :This OID indicates that the 
        past 15-min Input CRC counter is 
        invalid
        "
	::= { pmcryptoPerfDatacomClientPast15StatHistoryPort1Entry 4 }


pmcryptoperfdatacomclientPast15StatInCrcCountPort1 OBJECT-TYPE
	SYNTAX  Counter64
	MAX-ACCESS read-only
	STATUS current
	DESCRIPTION
        "
        Client Past 15-min Input CRC counter 
        :This OID gives the past 15-min 
        Input CRC counter value
        "
	::= { pmcryptoPerfDatacomClientPast15StatHistoryPort1Entry 5 }


--- *****************************************************
---     Leaf of the datacomClientCurrent24Stat
--- *****************************************************
--- *********************************************************
---     TABLE for the pmcryptoPerfDatacomClientCurrent24Stat articles
--- *********************************************************

pmcryptoPerfDatacomClientCurrent24StatTable OBJECT-TYPE
	SYNTAX  SEQUENCE OF PmcryptoPerfDatacomClientCurrent24StatEntry
	MAX-ACCESS not-accessible
	STATUS current
	DESCRIPTION
        "
        List of pmcryptoPerfDatacomClientCurrent24Stat 
        Article
        "
	::= { pmcryptoMonPerfClient 912 }


pmcryptoPerfDatacomClientCurrent24StatEntry OBJECT-TYPE
	SYNTAX PmcryptoPerfDatacomClientCurrent24StatEntry
	MAX-ACCESS not-accessible
	STATUS current
	DESCRIPTION
        "
        Row definition for the pmcryptoPerfDatacomClientCurrent24Stat 
        table
        "
	INDEX   { pmcryptoPerfDatacomClientCurrent24StatIndex }
	::= { pmcryptoPerfDatacomClientCurrent24StatTable 1 }


PmcryptoPerfDatacomClientCurrent24StatEntry ::=
	SEQUENCE {
	pmcryptoPerfDatacomClientCurrent24StatIndex
		INTEGER,
	pmcryptoperfdatacomclientCurrent24StatOutPacketCountInvPortn
		EkiOnOff,
	pmcryptoperfdatacomclientCurrent24StatOutPacketCountPortn
		Counter64,
	pmcryptoperfdatacomclientCurrent24StatOutCrcCountInvPortn
		EkiOnOff,
	pmcryptoperfdatacomclientCurrent24StatOutCrcCountPortn
		Counter64,
	pmcryptoperfdatacomclientCurrent24StatInPacketCountInvPortn
		EkiOnOff,
	pmcryptoperfdatacomclientCurrent24StatInPacketCountPortn
		Counter64,
	pmcryptoperfdatacomclientCurrent24StatInCrcCountInvPortn
		EkiOnOff,
	pmcryptoperfdatacomclientCurrent24StatInCrcCountPortn
		Counter64
	}


pmcryptoPerfDatacomClientCurrent24StatIndex OBJECT-TYPE
	SYNTAX  INTEGER(0..128)
	MAX-ACCESS  read-only
	STATUS current
	DESCRIPTION
        "
        Index definition for the pmcryptoPerfDatacomClientCurrent24Stat 
        table
        "
	::= { pmcryptoPerfDatacomClientCurrent24StatEntry 1 }


pmcryptoperfdatacomclientCurrent24StatOutPacketCountInvPortn OBJECT-TYPE
	SYNTAX  EkiOnOff
	MAX-ACCESS read-only
	STATUS current
	DESCRIPTION
        "
        Client Current 24-hours Output 
        Packet counter inv. :This OID indicates 
        that the current 24-hours Output 
        Packets counter is invalid
        "
	::= { pmcryptoPerfDatacomClientCurrent24StatEntry 30 }


pmcryptoperfdatacomclientCurrent24StatOutPacketCountPortn OBJECT-TYPE
	SYNTAX  Counter64
	MAX-ACCESS read-only
	STATUS current
	DESCRIPTION
        "
        Client Current 24-hours Output 
        Packet counter :This OID gives
         the current 24-hours Output Packets 
        counter value
        "
	::= { pmcryptoPerfDatacomClientCurrent24StatEntry 31 }


pmcryptoperfdatacomclientCurrent24StatOutCrcCountInvPortn OBJECT-TYPE
	SYNTAX  EkiOnOff
	MAX-ACCESS read-only
	STATUS current
	DESCRIPTION
        "
        Client Current 24-hours Output 
        CRC counter inv. :This OID indicates 
        that the current 24-hours Output 
        CRC counter is invalid
        "
	::= { pmcryptoPerfDatacomClientCurrent24StatEntry 28 }


pmcryptoperfdatacomclientCurrent24StatOutCrcCountPortn OBJECT-TYPE
	SYNTAX  Counter64
	MAX-ACCESS read-only
	STATUS current
	DESCRIPTION
        "
        Client Current 24-hours Output 
        CRC counter :This OID gives the 
        current 24-hours Output CRC counter 
        value
        "
	::= { pmcryptoPerfDatacomClientCurrent24StatEntry 29 }


pmcryptoperfdatacomclientCurrent24StatInPacketCountInvPortn OBJECT-TYPE
	SYNTAX  EkiOnOff
	MAX-ACCESS read-only
	STATUS current
	DESCRIPTION
        "
        Client Current 24-hours Input
         Packet counter inv. :This OID
         indicates that the current 24-hours 
        Input Packet counter is invalid
        "
	::= { pmcryptoPerfDatacomClientCurrent24StatEntry 6 }


pmcryptoperfdatacomclientCurrent24StatInPacketCountPortn OBJECT-TYPE
	SYNTAX  Counter64
	MAX-ACCESS read-only
	STATUS current
	DESCRIPTION
        "
        Client Current 24-hours Input
         Packet counter :This OID gives 
        the current 24-hours Input Packet 
        counter value
        "
	::= { pmcryptoPerfDatacomClientCurrent24StatEntry 7 }


pmcryptoperfdatacomclientCurrent24StatInCrcCountInvPortn OBJECT-TYPE
	SYNTAX  EkiOnOff
	MAX-ACCESS read-only
	STATUS current
	DESCRIPTION
        "
        Client Current 24-hours Input
         CRC counter inv. :This OID indicates 
        that the current 24-hours Input 
        CRC counter is invalid
        "
	::= { pmcryptoPerfDatacomClientCurrent24StatEntry 4 }


pmcryptoperfdatacomclientCurrent24StatInCrcCountPortn OBJECT-TYPE
	SYNTAX  Counter64
	MAX-ACCESS read-only
	STATUS current
	DESCRIPTION
        "
        Client Current 24-hours Input
         CRC counter :This OID gives the 
        current 24-hours Input CRC counter 
        value
        "
	::= { pmcryptoPerfDatacomClientCurrent24StatEntry 5 }


--- *****************************************************
---     Leaf of the datacomClientPast24Stat
--- *****************************************************
--- *********************************************************
---     TABLE for the pmcryptoPerfDatacomClientPast24StatHistory articles
--- *********************************************************

pmcryptoPerfDatacomClientPast24StatHistoryPort1Table OBJECT-TYPE
	SYNTAX  SEQUENCE OF PmcryptoPerfDatacomClientPast24StatHistoryPort1Entry
	MAX-ACCESS not-accessible
	STATUS current
	DESCRIPTION
        "
        List of pmcryptoPerfDatacomClientPast24StatHistory 
        Article
        "
	::= { pmcryptoMonPerfClient 944 }


pmcryptoPerfDatacomClientPast24StatHistoryPort1Entry OBJECT-TYPE
	SYNTAX PmcryptoPerfDatacomClientPast24StatHistoryPort1Entry
	MAX-ACCESS not-accessible
	STATUS current
	DESCRIPTION
        "
        Row definition for the pmcryptoPerfDatacomClientPast24StatHistory 
        table
        "
	INDEX   { pmcryptoPerfDatacomClientPast24StatHistoryPort1Index }
	::= { pmcryptoPerfDatacomClientPast24StatHistoryPort1Table 1 }


PmcryptoPerfDatacomClientPast24StatHistoryPort1Entry ::=
	SEQUENCE {
	pmcryptoPerfDatacomClientPast24StatHistoryPort1Index
		INTEGER,
	pmcryptoperfdatacomclientPast24StatOutPacketCountInvPort1
		EkiOnOff,
	pmcryptoperfdatacomclientPast24StatOutPacketCountPort1
		Counter64,
	pmcryptoperfdatacomclientPast24StatOutCrcCountInvPort1
		EkiOnOff,
	pmcryptoperfdatacomclientPast24StatOutCrcCountPort1
		Counter64,
	pmcryptoperfdatacomclientPast24StatInPacketCountInvPort1
		EkiOnOff,
	pmcryptoperfdatacomclientPast24StatInPacketCountPort1
		Counter64,
	pmcryptoperfdatacomclientPast24StatInCrcCountInvPort1
		EkiOnOff,
	pmcryptoperfdatacomclientPast24StatInCrcCountPort1
		Counter64
	}


pmcryptoPerfDatacomClientPast24StatHistoryPort1Index OBJECT-TYPE
	SYNTAX  INTEGER(0..128)
	MAX-ACCESS  read-only
	STATUS current
	DESCRIPTION
        "
        Index definition for the pmcryptoPerfDatacomClientPast24StatHistory 
        table
        "
	::= { pmcryptoPerfDatacomClientPast24StatHistoryPort1Entry 1 }


pmcryptoperfdatacomclientPast24StatOutPacketCountInvPort1 OBJECT-TYPE
	SYNTAX  EkiOnOff
	MAX-ACCESS read-only
	STATUS current
	DESCRIPTION
        "
        Client Past 24-hours Output Packet 
        counter inv. :This OID indicates 
        that the past 24-hours Output Packets 
        counter is invalid
        "
	::= { pmcryptoPerfDatacomClientPast24StatHistoryPort1Entry 30 }


pmcryptoperfdatacomclientPast24StatOutPacketCountPort1 OBJECT-TYPE
	SYNTAX  Counter64
	MAX-ACCESS read-only
	STATUS current
	DESCRIPTION
        "
        Client Past 24-hours Output Packet 
        counter :This OID gives the past 
        24-hours Output Packets counter 
        value
        "
	::= { pmcryptoPerfDatacomClientPast24StatHistoryPort1Entry 31 }


pmcryptoperfdatacomclientPast24StatOutCrcCountInvPort1 OBJECT-TYPE
	SYNTAX  EkiOnOff
	MAX-ACCESS read-only
	STATUS current
	DESCRIPTION
        "
        Client Past 24-hours Output CRC 
        counter inv. :This OID indicates 
        that the past 24-hours Output CRC 
        counter is invalid
        "
	::= { pmcryptoPerfDatacomClientPast24StatHistoryPort1Entry 28 }


pmcryptoperfdatacomclientPast24StatOutCrcCountPort1 OBJECT-TYPE
	SYNTAX  Counter64
	MAX-ACCESS read-only
	STATUS current
	DESCRIPTION
        "
        Client Past 24-hours Output CRC 
        counter :This OID gives the past 
        24-hours Output CRC counter value
        "
	::= { pmcryptoPerfDatacomClientPast24StatHistoryPort1Entry 29 }


pmcryptoperfdatacomclientPast24StatInPacketCountInvPort1 OBJECT-TYPE
	SYNTAX  EkiOnOff
	MAX-ACCESS read-only
	STATUS current
	DESCRIPTION
        "
        Client Past 24-hours Input Packet 
        counter inv. :This OID indicates 
        that the past 24-hours Input Packet 
        counter is invalid
        "
	::= { pmcryptoPerfDatacomClientPast24StatHistoryPort1Entry 6 }


pmcryptoperfdatacomclientPast24StatInPacketCountPort1 OBJECT-TYPE
	SYNTAX  Counter64
	MAX-ACCESS read-only
	STATUS current
	DESCRIPTION
        "
        Client Past 24-hours Input Packet 
        counter :This OID gives the past 
        24-hours Input Packet counter value
        "
	::= { pmcryptoPerfDatacomClientPast24StatHistoryPort1Entry 7 }


pmcryptoperfdatacomclientPast24StatInCrcCountInvPort1 OBJECT-TYPE
	SYNTAX  EkiOnOff
	MAX-ACCESS read-only
	STATUS current
	DESCRIPTION
        "
        Client Past 24-hours Input CRC 
        counter inv. :This OID indicates 
        that the past 24-hours Input CRC 
        counter is invalid
        "
	::= { pmcryptoPerfDatacomClientPast24StatHistoryPort1Entry 4 }


pmcryptoperfdatacomclientPast24StatInCrcCountPort1 OBJECT-TYPE
	SYNTAX  Counter64
	MAX-ACCESS read-only
	STATUS current
	DESCRIPTION
        "
        Client Past 24-hours Input CRC 
        counter :This OID gives the past 
        24-hours Input CRC counter value
        "
	::= { pmcryptoPerfDatacomClientPast24StatHistoryPort1Entry 5 }



pmcryptoPerfEnable OBJECT-TYPE
	SYNTAX EkiOnOff
	MAX-ACCESS read-write
	STATUS current
	DESCRIPTION
        "
        Perf. Mon. Enable :This OID enables 
        the Performance Monitoring application
        "
	::= { pmcryptoMonPerfSync 257 }


pmcryptoPerf15minSync OBJECT-TYPE
	SYNTAX EkiOnOff
	MAX-ACCESS read-write
	STATUS current
	DESCRIPTION
        "
        Perf. Mon. 15-min sync. :This
         OID must be used in external synchronisation 
        mode only to send a 15-min synchronisation 
        command
        "
	::= { pmcryptoMonPerfSync 259 }


pmcryptoPerf24hSync OBJECT-TYPE
	SYNTAX EkiOnOff
	MAX-ACCESS read-write
	STATUS current
	DESCRIPTION
        "
        Perf. Mon. 24-hours sync. :This 
        OID must be used in external synchronisation 
        mode only to send a 24-hours synchronisation 
        command
        "
	::= { pmcryptoMonPerfSync 260 }


pmcryptoPerf15MinShort OBJECT-TYPE
	SYNTAX EkiOnOff
	MAX-ACCESS read-write
	STATUS current
	DESCRIPTION
        "
        15-min period is short :This OID 
        indicates that the 15-min period 
        lasts less than 890 seconds
        "
	::= { pmcryptoMonPerfTimeStamp 1 }


pmcryptoPerf15MinLong OBJECT-TYPE
	SYNTAX EkiOnOff
	MAX-ACCESS read-write
	STATUS current
	DESCRIPTION
        "
        15-min period is long :This OID 
        indicates that the 15-min period 
        lasts more than 910 seconds
        "
	::= { pmcryptoMonPerfTimeStamp 2 }


pmcryptoPerf24HoursShort OBJECT-TYPE
	SYNTAX Counter32
	MAX-ACCESS read-write
	STATUS current
	DESCRIPTION
        "
        24-hours period is short :This 
        OID indicates that 24-hours period 
        lasts less than 86390 seconds
        "
	::= { pmcryptoMonPerfTimeStamp 5 }


pmcryptoPerf24HoursLong OBJECT-TYPE
	SYNTAX Counter32
	MAX-ACCESS read-write
	STATUS current
	DESCRIPTION
        "
        24-hours period is long :This
         OID indicates that 24-hours period 
        lasts more than 86410 seconds
        "
	::= { pmcryptoMonPerfTimeStamp 6 }


pmcryptoPerfCurrent15MinElapsedTime OBJECT-TYPE
	SYNTAX Counter32
	MAX-ACCESS read-write
	STATUS current
	DESCRIPTION
        "
        Current 15min period Elapsed Time 
         :This OID gives the number of
         seconds elapsed in the current 
        15-minutes period
        "
	::= { pmcryptoMonPerfTimeStamp 7 }


pmcryptoPerfCurrent24HoursElapsedTime OBJECT-TYPE
	SYNTAX Counter32
	MAX-ACCESS read-write
	STATUS current
	DESCRIPTION
        "
        Current 24hours period Elapsed 
        Time :This OID gives the number 
        of seconds elapsed in the current 
        24-hours period
        "
	::= { pmcryptoMonPerfTimeStamp 8 }






--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pmcryptoDwlrestartProcess OBJECT IDENTIFIER ::= { pmcryptoDwlOther 0 }




pmcryptoDwlColdRestartProcessed OBJECT-TYPE
	  SYNTAX EkiOnOff
	  MAX-ACCESS read-only
	  STATUS current
	  DESCRIPTION
        "
        Cold Restart :This OID indicates 
        that the module last restart was 
        a Cold RESTART
        "
	  ::= { pmcryptoDwlrestartProcess 2 }



pmcryptoDwlWarmRestartProcessed OBJECT-TYPE
	  SYNTAX EkiOnOff
	  MAX-ACCESS read-only
	  STATUS current
	  DESCRIPTION
        "
        Warm Restart :This OID indicates 
        that the module last restart was 
        a Warm RESTART
        "
	  ::= { pmcryptoDwlrestartProcess 1 }



--- *****************************************************
---     LEAF for the swBanksUsed article
--- *****************************************************
pmcryptoDwlswBanksUsed OBJECT IDENTIFIER ::= { pmcryptoDwlOther 1 }




pmcryptoDwlSwBank2Notempty OBJECT-TYPE
	  SYNTAX EkiOnOff
	  MAX-ACCESS read-only
	  STATUS current
	  DESCRIPTION
        "
        SW bank 2 loaded :This OID indicates 
        a software is loaded in SW bank 
        2  <Help>  This status indicates 
        if the SW bank 2 contains SW package
        "
	  ::= { pmcryptoDwlswBanksUsed 6 }



pmcryptoDwlSwBank1Notempty OBJECT-TYPE
	  SYNTAX EkiOnOff
	  MAX-ACCESS read-only
	  STATUS current
	  DESCRIPTION
        "
        SW bank 1 loaded :This OID indicates 
        a software is loaded in SW bank 
        1  <Help>  This status indicates 
        if the SW bank 1 contains SW package
        "
	  ::= { pmcryptoDwlswBanksUsed 5 }



pmcryptoDwlSwBank2Used OBJECT-TYPE
	  SYNTAX EkiOnOff
	  MAX-ACCESS read-only
	  STATUS current
	  DESCRIPTION
        "
        SW bank 2 active :This OID indicates 
        the module is working on SW bank 
        2  <Help>  This status indicates 
        if the SW bank 2 is active or standby
        "
	  ::= { pmcryptoDwlswBanksUsed 2 }



pmcryptoDwlSwBank1Used OBJECT-TYPE
	  SYNTAX EkiOnOff
	  MAX-ACCESS read-only
	  STATUS current
	  DESCRIPTION
        "
        SW bank 1 active :This OID indicates 
        the module is working on SW bank 
        1  <Help>  This status indicates 
        if the SW bank 1 is active or standby
        "
	  ::= { pmcryptoDwlswBanksUsed 1 }



--- *****************************************************
---     LEAF for the gwBanksUsed article
--- *****************************************************
pmcryptoDwlgwBanksUsed OBJECT IDENTIFIER ::= { pmcryptoDwlOther 2 }




pmcryptoDwlGwBank4Notempty OBJECT-TYPE
	  SYNTAX EkiOnOff
	  MAX-ACCESS read-only
	  STATUS current
	  DESCRIPTION
        "
        GW bank 4 loaded :This OID indicates 
        a gateware is loaded in GW bank 
        4
        "
	  ::= { pmcryptoDwlgwBanksUsed 8 }



pmcryptoDwlGwBank3Notempty OBJECT-TYPE
	  SYNTAX EkiOnOff
	  MAX-ACCESS read-only
	  STATUS current
	  DESCRIPTION
        "
        GW bank 3 loaded :This OID indicates 
        a gateware is loaded in GW bank 
        3  <Help>  This status indicates 
        if the GW bank 3 contains GW package
        "
	  ::= { pmcryptoDwlgwBanksUsed 7 }



pmcryptoDwlGwBank2Notempty OBJECT-TYPE
	  SYNTAX EkiOnOff
	  MAX-ACCESS read-only
	  STATUS current
	  DESCRIPTION
        "
        GW bank 2 loaded :This OID indicates 
        a gateware is loaded in GW bank 
        2
        "
	  ::= { pmcryptoDwlgwBanksUsed 6 }



pmcryptoDwlGwBank1Notempty OBJECT-TYPE
	  SYNTAX EkiOnOff
	  MAX-ACCESS read-only
	  STATUS current
	  DESCRIPTION
        "
        GW bank 1 loaded :This OID indicates 
        a gateware is loaded in GW bank 
        1  <Help>  This status indicates 
        if the GW bank 1 contains GW package
        "
	  ::= { pmcryptoDwlgwBanksUsed 5 }



pmcryptoDwlGwBank4Used OBJECT-TYPE
	  SYNTAX EkiOnOff
	  MAX-ACCESS read-only
	  STATUS current
	  DESCRIPTION
        "
        GW bank 4 active :This OID indicates 
        the module is working on GW bank 
        4
        "
	  ::= { pmcryptoDwlgwBanksUsed 4 }



pmcryptoDwlGwBank3Used OBJECT-TYPE
	  SYNTAX EkiOnOff
	  MAX-ACCESS read-only
	  STATUS current
	  DESCRIPTION
        "
        GW bank 3 active :This OID indicates 
        the module is working on GW bank 
        3  <Help>  This status indicates 
        if the GW bank 3 is active or standby
        "
	  ::= { pmcryptoDwlgwBanksUsed 3 }



pmcryptoDwlGwBank2Used OBJECT-TYPE
	  SYNTAX EkiOnOff
	  MAX-ACCESS read-only
	  STATUS current
	  DESCRIPTION
        "
        GW bank 2 active :This OID indicates 
        the module is working on GW bank 
        2
        "
	  ::= { pmcryptoDwlgwBanksUsed 2 }



pmcryptoDwlGwBank1Used OBJECT-TYPE
	  SYNTAX EkiOnOff
	  MAX-ACCESS read-only
	  STATUS current
	  DESCRIPTION
        "
        GW bank 1 active :This OID indicates 
        the module is working on GW bank 
        1  <Help>  This status indicates 
        if the GW bank 1 is active or standby
        "
	  ::= { pmcryptoDwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pmcryptoCfgAccessCAisCsf OBJECT IDENTIFIER ::= { pmcryptoConfig 1 }



--- *****************************************************
---     LEAF for the table 0012
--- *****************************************************

pmcryptoCfgClientcaiscsfTable OBJECT-TYPE
	SYNTAX  SEQUENCE OF PmcryptoCfgClientcaiscsfEntry
	MAX-ACCESS not-accessible
	STATUS current
	DESCRIPTION
        "
        List of  Article
        "
	::= { pmcryptoCfgAccessCAisCsf 1 }


pmcryptoCfgClientcaiscsfEntry OBJECT-TYPE
	SYNTAX PmcryptoCfgClientcaiscsfEntry
	MAX-ACCESS not-accessible
	STATUS current
	DESCRIPTION
        "
        Row definition for the accessCAisCsf 
        table
        "
	INDEX   { pmcryptoCfgClientcaiscsfIndex }
	::= { pmcryptoCfgClientcaiscsfTable 1 }


PmcryptoCfgClientcaiscsfEntry ::=
	SEQUENCE {
	pmcryptoCfgClientcaiscsfIndex
		INTEGER,
	pmcryptoCfgReservePortn
		Unsigned32
	}


pmcryptoCfgClientcaiscsfIndex OBJECT-TYPE
	SYNTAX  INTEGER(0..128)
	MAX-ACCESS  read-only
	STATUS current
	DESCRIPTION
        "
        Index definition for the clientcaiscsf 
        table
        "
	::= { pmcryptoCfgClientcaiscsfEntry 1 }


pmcryptoCfgReservePortn OBJECT-TYPE
	SYNTAX  Unsigned32 (0..65536)
	MAX-ACCESS read-write
	STATUS current
	DESCRIPTION
        "
        CAIS mode  on Client Port :This 
        register enables/disables port
          laser shutdown on CAIS insertion 
        condition
        "
	::= { pmcryptoCfgClientcaiscsfEntry 3 }


--- *****************************************************
---     LEAF for the table Group startup
--- *****************************************************

pmcryptoCfgStartup OBJECT IDENTIFIER ::= { pmcryptoConfig 2 }



--- *****************************************************
---     LEAF for the table 2110
--- *****************************************************

pmcryptoCfgClientStartupTable OBJECT-TYPE
	SYNTAX  SEQUENCE OF PmcryptoCfgClientStartupEntry
	MAX-ACCESS not-accessible
	STATUS current
	DESCRIPTION
        "
        List of  Article
        "
	::= { pmcryptoCfgStartup 1 }


pmcryptoCfgClientStartupEntry OBJECT-TYPE
	SYNTAX PmcryptoCfgClientStartupEntry
	MAX-ACCESS not-accessible
	STATUS current
	DESCRIPTION
        "
        Row definition for the startup 
        table
        "
	INDEX   { pmcryptoCfgClientStartupIndex }
	::= { pmcryptoCfgClientStartupTable 1 }


PmcryptoCfgClientStartupEntry ::=
	SEQUENCE {
	pmcryptoCfgClientStartupIndex
		INTEGER,
	pmcryptoCfgSystConfPortPortn
		Unsigned32,
	pmcryptoCfgNetConfPortPortn
		Unsigned32,
	pmcryptoCfgOptionsPortPortn
		Unsigned32
	}


pmcryptoCfgClientStartupIndex OBJECT-TYPE
	SYNTAX  INTEGER(0..128)
	MAX-ACCESS  read-only
	STATUS current
	DESCRIPTION
        "
        Index definition for the clientStartup 
        table
        "
	::= { pmcryptoCfgClientStartupEntry 1 }


pmcryptoCfgSystConfPortPortn OBJECT-TYPE
	SYNTAX  Unsigned32 (0..65536)
	MAX-ACCESS read-write
	STATUS current
	DESCRIPTION
        "
        Default Settings on Client Port 
        :This  register configures the
         default initialisation settings 
        on the port.
        "
	::= { pmcryptoCfgClientStartupEntry 3 }


pmcryptoCfgNetConfPortPortn OBJECT-TYPE
	SYNTAX  Unsigned32 (0..65536)
	MAX-ACCESS read-write
	STATUS current
	DESCRIPTION
        "
        Default Settings on Client Port 
        :This  register configures the
         default initialisation settings 
        on the port.
        "
	::= { pmcryptoCfgClientStartupEntry 4 }


pmcryptoCfgOptionsPortPortn OBJECT-TYPE
	SYNTAX  Unsigned32 (0..65536)
	MAX-ACCESS read-write
	STATUS current
	DESCRIPTION
        "
        Default Options on Client Port 
        :This register configures the default 
        options on the port.
        "
	::= { pmcryptoCfgClientStartupEntry 14 }


--- *****************************************************
---     LEAF for the table 2190
--- *****************************************************

pmcryptoCfgLineStartupTable OBJECT-TYPE
	SYNTAX  SEQUENCE OF PmcryptoCfgLineStartupEntry
	MAX-ACCESS not-accessible
	STATUS current
	DESCRIPTION
        "
        List of  Article
        "
	::= { pmcryptoCfgStartup 2 }


pmcryptoCfgLineStartupEntry OBJECT-TYPE
	SYNTAX PmcryptoCfgLineStartupEntry
	MAX-ACCESS not-accessible
	STATUS current
	DESCRIPTION
        "
        Row definition for the startup 
        table
        "
	INDEX   { pmcryptoCfgLineStartupIndex }
	::= { pmcryptoCfgLineStartupTable 1 }


PmcryptoCfgLineStartupEntry ::=
	SEQUENCE {
	pmcryptoCfgLineStartupIndex
		INTEGER,
	pmcryptoCfgSystConfLinePortn
		Unsigned32,
	pmcryptoCfgOptionsLinePortn
		Unsigned32
	}


pmcryptoCfgLineStartupIndex OBJECT-TYPE
	SYNTAX  INTEGER(0..128)
	MAX-ACCESS  read-only
	STATUS current
	DESCRIPTION
        "
        Index definition for the lineStartup 
        table
        "
	::= { pmcryptoCfgLineStartupEntry 1 }


pmcryptoCfgSystConfLinePortn OBJECT-TYPE
	SYNTAX  Unsigned32 (0..65536)
	MAX-ACCESS read-write
	STATUS current
	DESCRIPTION
        "
        Default Settings on Line :This 
        register configures the default 
        initialisation settings on Line
        "
	::= { pmcryptoCfgLineStartupEntry 3 }


pmcryptoCfgOptionsLinePortn OBJECT-TYPE
	SYNTAX  Unsigned32 (0..65536)
	MAX-ACCESS read-write
	STATUS current
	DESCRIPTION
        "
        Default Options on Line :This
         register configures the default 
        options on the line
        "
	::= { pmcryptoCfgLineStartupEntry 14 }


--- *****************************************************
---     LEAF for the table 21AB
--- *****************************************************

pmcryptoCfgXfpTable OBJECT-TYPE
	SYNTAX  SEQUENCE OF PmcryptoCfgXfpEntry
	MAX-ACCESS not-accessible
	STATUS current
	DESCRIPTION
        "
        List of  Article
        "
	::= { pmcryptoCfgStartup 3 }


pmcryptoCfgXfpEntry OBJECT-TYPE
	SYNTAX PmcryptoCfgXfpEntry
	MAX-ACCESS not-accessible
	STATUS current
	DESCRIPTION
        "
        Row definition for the startup 
        table
        "
	INDEX   { pmcryptoCfgXfpIndex }
	::= { pmcryptoCfgXfpTable 1 }


PmcryptoCfgXfpEntry ::=
	SEQUENCE {
	pmcryptoCfgXfpIndex
		INTEGER,
	pmcryptoCfgSystConfMsaLinePortn
		Unsigned32
	}


pmcryptoCfgXfpIndex OBJECT-TYPE
	SYNTAX  INTEGER(0..128)
	MAX-ACCESS  read-only
	STATUS current
	DESCRIPTION
        "
        Index definition for the xfp table
        "
	::= { pmcryptoCfgXfpEntry 1 }


pmcryptoCfgSystConfMsaLinePortn OBJECT-TYPE
	SYNTAX  Unsigned32 (0..65536)
	MAX-ACCESS read-write
	STATUS current
	DESCRIPTION
        "
        Default settings on MSA :This
         register configures the default 
        initialisation settings on MSA
        "
	::= { pmcryptoCfgXfpEntry 3 }


--- *****************************************************
---     LEAF for the table Group labels
--- *****************************************************

pmcryptoCfgLabels OBJECT IDENTIFIER ::= { pmcryptoConfig 3 }



--- *****************************************************
---     LEAF for the table 0003
--- *****************************************************

pmcryptoCfgLabelclientTable OBJECT-TYPE
	SYNTAX  SEQUENCE OF PmcryptoCfgLabelclientEntry
	MAX-ACCESS not-accessible
	STATUS current
	DESCRIPTION
        "
        List of  Article
        "
	::= { pmcryptoCfgLabels 1 }


pmcryptoCfgLabelclientEntry OBJECT-TYPE
	SYNTAX PmcryptoCfgLabelclientEntry
	MAX-ACCESS not-accessible
	STATUS current
	DESCRIPTION
        "
        Row definition for the labels
         table
        "
	INDEX   { pmcryptoCfgLabelclientIndex }
	::= { pmcryptoCfgLabelclientTable 1 }


PmcryptoCfgLabelclientEntry ::=
	SEQUENCE {
	pmcryptoCfgLabelclientIndex
		INTEGER,
	pmcryptoCfgLabelclientPortn
		DisplayString
	}


pmcryptoCfgLabelclientIndex OBJECT-TYPE
	SYNTAX  INTEGER(0..128)
	MAX-ACCESS  read-only
	STATUS current
	DESCRIPTION
        "
        Index definition for the labelclient 
        table
        "
	::= { pmcryptoCfgLabelclientEntry 1 }


pmcryptoCfgLabelclientPortn OBJECT-TYPE
	SYNTAX  DisplayString( SIZE(1..16))
	MAX-ACCESS read-write
	STATUS current
	DESCRIPTION
        "
        Default settings on the label
         of the Ports :These registers
         configures the default initialisation 
        settings of the labels of the ports.
        "
	::= { pmcryptoCfgLabelclientEntry 3 }


--- *****************************************************
---     LEAF for the table 0004
--- *****************************************************

pmcryptoCfgLabellineTable OBJECT-TYPE
	SYNTAX  SEQUENCE OF PmcryptoCfgLabellineEntry
	MAX-ACCESS not-accessible
	STATUS current
	DESCRIPTION
        "
        List of  Article
        "
	::= { pmcryptoCfgLabels 2 }


pmcryptoCfgLabellineEntry OBJECT-TYPE
	SYNTAX PmcryptoCfgLabellineEntry
	MAX-ACCESS not-accessible
	STATUS current
	DESCRIPTION
        "
        Row definition for the labels
         table
        "
	INDEX   { pmcryptoCfgLabellineIndex }
	::= { pmcryptoCfgLabellineTable 1 }


PmcryptoCfgLabellineEntry ::=
	SEQUENCE {
	pmcryptoCfgLabellineIndex
		INTEGER,
	pmcryptoCfgLabellinePortn
		DisplayString
	}


pmcryptoCfgLabellineIndex OBJECT-TYPE
	SYNTAX  INTEGER(0..128)
	MAX-ACCESS  read-only
	STATUS current
	DESCRIPTION
        "
        Index definition for the labelline 
        table
        "
	::= { pmcryptoCfgLabellineEntry 1 }


pmcryptoCfgLabellinePortn OBJECT-TYPE
	SYNTAX  DisplayString( SIZE(1..16))
	MAX-ACCESS read-write
	STATUS current
	DESCRIPTION
        "
        Default settings on the label
         of the lines :These registers
         configures the default initialisation 
        settings of the labels of the lines.
        "
	::= { pmcryptoCfgLabellineEntry 3 }


--- *****************************************************
---     LEAF for the table Group startuptlh
--- *****************************************************

pmcryptoCfgStartuptlh OBJECT IDENTIFIER ::= { pmcryptoConfig 4 }



--- *****************************************************
---     LEAF for the table 25AB
--- *****************************************************

pmcryptoCfgOtxtlhTable OBJECT-TYPE
	SYNTAX  SEQUENCE OF PmcryptoCfgOtxtlhEntry
	MAX-ACCESS not-accessible
	STATUS current
	DESCRIPTION
        "
        List of  Article
        "
	::= { pmcryptoCfgStartuptlh 1 }


pmcryptoCfgOtxtlhEntry OBJECT-TYPE
	SYNTAX PmcryptoCfgOtxtlhEntry
	MAX-ACCESS not-accessible
	STATUS current
	DESCRIPTION
        "
        Row definition for the startuptlh 
        table
        "
	INDEX   { pmcryptoCfgOtxtlhIndex }
	::= { pmcryptoCfgOtxtlhTable 1 }


PmcryptoCfgOtxtlhEntry ::=
	SEQUENCE {
	pmcryptoCfgOtxtlhIndex
		INTEGER,
	pmcryptoCfgLinePwrLaserPortn
		Unsigned32,
	pmcryptoCfgLineFCurrentPortn
		Unsigned32,
	pmcryptoCfgLineGridCurrentPortn
		Unsigned32,
	pmcryptoCfgFPortn
		Unsigned32,
	pmcryptoCfgRxLineFCurrentPortn
		Unsigned32
	}


pmcryptoCfgOtxtlhIndex OBJECT-TYPE
	SYNTAX  INTEGER(0..128)
	MAX-ACCESS  read-only
	STATUS current
	DESCRIPTION
        "
        Index definition for the otxtlh 
        table
        "
	::= { pmcryptoCfgOtxtlhEntry 1 }


pmcryptoCfgLinePwrLaserPortn OBJECT-TYPE
	SYNTAX  Unsigned32 (0..65536)
	MAX-ACCESS read-write
	STATUS current
	DESCRIPTION
        "
        Defaut Line output Power :This 
        register configures the start-up 
        output power of the Line tranceiver 
         (Unit = dBm)
        "
	::= { pmcryptoCfgOtxtlhEntry 6 }


pmcryptoCfgLineFCurrentPortn OBJECT-TYPE
	SYNTAX  Unsigned32 (0..65536)
	MAX-ACCESS read-write
	STATUS current
	DESCRIPTION
        "
        Default Line transceiver Tx Channel 
        :This register configures the start-up 
        laser channel of the Line Tx transceiver
        "
	::= { pmcryptoCfgOtxtlhEntry 7 }


pmcryptoCfgLineGridCurrentPortn OBJECT-TYPE
	SYNTAX  Unsigned32 (0..65536)
	MAX-ACCESS read-write
	STATUS current
	DESCRIPTION
        "
        Default Line transceiver Grid
         :This register configures the
         start-up laser grid of the Line 
        transceiver
        "
	::= { pmcryptoCfgOtxtlhEntry 8 }


pmcryptoCfgFPortn OBJECT-TYPE
	SYNTAX  Unsigned32 (0..65536)
	MAX-ACCESS read-write
	STATUS current
	DESCRIPTION
        "
        Default Line TRX lowest Freq :This 
        register configures the start-up 
        lowest frequency of the Line transceiver
        "
	::= { pmcryptoCfgOtxtlhEntry 9 }


pmcryptoCfgRxLineFCurrentPortn OBJECT-TYPE
	SYNTAX  Unsigned32 (0..65536)
	MAX-ACCESS read-write
	STATUS current
	DESCRIPTION
        "
        Default Line transceiver Rx Channel 
        :This register configures the start-up 
        laser channel of the Line Rx transceiver
        "
	::= { pmcryptoCfgOtxtlhEntry 10 }


--- *****************************************************
---     LEAF for the table Group other
--- *****************************************************

pmcryptoCfgOther OBJECT IDENTIFIER ::= { pmcryptoConfig 5 }



--- *****************************************************
---     LEAF for the table 2300
--- *****************************************************

pmcryptotablemoduleOther OBJECT IDENTIFIER ::= { pmcryptoCfgOther 1 }



pmcryptoCfgmode OBJECT-TYPE
	  SYNTAX Unsigned32 (0..65536)
	  MAX-ACCESS read-write
	  STATUS current
	  DESCRIPTION
        "
        Default settings on Module :This 
        register selects the configuration 
        mode of the module
        "
	  ::= { pmcryptotablemoduleOther 2 }



pmcryptoCfgfanLowSpeedThreshold OBJECT-TYPE
	  SYNTAX Unsigned32 (0..65536)
	  MAX-ACCESS read-write
	  STATUS current
	  DESCRIPTION
        "
        Default settings on Module :This 
        register selects the speed threshold 
        of the fan's
        "
	  ::= { pmcryptotablemoduleOther 3 }



pmcryptoCfgfanHighSpeedThreshold OBJECT-TYPE
	  SYNTAX Unsigned32 (0..65536)
	  MAX-ACCESS read-write
	  STATUS current
	  DESCRIPTION
        "
        Default settings on Module :This 
        register selects the speed threshold 
        of the fan's
        "
	  ::= { pmcryptotablemoduleOther 4 }



pmcryptoCfgprotocolMode OBJECT-TYPE
	  SYNTAX Unsigned32 (0..65536)
	  MAX-ACCESS read-write
	  STATUS current
	  DESCRIPTION
        "
        Default settings on Module :This 
        register selects the configuration 
        mode of the module
        "
	  ::= { pmcryptotablemoduleOther 5 }



--- *****************************************************
---     LEAF for the table Group startuptablefive
--- *****************************************************

pmcryptoCfgStartuptablefive OBJECT IDENTIFIER ::= { pmcryptoConfig 6 }



--- *****************************************************
---     LEAF for the table 0005
--- *****************************************************

pmcryptoCfgOtxtlhcapabilitiesTable OBJECT-TYPE
	SYNTAX  SEQUENCE OF PmcryptoCfgOtxtlhcapabilitiesEntry
	MAX-ACCESS not-accessible
	STATUS current
	DESCRIPTION
        "
        List of  Article
        "
	::= { pmcryptoCfgStartuptablefive 1 }


pmcryptoCfgOtxtlhcapabilitiesEntry OBJECT-TYPE
	SYNTAX PmcryptoCfgOtxtlhcapabilitiesEntry
	MAX-ACCESS not-accessible
	STATUS current
	DESCRIPTION
        "
        Row definition for the startuptablefive 
        table
        "
	INDEX   { pmcryptoCfgOtxtlhcapabilitiesIndex }
	::= { pmcryptoCfgOtxtlhcapabilitiesTable 1 }


PmcryptoCfgOtxtlhcapabilitiesEntry ::=
	SEQUENCE {
	pmcryptoCfgOtxtlhcapabilitiesIndex
		INTEGER,
	pmcryptoCfgComponentTypePortn
		Unsigned32,
	pmcryptoCfgMiscellaneousPortn
		Unsigned32,
	pmcryptoCfgFirstChannelPortn
		Unsigned32,
	pmcryptoCfgLastChannelPortn
		Unsigned32,
	pmcryptoCfgGridPortn
		Unsigned32
	}


pmcryptoCfgOtxtlhcapabilitiesIndex OBJECT-TYPE
	SYNTAX  INTEGER(0..128)
	MAX-ACCESS  read-only
	STATUS current
	DESCRIPTION
        "
        Index definition for the otxtlhcapabilities 
        table
        "
	::= { pmcryptoCfgOtxtlhcapabilitiesEntry 1 }


pmcryptoCfgComponentTypePortn OBJECT-TYPE
	SYNTAX  Unsigned32 (0..65536)
	MAX-ACCESS read-only
	STATUS current
	DESCRIPTION
        "
        Component parameters :This OID 
        defines the component parameters
        "
	::= { pmcryptoCfgOtxtlhcapabilitiesEntry 3 }


pmcryptoCfgMiscellaneousPortn OBJECT-TYPE
	SYNTAX  Unsigned32 (0..65536)
	MAX-ACCESS read-only
	STATUS current
	DESCRIPTION
        "
        Miscellaneous default settings 
        :This OID defines the miscellaneous 
        parameters
        "
	::= { pmcryptoCfgOtxtlhcapabilitiesEntry 4 }


pmcryptoCfgFirstChannelPortn OBJECT-TYPE
	SYNTAX  Unsigned32 (0..65536)
	MAX-ACCESS read-only
	STATUS current
	DESCRIPTION
        "
        Number of the first channel of 
        the component :This OID defines 
        the first channel number of the 
        PM
        "
	::= { pmcryptoCfgOtxtlhcapabilitiesEntry 5 }


pmcryptoCfgLastChannelPortn OBJECT-TYPE
	SYNTAX  Unsigned32 (0..65536)
	MAX-ACCESS read-only
	STATUS current
	DESCRIPTION
        "
        Number of the last channel of
         the component :This OID defines 
        the last channel number of the
         PM
        "
	::= { pmcryptoCfgOtxtlhcapabilitiesEntry 6 }


pmcryptoCfgGridPortn OBJECT-TYPE
	SYNTAX  Unsigned32 (0..65536)
	MAX-ACCESS read-only
	STATUS current
	DESCRIPTION
        "
        Grid value of the component :This 
        OID defines the grid of the PM
        "
	::= { pmcryptoCfgOtxtlhcapabilitiesEntry 7 }



pmcryptoCfgWriteConfiguration  OBJECT-TYPE
	SYNTAX EkiOnOff
	MAX-ACCESS read-write
	STATUS current
	DESCRIPTION
	"Write configuration to module:This OID 
	 writes the complete configuration to the module"
	::= { pmcryptoConfig 257 }






--- *****************************************************
---     TRAP OBJECTS
--- *****************************************************

pmcryptotrapPortNumber OBJECT-TYPE
	SYNTAX INTEGER(1..64)
	MAX-ACCESS read-only
	STATUS current
	DESCRIPTION
	"Last port which generates a trap"
	::= { pmcryptotraps 2 }

pmcryptotrapLineNumber OBJECT-TYPE
	SYNTAX INTEGER(1..64)
	MAX-ACCESS read-only
	STATUS current
	DESCRIPTION
	"Last Line which generates a trap"
	::= { pmcryptotraps 3 }

pmcryptotrapBoardNumber OBJECT-TYPE
	SYNTAX INTEGER(1..64)
	MAX-ACCESS read-only
	STATUS current
	DESCRIPTION
	"Last module which generates a trap"
	::= { pmcryptotraps 4 }







--- *****************************************************
---     LINE TRAPS
--- *****************************************************

pmcryptoLineTrapNotUrgentGoesOn NOTIFICATION-TYPE
	OBJECTS {pmcryptoAlmLineDdmWarningPortn, pmcryptotrapLineNumber, pmcryptotrapBoardNumber}
	STATUS current
	DESCRIPTION "Not urgent Line default is activated"
	::= { pmcryptotraps 30 }

pmcryptoLineTrapNotUrgentGoesOff NOTIFICATION-TYPE
	OBJECTS {pmcryptoAlmLineDdmWarningPortn, pmcryptotrapLineNumber, pmcryptotrapBoardNumber}
	STATUS current
	DESCRIPTION "Not urgent Line default disappeared"
	::= { pmcryptotraps 31 }

pmcryptoLineTrapUrgentGoesOn NOTIFICATION-TYPE
	OBJECTS {pmcryptoAlmLineDdmAlmPortn, pmcryptotrapLineNumber, pmcryptotrapBoardNumber}
	STATUS current
	DESCRIPTION "Urgent Line default is activated"
	::= { pmcryptotraps 32 }

pmcryptoLineTrapUrgentGoesOff NOTIFICATION-TYPE
	OBJECTS {pmcryptoAlmLineDdmAlmPortn, pmcryptotrapLineNumber, pmcryptotrapBoardNumber}
	STATUS current
	DESCRIPTION "Urgent Line default disappeared"
	::= { pmcryptotraps 33 }

pmcryptoLineTrapCritGoesOn NOTIFICATION-TYPE
	OBJECTS {pmcryptoAlmLineFailPortn , pmcryptoAlmLineHwFailPortn , pmcryptotrapLineNumber, pmcryptotrapBoardNumber}
	STATUS current
	DESCRIPTION "Critical Line default is activated"
	::= { pmcryptotraps 34 }

pmcryptoLineTrapCritGoesOff NOTIFICATION-TYPE
	OBJECTS {pmcryptoAlmLineFailPortn , pmcryptoAlmLineHwFailPortn , pmcryptotrapLineNumber, pmcryptotrapBoardNumber}
	STATUS current
	DESCRIPTION "Critical Line default disappeared"
	::= { pmcryptotraps 35 }






--- *****************************************************
---     CLIENT TRAPS
--- *****************************************************

pmcryptoClientTrapNotUrgentGoesOn NOTIFICATION-TYPE
	OBJECTS {pmcryptoAlmSfpDdmWarningPortn, pmcryptotrapPortNumber, pmcryptotrapBoardNumber}
	STATUS current
	DESCRIPTION "Not urgent client default is activated"
	::= { pmcryptotraps 40 }

pmcryptoClientTrapNotUrgentGoesOff NOTIFICATION-TYPE
	OBJECTS {pmcryptoAlmSfpDdmWarningPortn, pmcryptotrapPortNumber, pmcryptotrapBoardNumber}
	STATUS current
	DESCRIPTION "Not urgent client default disappeared"
	::= { pmcryptotraps 41 }

pmcryptoClientTrapUrgentGoesOn NOTIFICATION-TYPE
	OBJECTS {pmcryptoAlmSfpDdmAlmPortn, pmcryptotrapPortNumber, pmcryptotrapBoardNumber}
	STATUS current
	DESCRIPTION "Urgent client default is activated"
	::= { pmcryptotraps 42 }

pmcryptoClientTrapUrgentGoesOff NOTIFICATION-TYPE
	OBJECTS {pmcryptoAlmSfpDdmAlmPortn, pmcryptotrapPortNumber, pmcryptotrapBoardNumber}
	STATUS current
	DESCRIPTION "Urgent client default disappeared"
	::= { pmcryptotraps 43 }

pmcryptoClientTrapCritGoesOn NOTIFICATION-TYPE
	OBJECTS {pmcryptoAlmFailAccPortn, pmcryptoAlmHwFailAccPortn, pmcryptotrapPortNumber, pmcryptotrapBoardNumber}
	STATUS current
	DESCRIPTION "Critical client default is activated"
	::= { pmcryptotraps 44 }

pmcryptoClientTrapCritGoesOff NOTIFICATION-TYPE
	OBJECTS {pmcryptoAlmFailAccPortn, pmcryptoAlmHwFailAccPortn, pmcryptotrapPortNumber, pmcryptotrapBoardNumber}
	STATUS current
	DESCRIPTION "Critical client default disappeared"
	::= { pmcryptotraps 45 }






--- *****************************************************
---     HW TRAPS
--- *****************************************************

pmcryptoPowerTrapUrgentGoesOn NOTIFICATION-TYPE
	OBJECTS {pmcryptoAlmDefFuseB, pmcryptoAlmDefFuseA , pmcryptotrapBoardNumber}
	STATUS current
	DESCRIPTION "Urgent power supply default is activated"
	::= { pmcryptotraps 50 }

pmcryptoPowerTrapUrgentGoesOff NOTIFICATION-TYPE
	OBJECTS {pmcryptoAlmDefFuseB, pmcryptoAlmDefFuseA , pmcryptotrapBoardNumber}
	STATUS current
	DESCRIPTION "Urgent power supply default disappeared"
	::= { pmcryptotraps 51 }






END
