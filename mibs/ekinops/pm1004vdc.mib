-- *****************************************************************
-- EKINOPS-Pm1004VDC.TXT:  MIB
--
--MIB Part Number:3MI00019AAAD
--MIB Version:02
--
-- Copyright (c) 2016 by Ekinops
-- All rights reserved.
-- 
-- *****************************************************************

EKINOPS-Pm1004VDC-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress                
        		FROM SNMPv2-SMI
 	TEXTUAL-CONVENTION,
	DisplayString
                FROM SNMPv2-TC;

modulePm1004vdc MODULE-IDENTITY
        LAST-UPDATED "201606020000Z"
        ORGANIZATION "Ekinops"
        CONTACT-INFO
         "Ekinops

          11, rue Louis de Broglie
          F-22300 Lannion / FRANCE

          Tel : +33 (0)2 96 05 00 30
          Fax : +33 (0)2 96 48 62 39

          E-mail: support@ekinops.net"
        DESCRIPTION
          "MIB for managing Ekinops modules with PM1004vdc software"
	REVISION "200803110000Z"
	DESCRIPTION
	  "Initial Version."
	REVISION "200808180000Z"
	DESCRIPTION
	  "Labels modifications."
	REVISION "200812020000Z"
	DESCRIPTION
	  "DCC Storm suppress"
	REVISION "200812080000Z"
	DESCRIPTION
	  "Client Signal Shutdown label"
	REVISION "200905260000Z"
	DESCRIPTION
	  "Client OOS TX and RX insertion"
	REVISION "200907220000Z"
	DESCRIPTION
	  "Add DCC and MAINTENANCE control"
	REVISION "200909020000Z"
	DESCRIPTION
	  "Some Labels updates"
	REVISION "200910270000Z"
	DESCRIPTION
	  "Add LossOfSync as alarm Line"
	REVISION "201003030000Z"
	DESCRIPTION
	  "Probcause,AlarmType - NMS"
	REVISION "201102040000Z"
	DESCRIPTION
	  "Formulas in comments and Event on XFP init"
	REVISION "201104290000Z"
	DESCRIPTION
	  "OTX-TLH features insertion"
	REVISION "201203080000Z"
	DESCRIPTION
	  "OTX-TLH features insertion"
	REVISION "201403280000Z"
	DESCRIPTION
	  "Probcause,AlarmType - NMS completion"
	REVISION "201412230000Z"
	DESCRIPTION
	  "Labels cosmetic updates"
	REVISION "201605200000Z"
	DESCRIPTION
	  "New AlarmType – synthesisAlarm (12)"
	REVISION "201606020000Z"
	DESCRIPTION
	  "Capabilities objects of Table 5"
        ::= { ekinops 38 }



--- *****************************************************
---     LEAF LEVEL 2
--- *****************************************************


pm1004vdcalarms OBJECT IDENTIFIER ::= { modulePm1004vdc 2 }	
pm1004vdcAlmOther OBJECT IDENTIFIER ::= { pm1004vdcalarms 1 }
pm1004vdcAlmOtherNurg OBJECT IDENTIFIER ::= { pm1004vdcAlmOther 1 }
pm1004vdcAlmOtherUrg OBJECT IDENTIFIER ::= { pm1004vdcAlmOther 2 }
pm1004vdcAlmOtherCrit OBJECT IDENTIFIER ::= { pm1004vdcAlmOther 3 }

pm1004vdcAlmClient OBJECT IDENTIFIER ::= { pm1004vdcalarms 2 }
pm1004vdcAlmClientNurg OBJECT IDENTIFIER ::= { pm1004vdcAlmClient 1 }
pm1004vdcAlmClientUrg OBJECT IDENTIFIER ::= { pm1004vdcAlmClient 2 }
pm1004vdcAlmClientCrit OBJECT IDENTIFIER ::= { pm1004vdcAlmClient 3 }
	
pm1004vdcAlmLine OBJECT IDENTIFIER ::= { pm1004vdcalarms 3 }
pm1004vdcAlmLineNurg OBJECT IDENTIFIER ::= { pm1004vdcAlmLine 1 }
pm1004vdcAlmLineUrg OBJECT IDENTIFIER ::= { pm1004vdcAlmLine 2 }
pm1004vdcAlmLineCrit OBJECT IDENTIFIER ::= { pm1004vdcAlmLine 3 }





pm1004vdcmeasures OBJECT IDENTIFIER ::= { modulePm1004vdc 3 }	
pm1004vdcMesrOther OBJECT IDENTIFIER ::= { pm1004vdcmeasures 1 }	
pm1004vdcMesrClient OBJECT IDENTIFIER ::= { pm1004vdcmeasures 2 }	
pm1004vdcMesrLine OBJECT IDENTIFIER ::= { pm1004vdcmeasures 3 }	




pm1004vdccounters OBJECT IDENTIFIER ::= { modulePm1004vdc 4 }
pm1004vdcCntOther OBJECT IDENTIFIER ::= { pm1004vdccounters 1 }
pm1004vdcCntClient OBJECT IDENTIFIER ::= { pm1004vdccounters 2 }
pm1004vdcCntLine OBJECT IDENTIFIER ::= { pm1004vdccounters 3 }


pm1004vdccontrolsWrite OBJECT IDENTIFIER ::= { modulePm1004vdc 6 }
pm1004vdcCtrlOther OBJECT IDENTIFIER ::= { pm1004vdccontrolsWrite 1 }
pm1004vdcCtrlClient OBJECT IDENTIFIER ::= { pm1004vdccontrolsWrite 2 }
pm1004vdcCtrlLine OBJECT IDENTIFIER ::= { pm1004vdccontrolsWrite 3 }

pm1004vdcri OBJECT IDENTIFIER ::= { modulePm1004vdc 7 }
pm1004vdcriTable OBJECT IDENTIFIER ::= { pm1004vdcri 1 }

pm1004vdcdownload OBJECT IDENTIFIER ::= { modulePm1004vdc 8 }
pm1004vdcDwlOther OBJECT IDENTIFIER ::= { pm1004vdcdownload 1 }
pm1004vdcDwlClient OBJECT IDENTIFIER ::= { pm1004vdcdownload 2 }
pm1004vdcDwlLine OBJECT IDENTIFIER ::= { pm1004vdcdownload 3 }


pm1004vdcConfig OBJECT IDENTIFIER ::= { modulePm1004vdc 9 }

pm1004vdctraps OBJECT IDENTIFIER ::= { modulePm1004vdc 10 }



pm1004vdcMonitoring OBJECT IDENTIFIER ::= { modulePm1004vdc 11}

pm1004vdcMonOther OBJECT IDENTIFIER ::= { pm1004vdcMonitoring 1 }
pm1004vdcMonRmon OBJECT IDENTIFIER ::= { pm1004vdcMonOther 3 }

pm1004vdcMonClient OBJECT IDENTIFIER ::= { pm1004vdcMonitoring 2 }
pm1004vdcMonClientRmonCounter OBJECT IDENTIFIER ::= { pm1004vdcMonClient 4 }
pm1004vdcMonLine OBJECT IDENTIFIER ::= { pm1004vdcMonitoring 3 }
pm1004vdcMonLineRmonCounter OBJECT IDENTIFIER ::= { pm1004vdcMonLine 4 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pm1004vdcModeTimeSlot ::= TEXTUAL-CONVENTION
    STATUS      current
    DESCRIPTION "different mode for time slot"
    SYNTAX INTEGER {
		singleSplitSelect(256)
           }


Pm1004vdcModeAddDrop ::= TEXTUAL-CONVENTION
    STATUS      current
    DESCRIPTION "different mode for client"
    SYNTAX INTEGER {
		singleSplitSelect(256)
           }


Pm1004vdcProtectionTimeSlot ::= TEXTUAL-CONVENTION
    STATUS      current
    DESCRIPTION "protection for control"
    SYNTAX INTEGER {
		auto(0),
		manualX2Line2(257),
		manualX1Line1(513)
           }

Pm1004vdcProtectionStartUp ::= TEXTUAL-CONVENTION
    STATUS      current
    DESCRIPTION "protection for startup"
    SYNTAX INTEGER {
		auto(2),
		manualX2Line2(0),
		manualX1Line1(1)
           }


Pm1004vdcDccMode ::= TEXTUAL-CONVENTION
    STATUS      current
    DESCRIPTION "Mode for DCC"
    SYNTAX INTEGER {
		dccNo(0),
		dcctermLine1(1),
		dcctermLine2(2),
		dcctermLines12(3),
		dccmaster(4),
		dccslaveLine12(7)
           }

Pm1004vdcClientOosMode ::= TEXTUAL-CONVENTION
    STATUS      current
    DESCRIPTION "Mode for OOS on client ports"
    SYNTAX INTEGER {		
		clientportis(0),
		clienttxoos(1),
		clientrxoos(2),
		clientportoos(3)
           }


Pm1004vdcOtxMode ::= TEXTUAL-CONVENTION
    STATUS      current
    DESCRIPTION "Different modes on OTX-TLH on client and line ports"
    SYNTAX INTEGER {
		otx80mode(1),
		otx60mode(2),
		otxadjustmode(4)
           }

Pm1004vdcOtxGrid ::= TEXTUAL-CONVENTION
    STATUS      current
    DESCRIPTION "Different grids on OTX-TLH on client and line ports"
    SYNTAX INTEGER {
		otxgrid200(200),
		otxgrid100(100),
		otxgrid50(50)
           }

Pm1004vdcAdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm1004vdcOtxChannel ::= TEXTUAL-CONVENTION
    STATUS      current
    DESCRIPTION "Channel selection on OTX-TLH on client and line ports"
    SYNTAX INTEGER


--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm1004vdcRinvReloadInventory OBJECT-TYPE
  SYNTAX EkiOnOff
  MAX-ACCESS read-write
  STATUS current
  DESCRIPTION
        "Reload the inventory: This OID triggers an 
         inventory reload."
  ::= { pm1004vdcri 2 }

pm1004vdcRinvHwPlatform OBJECT-TYPE
  SYNTAX DisplayString
  MAX-ACCESS read-only
  STATUS current
  DESCRIPTION
        "HW platform description: This OID contains the 
         description of the Hardware platform."
  ::= { pm1004vdcri 3 }
  
pm1004vdcRinvModulePlatform OBJECT-TYPE
  SYNTAX DisplayString
  MAX-ACCESS read-only
  STATUS current
  DESCRIPTION
        "Module platform description: This OID contains the 
         description of the Module."
  ::= { pm1004vdcri 4 }
  
pm1004vdcRinvSwPlatform OBJECT-TYPE
  SYNTAX DisplayString
  MAX-ACCESS read-only
  STATUS current
  DESCRIPTION
        "SW platform description: This OID contains the 
         description of the Software platform."
  ::= { pm1004vdcri 5 }
  
pm1004vdcRinvGwPlatform OBJECT-TYPE
  SYNTAX DisplayString
  MAX-ACCESS read-only
  STATUS current
  DESCRIPTION
        "GW platform desciption: This OID contains the 
         description of the Gateware platform."
  ::= { pm1004vdcri 6 }


pm1004vdcRinvSfpTable OBJECT-TYPE
      SYNTAX  SEQUENCE OF Pm1004vdcRinvSfpEntry
      MAX-ACCESS  not-accessible
      STATUS  current
      DESCRIPTION
              "List of the SFPs on the selected module"
      ::= { pm1004vdcriTable 1 }

pm1004vdcRinvSfpEntry OBJECT-TYPE
        SYNTAX  Pm1004vdcRinvSfpEntry
        MAX-ACCESS  not-accessible
        STATUS  current
        DESCRIPTION
              "Row definition for the SFP table"
        INDEX   { pm1004vdcRinvSfpIndex }
        ::= { pm1004vdcRinvSfpTable 1 }
    


Pm1004vdcRinvSfpEntry::=
        SEQUENCE {
          pm1004vdcRinvSfpIndex 
              Integer32,
          pm1004vdcRinvsfp
              DisplayString
        }


    pm1004vdcRinvSfpIndex OBJECT-TYPE
        SYNTAX  Integer32(1..16)
        MAX-ACCESS  read-only
        STATUS  current
        DESCRIPTION
              "Index for SFP table"
        ::= { pm1004vdcRinvSfpEntry 1 }


    pm1004vdcRinvsfp OBJECT-TYPE
        SYNTAX  DisplayString
        MAX-ACCESS  read-only
        STATUS  current
        DESCRIPTION
              "Inventory for the SFP: This OID contains the inventory for the SFP"
        ::= { pm1004vdcRinvSfpEntry 2 }




pm1004vdcRinvLineTable OBJECT-TYPE
      SYNTAX  SEQUENCE OF Pm1004vdcRinvLineEntry
      MAX-ACCESS  not-accessible
      STATUS  current
      DESCRIPTION
              "List of the XFPs on the selected module"
      ::= { pm1004vdcriTable 2 }

pm1004vdcRinvLineEntry OBJECT-TYPE
        SYNTAX  Pm1004vdcRinvLineEntry
        MAX-ACCESS  not-accessible
        STATUS  current
        DESCRIPTION
              "Row definition for the XFP table"
        INDEX   { pm1004vdcRinvLineIndex }
        ::= { pm1004vdcRinvLineTable 1 }
    


Pm1004vdcRinvLineEntry::=
        SEQUENCE {
          pm1004vdcRinvLineIndex 
              Integer32,
          pm1004vdcRinvxfpLine
              DisplayString
        }


    pm1004vdcRinvLineIndex OBJECT-TYPE
        SYNTAX  Integer32(1..16)
        MAX-ACCESS  read-only
        STATUS  current
        DESCRIPTION
              "Index for XFP table"
        ::= { pm1004vdcRinvLineEntry 1 }


    pm1004vdcRinvxfpLine OBJECT-TYPE
        SYNTAX  DisplayString
        MAX-ACCESS  read-only
        STATUS  current
        DESCRIPTION
              "Inventory for the XFP: This OID contains the inventory for the XFP"
        ::= { pm1004vdcRinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm1004vdcAlmsynthAlm0 OBJECT IDENTIFIER ::= { pm1004vdcAlmOtherCrit 0 }




pm1004vdcAlmDefFuseB OBJECT-TYPE
	  SYNTAX EkiOnOff
	  MAX-ACCESS read-only
	  STATUS current
	  DESCRIPTION
        "
        Fuse B Fail :This OID indicates 
        that the fuse of the power input 
        B is in fail condition  <Help>
          Status of the Fuse B <Condtype> 
        DEF_FUSE_B <Probcause> powerProblem 
        (36) <Alarmtype> equipmentAlarm 
        (5) <Polarity> (2) 
        "
	  ::= { pm1004vdcAlmsynthAlm0 16 }



pm1004vdcAlmDefFuseA OBJECT-TYPE
	  SYNTAX EkiOnOff
	  MAX-ACCESS read-only
	  STATUS current
	  DESCRIPTION
        "
        Fuse A Fail :This OID indicates 
        that the fuse of the power input 
        A is in fail condition  <Help>
          Status of the Fuse A <Condtype> 
        DEF_FUSE_A <Probcause> powerProblem 
        (36) <Alarmtype> equipmentAlarm 
        (5) <Polarity> (2) 
        "
	  ::= { pm1004vdcAlmsynthAlm0 15 }



pm1004vdcAlmModGlobFail OBJECT-TYPE
	  SYNTAX EkiOnOff
	  MAX-ACCESS read-only
	  STATUS current
	  DESCRIPTION
        "
        Module Failure :This OID is set 
        on detection of a failure originating 
        from the PM <Condtype> MOD_GLOB_FAIL 
        <Probcause> equipmentMalfunction 
        (16) <Alarmtype> synthesisAlarm 
        (12)  <Polarity> (2) 
        "
	  ::= { pm1004vdcAlmsynthAlm0 9 }



--- *****************************************************
---     LEAF for the synthAlm2 article
--- *****************************************************
pm1004vdcAlmsynthAlm2 OBJECT IDENTIFIER ::= { pm1004vdcAlmOtherNurg 2 }




pm1004vdcAlmMaintenanceOn OBJECT-TYPE
	  SYNTAX EkiOnOff
	  MAX-ACCESS read-only
	  STATUS current
	  DESCRIPTION
        "
        Maintenance Mode :This OID indicates 
        that the PM is in maintenance mode. 
         <Help>  This alarm indicates that 
        the maintenance mode is enabled 
        on the PM <Condtype> MAINTENANCE_ON 
        <Probcause> other (1) <Alarmtype> 
        other (1) <Polarity> (2) 
        "
	  ::= { pm1004vdcAlmsynthAlm2 5 }



pm1004vdcAlmCorrelatOff OBJECT-TYPE
	  SYNTAX EkiOnOff
	  MAX-ACCESS read-only
	  STATUS current
	  DESCRIPTION
        "
        Not Used :This OID, when set,
         indicates that alarm correlation 
        is not being performed. <Condtype> 
        CORRELAT_OFF <Probcause> other
         (1) <Alarmtype> other (1) <Polarity> 
        (2) 
        "
	  ::= { pm1004vdcAlmsynthAlm2 4 }



pm1004vdcAlmConfTableLoad OBJECT-TYPE
	  SYNTAX EkiOnOff
	  MAX-ACCESS read-only
	  STATUS current
	  DESCRIPTION
        "
        PM Configuration Load :This OID 
         is at 1 during the loading of
         configuration tables in the modules 
        RAM. <Condtype> CONF_TABLE_LOAD 
        <Probcause> other (1) <Alarmtype> 
        other (1) <Polarity> (2) 
        "
	  ::= { pm1004vdcAlmsynthAlm2 3 }



pm1004vdcAlmInvUpload OBJECT-TYPE
	  SYNTAX EkiOnOff
	  MAX-ACCESS read-only
	  STATUS current
	  DESCRIPTION
        "
        Inventory Upload :This OID is
         at 1 during the uploading of PM 
        inventory information. <Condtype> 
        INV_UPLOAD <Probcause> other (1) 
        <Alarmtype> other (1) <Polarity> 
        (2) 
        "
	  ::= { pm1004vdcAlmsynthAlm2 2 }



pm1004vdcAlmConfTableSave OBJECT-TYPE
	  SYNTAX EkiOnOff
	  MAX-ACCESS read-only
	  STATUS current
	  DESCRIPTION
        "
        PM Configuration Save :This OID 
        is at 1 during the saving of a
         new configuration table in the 
        module Flash memory. <Condtype> 
        CONF_TABLE_SAVE <Probcause> other 
        (1) <Alarmtype> other (1) <Polarity> 
        (2) 
        "
	  ::= { pm1004vdcAlmsynthAlm2 1 }



--- *********************************************************
---     TABLE for the pm1004vdcAlmsynthAlmLine articles
--- *********************************************************

pm1004vdcAlmsynthAlmLineTable OBJECT-TYPE
	SYNTAX  SEQUENCE OF Pm1004vdcAlmsynthAlmLineEntry
	MAX-ACCESS not-accessible
	STATUS current
	DESCRIPTION
        "
        List of pm1004vdcAlmsynthAlmLine 
        Article
        "
	::= { pm1004vdcAlmLineCrit 7 }


pm1004vdcAlmsynthAlmLineEntry OBJECT-TYPE
	SYNTAX Pm1004vdcAlmsynthAlmLineEntry
	MAX-ACCESS not-accessible
	STATUS current
	DESCRIPTION
        "
        Row definition for the pm1004vdcAlmsynthAlmLine 
        table
        "
	INDEX   { pm1004vdcAlmsynthAlmLineIndex }
	::= { pm1004vdcAlmsynthAlmLineTable 1 }


Pm1004vdcAlmsynthAlmLineEntry ::=
	SEQUENCE {
	pm1004vdcAlmsynthAlmLineIndex
		INTEGER,
	pm1004vdcAlmLineActivePortn
		EkiOnOff,
	pm1004vdcAlmLineFailPortn
		EkiOnOff,
	pm1004vdcAlmLineDdmCritPortn
		EkiOnOff,
	pm1004vdcAlmLineDdmAlmPortn
		EkiOnOff,
	pm1004vdcAlmLineDdmWarningPortn
		EkiOnOff,
	pm1004vdcAlmLineLocalOosPortn
		EkiOnOff,
	pm1004vdcAlmXfpTxOffPortn
		EkiOnOff,
	pm1004vdcAlmLineHwFailPortn
		EkiOnOff,
	pm1004vdcAlmXfpInitNotComplPortn
		EkiOnOff,
	pm1004vdcAlmXfpAbsentPortn
		EkiOnOff
	}


pm1004vdcAlmsynthAlmLineIndex OBJECT-TYPE
	SYNTAX  INTEGER(0..128)
	MAX-ACCESS  read-only
	STATUS current
	DESCRIPTION
        "
        Index definition for the pm1004vdcAlmsynthAlmLine 
        table
        "
	::= { pm1004vdcAlmsynthAlmLineEntry 1 }


pm1004vdcAlmLineActivePortn OBJECT-TYPE
	SYNTAX  EkiOnOff
	MAX-ACCESS read-only
	STATUS current
	DESCRIPTION
        "
        Line Active :This bit indicates 
        the line #n is active on receive 
        side  <Help>  This status indicates 
        whether the line is active or standby. 
        <Condtype> LINE_ACTIVE <Probcause> 
        informationalStatus(1000) <Alarmtype> 
        other (1) <Polarity> (2) 
        "
	::= { pm1004vdcAlmsynthAlmLineEntry 17 }


pm1004vdcAlmLineFailPortn OBJECT-TYPE
	SYNTAX  EkiOnOff
	MAX-ACCESS read-only
	STATUS current
	DESCRIPTION
        "
        Line Port Failure :This OID indicates 
        a failure on the line port <Condtype> 
        LINE_FAIL <Probcause> equipmentMalfunction 
        (16) <Alarmtype> synthesisAlarm 
        (12)  <Polarity> (2) 
        "
	::= { pm1004vdcAlmsynthAlmLineEntry 13 }


pm1004vdcAlmLineDdmCritPortn OBJECT-TYPE
	SYNTAX  EkiOnOff
	MAX-ACCESS read-only
	STATUS current
	DESCRIPTION
        "
        Custom Alarm On Line XFP/OTX DDM 
        :This OID indicates a Custom alarm 
        is present coming out of Line optical 
        interface DDM    <Help>   This
         alarm indicates if a DDM Custom 
        Alarm has been detected on the
         line transceiver <Condtype> LINE_DDM_CRIT 
        <Probcause> equipmentMalfunction 
        (16) <Alarmtype> synthesisAlarm 
        (12)  <Polarity> (2) 
        "
	::= { pm1004vdcAlmsynthAlmLineEntry 12 }


pm1004vdcAlmLineDdmAlmPortn OBJECT-TYPE
	SYNTAX  EkiOnOff
	MAX-ACCESS read-only
	STATUS current
	DESCRIPTION
        "
        Alarm On Line Optical Module DDM 
        :This OID indicates an alarm is 
        present coming out of Line optical 
        interface DDM  <Help>  This alarm 
        indicates if a DDM Alarm has been 
        detected on the line transceiver 
        <Condtype> LINE_DDM_ALM <Probcause> 
        equipmentMalfunction (16) <Alarmtype> 
        synthesisAlarm (12)  <Polarity> 
        (2) 
        "
	::= { pm1004vdcAlmsynthAlmLineEntry 11 }


pm1004vdcAlmLineDdmWarningPortn OBJECT-TYPE
	SYNTAX  EkiOnOff
	MAX-ACCESS read-only
	STATUS current
	DESCRIPTION
        "
        Warning On Line Optical Module 
        DDM :This OID indicates a warning 
        is present coming out of Line optical 
        interface DDM  <Help>  This alarm 
        indicates if a DDM Warning has
         been detected on the line transceiver 
        <Condtype> LINE_DDM_WARNING <Probcause> 
        equipmentMalfunction (16) <Alarmtype> 
        synthesisAlarm (12)  <Polarity> 
        (2) 
        "
	::= { pm1004vdcAlmsynthAlmLineEntry 10 }


pm1004vdcAlmLineLocalOosPortn OBJECT-TYPE
	SYNTAX  EkiOnOff
	MAX-ACCESS read-only
	STATUS current
	DESCRIPTION
        "
        Line Port In Service :This OID 
        indicates that the Line port is 
        In Service (1) of Out or Service 
        (2)  <Help>  This status indicates 
        if the line port is in service
         <Condtype> LINE_LOCAL_OOS <Probcause> 
        informationalStatus(1000) <Alarmtype> 
        other (1) <Polarity> (2) 
        "
	::= { pm1004vdcAlmsynthAlmLineEntry 7 }


pm1004vdcAlmXfpTxOffPortn OBJECT-TYPE
	SYNTAX  EkiOnOff
	MAX-ACCESS read-only
	STATUS current
	DESCRIPTION
        "
        Line Optical Module Laser Shutdown 
        :This OID indicates the line optical 
        output power is on  <Help>  This 
        status indicates if the line transceiver 
        laser is ON or OFF <Condtype> XFP_TX_OFF 
        <Probcause> other (1) <Alarmtype> 
        equipmentAlarm (5) <Polarity> (2) 
        "
	::= { pm1004vdcAlmsynthAlmLineEntry 6 }


pm1004vdcAlmLineHwFailPortn OBJECT-TYPE
	SYNTAX  EkiOnOff
	MAX-ACCESS read-only
	STATUS current
	DESCRIPTION
        "
        Line Port HW Failure :This OID 
        indicates a failure on line port, 
        most probably caused by a HW issue 
        <Condtype> LINE_HW_FAIL <Probcause> 
        equipmentMalfunction (16) <Alarmtype> 
        synthesisAlarm (12)  <Polarity> 
        (2) 
        "
	::= { pm1004vdcAlmsynthAlmLineEntry 5 }


pm1004vdcAlmXfpInitNotComplPortn OBJECT-TYPE
	SYNTAX  EkiOnOff
	MAX-ACCESS read-only
	STATUS current
	DESCRIPTION
        "
        Line Optical Module Ready :This 
        OID indicates that the optical
         interface (XFP or OTX) is not
         operational.  <Help>  This status 
        indicates if the line transceiver 
        has been correctly initialized
         <Condtype> XFP_INIT_NOT_COMPL
         <Probcause> equipmentMalfunction 
        (16) <Alarmtype> equipmentAlarm 
        (5) <Polarity> (2) <Event> ObjectCDINV
        "
	::= { pm1004vdcAlmsynthAlmLineEntry 3 }


pm1004vdcAlmXfpAbsentPortn OBJECT-TYPE
	SYNTAX  EkiOnOff
	MAX-ACCESS read-only
	STATUS current
	DESCRIPTION
        "
        Line Optical Module Absent :This 
        OID indicates that the line optical 
        interface (XFP or OTX) is not plugged 
        in.  <Help>  This alarm indicates 
        if the line transceiver is present. 
        <Condtype> XFP_ABSENT <Probcause> 
        inputOutputDeviceError (24) <Alarmtype> 
        equipmentAlarm (5) <Polarity> (2) 
        <Event> ObjectCDINV
        "
	::= { pm1004vdcAlmsynthAlmLineEntry 2 }


--- *********************************************************
---     TABLE for the pm1004vdcAlmsynthAlmPort articles
--- *********************************************************

pm1004vdcAlmsynthAlmPortTable OBJECT-TYPE
	SYNTAX  SEQUENCE OF Pm1004vdcAlmsynthAlmPortEntry
	MAX-ACCESS not-accessible
	STATUS current
	DESCRIPTION
        "
        List of pm1004vdcAlmsynthAlmPort 
        Article
        "
	::= { pm1004vdcAlmClientCrit 8 }


pm1004vdcAlmsynthAlmPortEntry OBJECT-TYPE
	SYNTAX Pm1004vdcAlmsynthAlmPortEntry
	MAX-ACCESS not-accessible
	STATUS current
	DESCRIPTION
        "
        Row definition for the pm1004vdcAlmsynthAlmPort 
        table
        "
	INDEX   { pm1004vdcAlmsynthAlmPortIndex }
	::= { pm1004vdcAlmsynthAlmPortTable 1 }


Pm1004vdcAlmsynthAlmPortEntry ::=
	SEQUENCE {
	pm1004vdcAlmsynthAlmPortIndex
		INTEGER,
	pm1004vdcAlmUpCsfPortn
		EkiOnOff,
	pm1004vdcAlmClientActivePortn
		EkiOnOff,
	pm1004vdcAlmFailAccPortn
		EkiOnOff,
	pm1004vdcAlmSfpDdmCritPortn
		EkiOnOff,
	pm1004vdcAlmSfpDdmAlmPortn
		EkiOnOff,
	pm1004vdcAlmSfpDdmWarningPortn
		EkiOnOff,
	pm1004vdcAlmDwCaisPortn
		EkiOnOff,
	pm1004vdcAlmClientLocalOosRxPortn
		EkiOnOff,
	pm1004vdcAlmClientLocalOosTxPortn
		EkiOnOff,
	pm1004vdcAlmDwLsdPortn
		EkiOnOff,
	pm1004vdcAlmHwFailAccPortn
		EkiOnOff,
	pm1004vdcAlmDdmAbsentPortn
		EkiOnOff,
	pm1004vdcAlmSfpAbsentPortn
		EkiOnOff
	}


pm1004vdcAlmsynthAlmPortIndex OBJECT-TYPE
	SYNTAX  INTEGER(0..128)
	MAX-ACCESS  read-only
	STATUS current
	DESCRIPTION
        "
        Index definition for the pm1004vdcAlmsynthAlmPort 
        table
        "
	::= { pm1004vdcAlmsynthAlmPortEntry 1 }


pm1004vdcAlmUpCsfPortn OBJECT-TYPE
	SYNTAX  EkiOnOff
	MAX-ACCESS read-only
	STATUS current
	DESCRIPTION
        "
        Client Signal Fail Inserted :This 
        OID indicates a CSF has been inserted 
        in the upstream client port.  <Help> 
         This status indicates if a Client 
        Signal Fail is currently inserted 
        on the line signal for this client 
        port <Condtype> UP_CSF_1 <Probcause> 
        other (1) <Alarmtype> other (1) 
        <Polarity> (2) 
        "
	::= { pm1004vdcAlmsynthAlmPortEntry 17 }


pm1004vdcAlmClientActivePortn OBJECT-TYPE
	SYNTAX  EkiOnOff
	MAX-ACCESS read-only
	STATUS current
	DESCRIPTION
        "
        Client Sink (Line1 Or Line2) :This 
        bit indicates the Client #n is
         active on receive side  <Help> 
         This status indicates whether
         the Client is extracted from Line 
        1 or Line 2. <Condtype> CLIENT_ACTIVE 
        <Probcause> other (1) <Alarmtype> 
        other (1) <Polarity> (2) 
        "
	::= { pm1004vdcAlmsynthAlmPortEntry 16 }


pm1004vdcAlmFailAccPortn OBJECT-TYPE
	SYNTAX  EkiOnOff
	MAX-ACCESS read-only
	STATUS current
	DESCRIPTION
        "
        Client Access Fail :This OID indicates 
        a failure on the Client port <Condtype> 
        FAIL_ACC_1 <Probcause> equipmentMalfunction 
        (16) <Alarmtype> synthesisAlarm 
        (12)  <Polarity> (2) 
        "
	::= { pm1004vdcAlmsynthAlmPortEntry 13 }


pm1004vdcAlmSfpDdmCritPortn OBJECT-TYPE
	SYNTAX  EkiOnOff
	MAX-ACCESS read-only
	STATUS current
	DESCRIPTION
        "
        Custom Alarm On Client SFP DDM 
        :This OID indicates a Custom alarm 
        is being received from the Client 
        SFP DDM  <Help>   This alarm indicates 
        if a DDM Custom Alarm has been
         detected on the client transceiver

 
        <Condtype> SFP_DDM_CRIT_1 <Probcause> 
        equipmentMalfunction (16) <Alarmtype> 
        synthesisAlarm (12)  <Polarity> 
        (2) 
        "
	::= { pm1004vdcAlmsynthAlmPortEntry 12 }


pm1004vdcAlmSfpDdmAlmPortn OBJECT-TYPE
	SYNTAX  EkiOnOff
	MAX-ACCESS read-only
	STATUS current
	DESCRIPTION
        "
        Alarm On Client SFP DDM :This
         OID indicates an alarm is being 
        received from the Client SFP DDM 
        (only significant on Client6-GbE 
        port)   <Help>   This alarm indicates 
        if a DDM Alarm has been detected 
        on the client transceiver (only 
        significant on Client6-GbE port) 
        <Condtype> SFP_DDM_ALM_1 <Probcause> 
        equipmentMalfunction (16) <Alarmtype> 
        synthesisAlarm (12)  <Polarity> 
        (2) 
        "
	::= { pm1004vdcAlmsynthAlmPortEntry 11 }


pm1004vdcAlmSfpDdmWarningPortn OBJECT-TYPE
	SYNTAX  EkiOnOff
	MAX-ACCESS read-only
	STATUS current
	DESCRIPTION
        "
        Warning On Client SFP DDM :This 
        OID indicates a warning is being 
        received from the Client SFP DDM 
        (only significant on Client6-GbE 
        port)   <Help>   This alarm indicates 
        if a DDM Warning has been detected 
        on the client transceiver (only 
        significant on Client6-GbE port) 
        <Condtype> SFP_DDM_WARNING_1 <Probcause> 
        equipmentMalfunction (16) <Alarmtype> 
        synthesisAlarm (12)  <Polarity> 
        (2) 
        "
	::= { pm1004vdcAlmsynthAlmPortEntry 10 }


pm1004vdcAlmDwCaisPortn OBJECT-TYPE
	SYNTAX  EkiOnOff
	MAX-ACCESS read-only
	STATUS current
	DESCRIPTION
        "
        Client AIS Inserted :This OID
         indicates a CAIS has been inserted 
        on the output client port.  <Help> 
          This status indictaes if a Client 
        Alarm Indication Signal is currently 
        inserted on the client interface 
        <Condtype> DW_CAIS_1 <Probcause> 
        informationalStatus(1000) <Alarmtype> 
        other (1) <Polarity> (2) 
        "
	::= { pm1004vdcAlmsynthAlmPortEntry 9 }


pm1004vdcAlmClientLocalOosRxPortn OBJECT-TYPE
	SYNTAX  EkiOnOff
	MAX-ACCESS read-only
	STATUS current
	DESCRIPTION
        "
        Rx Client Port In Service :This 
        OID indicates that the local Rx 
        Client port is In Service (1) or 
        Out of Service (2)  <Help>   This 
        status indicates if the local Rx 
        client port is in service <Condtype> 
        CLIENT_LOCAL_OOS_RX <Probcause> 
        informationalStatus(1000) <Alarmtype> 
        other (1) <Polarity> (2) 
        "
	::= { pm1004vdcAlmsynthAlmPortEntry 8 }


pm1004vdcAlmClientLocalOosTxPortn OBJECT-TYPE
	SYNTAX  EkiOnOff
	MAX-ACCESS read-only
	STATUS current
	DESCRIPTION
        "
        Tx Client Port In Service :This 
        OID indicates that the local Tx 
        Client port is In Service (1) or 
        Out of Service (2)  <Help>   This 
        status indicates if the local Tx 
        client port is in service
 <Condtype> 
        CLIENT_LOCAL_OOS_TX <Probcause> 
        informationalStatus(1000) <Alarmtype> 
        other (1) <Polarity> (2) 
        "
	::= { pm1004vdcAlmsynthAlmPortEntry 7 }


pm1004vdcAlmDwLsdPortn OBJECT-TYPE
	SYNTAX  EkiOnOff
	MAX-ACCESS read-only
	STATUS current
	DESCRIPTION
        "
        Client Signal Shutdown :This OID 
        indicates the Client SFP transmitter 
        output is ON.   <Help>   This status 
        indicates if the client transceiver 
         is ON or OFF <Condtype> DW_LSD_1 
        <Probcause> other (1) <Alarmtype> 
        equipmentAlarm (5) <Polarity> (2) 
        "
	::= { pm1004vdcAlmsynthAlmPortEntry 6 }


pm1004vdcAlmHwFailAccPortn OBJECT-TYPE
	SYNTAX  EkiOnOff
	MAX-ACCESS read-only
	STATUS current
	DESCRIPTION
        "
        Client HW Fail :This OID indicates 
        a failure on client port, most
         probably caused by a HW issue. 
        <Condtype> HW_FAIL_ACC_1 <Probcause> 
        equipmentMalfunction (16) <Alarmtype> 
        synthesisAlarm (12)  <Polarity> 
        (2) 
        "
	::= { pm1004vdcAlmsynthAlmPortEntry 5 }


pm1004vdcAlmDdmAbsentPortn OBJECT-TYPE
	SYNTAX  EkiOnOff
	MAX-ACCESS read-only
	STATUS current
	DESCRIPTION
        "
        DDM Supported On Client SFP :This 
        OID indicates that the Client SFP 
        module supports the Digital Diagnostic 
        Monitoring function (only significant 
        on Client6-GbE port)   <Help> 
          This status indicates if the
         client transceiver includes the 
        DDM feature (only significant on 
        Client6-GbE port) <Condtype> DDM_ABSENT_1 
        <Probcause> equipmentMalfunction 
        (16) <Alarmtype> other (1) <Polarity> 
        (2) 
        "
	::= { pm1004vdcAlmsynthAlmPortEntry 3 }


pm1004vdcAlmSfpAbsentPortn OBJECT-TYPE
	SYNTAX  EkiOnOff
	MAX-ACCESS read-only
	STATUS current
	DESCRIPTION
        "
        Client Optical Module Absent :This 
        OID indicates that the SFP module 
        is not present in the client port 
        (only significant on Client6-GbE 
        port).   <Help>   This alarm indicates 
        if the client transceiver is present 
        (only significant on Client6-GbE 
        port) <Condtype> SFP_ABSENT_1 <Probcause> 
        inputOutputDeviceError (24) <Alarmtype> 
        equipmentAlarm (5) <Polarity> (2) 
        <Event> ObjectCDINV
        "
	::= { pm1004vdcAlmsynthAlmPortEntry 2 }


--- *********************************************************
---     TABLE for the pm1004vdcAlmaccessioAlm articles
--- *********************************************************

pm1004vdcAlmaccessioAlmTable OBJECT-TYPE
	SYNTAX  SEQUENCE OF Pm1004vdcAlmaccessioAlmEntry
	MAX-ACCESS not-accessible
	STATUS current
	DESCRIPTION
        "
        List of pm1004vdcAlmaccessioAlm 
        Article
        "
	::= { pm1004vdcAlmClientCrit 16 }


pm1004vdcAlmaccessioAlmEntry OBJECT-TYPE
	SYNTAX Pm1004vdcAlmaccessioAlmEntry
	MAX-ACCESS not-accessible
	STATUS current
	DESCRIPTION
        "
        Row definition for the pm1004vdcAlmaccessioAlm 
        table
        "
	INDEX   { pm1004vdcAlmaccessioAlmIndex }
	::= { pm1004vdcAlmaccessioAlmTable 1 }


Pm1004vdcAlmaccessioAlmEntry ::=
	SEQUENCE {
	pm1004vdcAlmaccessioAlmIndex
		INTEGER,
	pm1004vdcAlmUpLosPortn
		EkiOnOff,
	pm1004vdcAlmDwLasFailPortn
		EkiOnOff
	}


pm1004vdcAlmaccessioAlmIndex OBJECT-TYPE
	SYNTAX  INTEGER(0..128)
	MAX-ACCESS  read-only
	STATUS current
	DESCRIPTION
        "
        Index definition for the pm1004vdcAlmaccessioAlm 
        table
        "
	::= { pm1004vdcAlmaccessioAlmEntry 1 }


pm1004vdcAlmUpLosPortn OBJECT-TYPE
	SYNTAX  EkiOnOff
	MAX-ACCESS read-only
	STATUS current
	DESCRIPTION
        "
        Client Input Loss Of Signal :This 
        OID indicates that no signal is 
        present on the client port  <Help> 
          This alarm indicates if a signal 
        is detected on the client input 
        <Condtype> UP_LOS_1 <Probcause> 
        receiveFailure (41) <Alarmtype> 
        physicalViolation (9) <Polarity> 
        (2) 
        "
	::= { pm1004vdcAlmaccessioAlmEntry 5 }


pm1004vdcAlmDwLasFailPortn OBJECT-TYPE
	SYNTAX  EkiOnOff
	MAX-ACCESS read-only
	STATUS current
	DESCRIPTION
        "
        Client SFP Tx Failed :This OID 
        indicates that the transmitter
         fails for the SFP plugged into 
        the client port. This alarm reports 
        the transmitter failure alarm generated 
        by the SFPs.  <Help>   This alarm 
        indicates if the laser of the client 
        transceiver is in fail condition 
        <Condtype> DW_LAS_FAIL_1 <Probcause> 
        transmitterFailure (56) <Alarmtype> 
        equipmentAlarm (5) <Polarity> (2) 
        "
	::= { pm1004vdcAlmaccessioAlmEntry 2 }


--- *********************************************************
---     TABLE for the pm1004vdcAlmsfpAlmDdm articles
--- *********************************************************

pm1004vdcAlmsfpAlmDdmTable OBJECT-TYPE
	SYNTAX  SEQUENCE OF Pm1004vdcAlmsfpAlmDdmEntry
	MAX-ACCESS not-accessible
	STATUS current
	DESCRIPTION
        "
        List of pm1004vdcAlmsfpAlmDdm
         Article
        "
	::= { pm1004vdcAlmClientUrg 32 }


pm1004vdcAlmsfpAlmDdmEntry OBJECT-TYPE
	SYNTAX Pm1004vdcAlmsfpAlmDdmEntry
	MAX-ACCESS not-accessible
	STATUS current
	DESCRIPTION
        "
        Row definition for the pm1004vdcAlmsfpAlmDdm 
        table
        "
	INDEX   { pm1004vdcAlmsfpAlmDdmIndex }
	::= { pm1004vdcAlmsfpAlmDdmTable 1 }


Pm1004vdcAlmsfpAlmDdmEntry ::=
	SEQUENCE {
	pm1004vdcAlmsfpAlmDdmIndex
		INTEGER,
	pm1004vdcAlmRxPwrHighAlaPortn
		EkiOnOff,
	pm1004vdcAlmRxPwrLowAlaPortn
		EkiOnOff,
	pm1004vdcAlmTempHighAlaPortn
		EkiOnOff,
	pm1004vdcAlmTempLowAlaPortn
		EkiOnOff,
	pm1004vdcAlmVccHighAlaPortn
		EkiOnOff,
	pm1004vdcAlmVccLowAlaPortn
		EkiOnOff,
	pm1004vdcAlmTxBiasHighAlaPortn
		EkiOnOff,
	pm1004vdcAlmTxBiasLowAlaPortn
		EkiOnOff,
	pm1004vdcAlmTxPwrHighAlaPortn
		EkiOnOff,
	pm1004vdcAlmTxPwrLowAlaPortn
		EkiOnOff
	}


pm1004vdcAlmsfpAlmDdmIndex OBJECT-TYPE
	SYNTAX  INTEGER(0..128)
	MAX-ACCESS  read-only
	STATUS current
	DESCRIPTION
        "
        Index definition for the pm1004vdcAlmsfpAlmDdm 
        table
        "
	::= { pm1004vdcAlmsfpAlmDdmEntry 1 }


pm1004vdcAlmRxPwrHighAlaPortn OBJECT-TYPE
	SYNTAX  EkiOnOff
	MAX-ACCESS read-only
	STATUS current
	DESCRIPTION
        "
        Client SFP Rx Power High :Alarm 
        indicating that the SFP input power 
        of port is higher than the threshold 
        value written in the SFP EEPROM 
        <Condtype> RX_PWR_HIGH_ALA_1 <Probcause> 
        receiveFailure (41) <Alarmtype> 
        equipmentAlarm (5) <Polarity> (2) 
        "
	::= { pm1004vdcAlmsfpAlmDdmEntry 17 }


pm1004vdcAlmRxPwrLowAlaPortn OBJECT-TYPE
	SYNTAX  EkiOnOff
	MAX-ACCESS read-only
	STATUS current
	DESCRIPTION
        "
        Client SFP Rx Power Low :Alarm 
        indicating that the SFP input power 
        of port is lower than the threshold 
        value written in the SFP EEPROM 
        <Condtype> RX_PWR_LOW_ALA_1 <Probcause> 
        receiveFailure (41) <Alarmtype> 
        equipmentAlarm (5) <Polarity> (2) 
        "
	::= { pm1004vdcAlmsfpAlmDdmEntry 16 }


pm1004vdcAlmTempHighAlaPortn OBJECT-TYPE
	SYNTAX  EkiOnOff
	MAX-ACCESS read-only
	STATUS current
	DESCRIPTION
        "
        Client SFP Temp High :Alarm indicating 
        that the SFP temperature of port 
        is higher than the threshold value 
        written in the SFP EEPROM <Condtype> 
        TEMP_HIGH_ALA_1 <Probcause> temperatureUnacceptable 
        (51) <Alarmtype> equipmentAlarm 
        (5) <Polarity> (2) 
        "
	::= { pm1004vdcAlmsfpAlmDdmEntry 9 }


pm1004vdcAlmTempLowAlaPortn OBJECT-TYPE
	SYNTAX  EkiOnOff
	MAX-ACCESS read-only
	STATUS current
	DESCRIPTION
        "
        Client SFP Temp Low :Alarm indicating 
        that the SFP temperature of port 
        is lower than the threshold value 
        written in the SFP EEPROM <Condtype> 
        TEMP_LOW_ALA_1 <Probcause> temperatureUnacceptable 
        (51) <Alarmtype> equipmentAlarm 
        (5) <Polarity> (2) 
        "
	::= { pm1004vdcAlmsfpAlmDdmEntry 8 }


pm1004vdcAlmVccHighAlaPortn OBJECT-TYPE
	SYNTAX  EkiOnOff
	MAX-ACCESS read-only
	STATUS current
	DESCRIPTION
        "
        Client SFP Power Supply High :Alarm 
        indicating that the SFP power supply 
        of port is higher than the threshold 
        value written in the SFP EEPROM 
         <Condtype> VCC_HIGH_ALA_1 <Probcause> 
        powerProblem (36) <Alarmtype> equipmentAlarm 
        (5) <Polarity> (2) 
        "
	::= { pm1004vdcAlmsfpAlmDdmEntry 7 }


pm1004vdcAlmVccLowAlaPortn OBJECT-TYPE
	SYNTAX  EkiOnOff
	MAX-ACCESS read-only
	STATUS current
	DESCRIPTION
        "
        Client SFP Power Supply Low :Alarm 
        indicating that the SFP power supply 
        of port is lower than the threshold 
        value written in the SFP EEPROM 
         <Condtype> VCC_LOW_ALA_1 <Probcause> 
        powerProblem (36) <Alarmtype> equipmentAlarm 
        (5) <Polarity> (2) 
        "
	::= { pm1004vdcAlmsfpAlmDdmEntry 6 }


pm1004vdcAlmTxBiasHighAlaPortn OBJECT-TYPE
	SYNTAX  EkiOnOff
	MAX-ACCESS read-only
	STATUS current
	DESCRIPTION
        "
        Client SFP Bias High :Alarm indicating 
        that the SFP laser bias current 
        of port is higher than the threshold 
        value written in the SFP EEPROM 
        <Condtype> TX_BIAS_HIGH_ALA_1 <Probcause> 
        transmitterFailure (56) <Alarmtype> 
        equipmentAlarm (5) <Polarity> (2) 
        "
	::= { pm1004vdcAlmsfpAlmDdmEntry 5 }


pm1004vdcAlmTxBiasLowAlaPortn OBJECT-TYPE
	SYNTAX  EkiOnOff
	MAX-ACCESS read-only
	STATUS current
	DESCRIPTION
        "
        Client SFP Bias Low :Alarm indicating 
        that the SFP laser bias current 
        of port is lower than the threshold 
        value written in the SFP EEPROM 
        <Condtype> TX_BIAS_LOW_ALA_1 <Probcause> 
        transmitterFailure (56) <Alarmtype> 
        equipmentAlarm (5) <Polarity> (2) 
        "
	::= { pm1004vdcAlmsfpAlmDdmEntry 4 }


pm1004vdcAlmTxPwrHighAlaPortn OBJECT-TYPE
	SYNTAX  EkiOnOff
	MAX-ACCESS read-only
	STATUS current
	DESCRIPTION
        "
        Client SFP Tx Power High :Alarm 
        indicating that the SFP output
         power of port is higher than the 
        threshold value written in the
         SFP EEPROM <Condtype> TX_PWR_HIGH_ALA_1 
        <Probcause> transmitterFailure
         (56) <Alarmtype> equipmentAlarm 
        (5) <Polarity> (2) 
        "
	::= { pm1004vdcAlmsfpAlmDdmEntry 3 }


pm1004vdcAlmTxPwrLowAlaPortn OBJECT-TYPE
	SYNTAX  EkiOnOff
	MAX-ACCESS read-only
	STATUS current
	DESCRIPTION
        "
        Client SFP Tx Power Low :Alarm 
        indicating that the SFP output
         power of port is lower than the 
        threshold value written in the
         SFP EEPROM <Condtype> TX_PWR_LOW_ALA_1 
        <Probcause> transmitterFailure
         (56) <Alarmtype> equipmentAlarm 
        (5) <Polarity> (2) 
        "
	::= { pm1004vdcAlmsfpAlmDdmEntry 2 }


--- *********************************************************
---     TABLE for the pm1004vdcAlmsfpWarnDdm articles
--- *********************************************************

pm1004vdcAlmsfpWarnDdmTable OBJECT-TYPE
	SYNTAX  SEQUENCE OF Pm1004vdcAlmsfpWarnDdmEntry
	MAX-ACCESS not-accessible
	STATUS current
	DESCRIPTION
        "
        List of pm1004vdcAlmsfpWarnDdm 
        Article
        "
	::= { pm1004vdcAlmClientNurg 48 }


pm1004vdcAlmsfpWarnDdmEntry OBJECT-TYPE
	SYNTAX Pm1004vdcAlmsfpWarnDdmEntry
	MAX-ACCESS not-accessible
	STATUS current
	DESCRIPTION
        "
        Row definition for the pm1004vdcAlmsfpWarnDdm 
        table
        "
	INDEX   { pm1004vdcAlmsfpWarnDdmIndex }
	::= { pm1004vdcAlmsfpWarnDdmTable 1 }


Pm1004vdcAlmsfpWarnDdmEntry ::=
	SEQUENCE {
	pm1004vdcAlmsfpWarnDdmIndex
		INTEGER,
	pm1004vdcAlmRxPwrHighWngPortn
		EkiOnOff,
	pm1004vdcAlmRxPwrLowWngPortn
		EkiOnOff,
	pm1004vdcAlmTempHighWngPortn
		EkiOnOff,
	pm1004vdcAlmTempLowWngPortn
		EkiOnOff,
	pm1004vdcAlmVccHighWngPortn
		EkiOnOff,
	pm1004vdcAlmVccLowWngPortn
		EkiOnOff,
	pm1004vdcAlmTxBiasHighWngPortn
		EkiOnOff,
	pm1004vdcAlmTxBiasLowWngPortn
		EkiOnOff,
	pm1004vdcAlmTxPwrHighWngPortn
		EkiOnOff,
	pm1004vdcAlmTxPwLowWngPortn
		EkiOnOff
	}


pm1004vdcAlmsfpWarnDdmIndex OBJECT-TYPE
	SYNTAX  INTEGER(0..128)
	MAX-ACCESS  read-only
	STATUS current
	DESCRIPTION
        "
        Index definition for the pm1004vdcAlmsfpWarnDdm 
        table
        "
	::= { pm1004vdcAlmsfpWarnDdmEntry 1 }


pm1004vdcAlmRxPwrHighWngPortn OBJECT-TYPE
	SYNTAX  EkiOnOff
	MAX-ACCESS read-only
	STATUS current
	DESCRIPTION
        "
        Client SFP Rx Power High Warning 
        :Warning indicating that the SFP 
        input power of port is higher than 
        the threshold value written in
         the SFP EEPROM <Condtype> RX_PWR_HIGH_WNG_1 
        <Probcause> receiveFailure (41) 
        <Alarmtype> equipmentAlarm (5)
         <Polarity> (2) 
        "
	::= { pm1004vdcAlmsfpWarnDdmEntry 17 }


pm1004vdcAlmRxPwrLowWngPortn OBJECT-TYPE
	SYNTAX  EkiOnOff
	MAX-ACCESS read-only
	STATUS current
	DESCRIPTION
        "
        Client SFP Rx Power Low Warning 
        :Warning indicating that the SFP 
        input power of port is lower than 
        the threshold value written in
         the SFP EEPROM <Condtype> RX_PWR_LOW_WNG_1 
        <Probcause> receiveFailure (41) 
        <Alarmtype> equipmentAlarm (5)
         <Polarity> (2) 
        "
	::= { pm1004vdcAlmsfpWarnDdmEntry 16 }


pm1004vdcAlmTempHighWngPortn OBJECT-TYPE
	SYNTAX  EkiOnOff
	MAX-ACCESS read-only
	STATUS current
	DESCRIPTION
        "
        Client SFP Temp High Warning :Warning 
        indicating that the SFP temperature 
        of port is higher than the threshold 
        value written in the SFP EEPROM 
        <Condtype> TEMP_HIGH_WNG_1 <Probcause> 
        temperatureUnacceptable (51) <Alarmtype> 
        equipmentAlarm (5) <Polarity> (2) 
        "
	::= { pm1004vdcAlmsfpWarnDdmEntry 9 }


pm1004vdcAlmTempLowWngPortn OBJECT-TYPE
	SYNTAX  EkiOnOff
	MAX-ACCESS read-only
	STATUS current
	DESCRIPTION
        "
        Client SFP Temp Low Warning :Warning 
        indicating that the SFP temperature 
        of port is lower than the threshold 
        value written in the SFP EEPROM 
        <Condtype> TEMP_LOW_WNG_1 <Probcause> 
        temperatureUnacceptable (51) <Alarmtype> 
        equipmentAlarm (5) <Polarity> (2) 
        "
	::= { pm1004vdcAlmsfpWarnDdmEntry 8 }


pm1004vdcAlmVccHighWngPortn OBJECT-TYPE
	SYNTAX  EkiOnOff
	MAX-ACCESS read-only
	STATUS current
	DESCRIPTION
        "
        Client SFP Power Supply High Warning 
        :Warning indicating that the SFP 
        power supply of port is higher
         than the threshold value written 
        in the SFP EEPROM  <Condtype> VCC_HIGH_WNG_1 
        <Probcause> powerProblem (36) <Alarmtype> 
        equipmentAlarm (5) <Polarity> (2) 
        "
	::= { pm1004vdcAlmsfpWarnDdmEntry 7 }


pm1004vdcAlmVccLowWngPortn OBJECT-TYPE
	SYNTAX  EkiOnOff
	MAX-ACCESS read-only
	STATUS current
	DESCRIPTION
        "
        Client SFP Power Supply Low Warning 
        :Warning indicating that the SFP 
        power supply of port is lower than 
        the threshold value written in
         the SFP EEPROM  <Condtype> VCC_LOW_WNG_1 
        <Probcause> powerProblem (36) <Alarmtype> 
        equipmentAlarm (5) <Polarity> (2) 
        "
	::= { pm1004vdcAlmsfpWarnDdmEntry 6 }


pm1004vdcAlmTxBiasHighWngPortn OBJECT-TYPE
	SYNTAX  EkiOnOff
	MAX-ACCESS read-only
	STATUS current
	DESCRIPTION
        "
        Client SFP Bias High Warning :Warning 
        indicating that the SFP laser bias 
        current of port is higher than
         the threshold value written in 
        the SFP EEPROM <Condtype> TX_BIAS_HIGH_WNG_1 
        <Probcause> transmitterFailure
         (56) <Alarmtype> equipmentAlarm 
        (5) <Polarity> (2) 
        "
	::= { pm1004vdcAlmsfpWarnDdmEntry 5 }


pm1004vdcAlmTxBiasLowWngPortn OBJECT-TYPE
	SYNTAX  EkiOnOff
	MAX-ACCESS read-only
	STATUS current
	DESCRIPTION
        "
        Client SFP Bias Low Warning :Warning 
        indicating that the SFP laser bias 
        current of port is lower than the 
        threshold value written in the
         SFP EEPROM <Condtype> TX_BIAS_LOW_WNG_1 
        <Probcause> transmitterFailure
         (56) <Alarmtype> equipmentAlarm 
        (5) <Polarity> (2) 
        "
	::= { pm1004vdcAlmsfpWarnDdmEntry 4 }


pm1004vdcAlmTxPwrHighWngPortn OBJECT-TYPE
	SYNTAX  EkiOnOff
	MAX-ACCESS read-only
	STATUS current
	DESCRIPTION
        "
        Client SFP Tx Power High Warning 
        :Warning indicating that the SFP 
        output power of port is higher
         than the threshold value written 
        in the SFP EEPROM <Condtype> TX_PWR_HIGH_WNG_1 
        <Probcause> transmitterFailure
         (56) <Alarmtype> equipmentAlarm 
        (5) <Polarity> (2) 
        "
	::= { pm1004vdcAlmsfpWarnDdmEntry 3 }


pm1004vdcAlmTxPwLowWngPortn OBJECT-TYPE
	SYNTAX  EkiOnOff
	MAX-ACCESS read-only
	STATUS current
	DESCRIPTION
        "
        Client SFP Tx Power Low Warning 
        :Warning indicating that the SFP 
        output power of port is lower than 
        the threshold value written in
         the SFP EEPROM <Condtype> TX_PW_LOW_WNG_1 
        <Probcause> transmitterFailure
         (56) <Alarmtype> equipmentAlarm 
        (5) <Polarity> (2) 
        "
	::= { pm1004vdcAlmsfpWarnDdmEntry 2 }


--- *********************************************************
---     TABLE for the pm1004vdcAlmsfpCritDdm articles
--- *********************************************************

pm1004vdcAlmsfpCritDdmTable OBJECT-TYPE
	SYNTAX  SEQUENCE OF Pm1004vdcAlmsfpCritDdmEntry
	MAX-ACCESS not-accessible
	STATUS current
	DESCRIPTION
        "
        List of pm1004vdcAlmsfpCritDdm 
        Article
        "
	::= { pm1004vdcAlmClientNurg 56 }


pm1004vdcAlmsfpCritDdmEntry OBJECT-TYPE
	SYNTAX Pm1004vdcAlmsfpCritDdmEntry
	MAX-ACCESS not-accessible
	STATUS current
	DESCRIPTION
        "
        Row definition for the pm1004vdcAlmsfpCritDdm 
        table
        "
	INDEX   { pm1004vdcAlmsfpCritDdmIndex }
	::= { pm1004vdcAlmsfpCritDdmTable 1 }


Pm1004vdcAlmsfpCritDdmEntry ::=
	SEQUENCE {
	pm1004vdcAlmsfpCritDdmIndex
		INTEGER,
	pm1004vdcAlmRxPwrHighCritPortn
		EkiOnOff,
	pm1004vdcAlmRxPwrLowCritPortn
		EkiOnOff,
	pm1004vdcAlmTxPwrHighCritPortn
		EkiOnOff,
	pm1004vdcAlmTxPwrLowCritPortn
		EkiOnOff
	}


pm1004vdcAlmsfpCritDdmIndex OBJECT-TYPE
	SYNTAX  INTEGER(0..128)
	MAX-ACCESS  read-only
	STATUS current
	DESCRIPTION
        "
        Index definition for the pm1004vdcAlmsfpCritDdm 
        table
        "
	::= { pm1004vdcAlmsfpCritDdmEntry 1 }


pm1004vdcAlmRxPwrHighCritPortn OBJECT-TYPE
	SYNTAX  EkiOnOff
	MAX-ACCESS read-only
	STATUS current
	DESCRIPTION
        "
        Client SFP Custom Rx Power High 
        :Custom Alarm indicating that the 
        SFP input power of port is higher 
        than the custom threshold defined 
        in configuration  <Help>  Custom 
        Alarm indicating that the SFP input 
        power of port is higher than the 
        custom threshold defined in custom 
        configuration <Condtype> RX_PWR_HIGH_CRIT_1 
        <Probcause> receiveFailure (41) 
        <Alarmtype> equipmentAlarm (5)
         <Polarity> (2) 
        "
	::= { pm1004vdcAlmsfpCritDdmEntry 17 }


pm1004vdcAlmRxPwrLowCritPortn OBJECT-TYPE
	SYNTAX  EkiOnOff
	MAX-ACCESS read-only
	STATUS current
	DESCRIPTION
        "
        Client SFP Custom Rx Power Low 
        :Custom Alarm indicating that the 
        SFP input power of port is lower 
        than the custom threshold defined 
        in configuration  <Help>  Custom 
        Alarm indicating that the SFP input 
        power of port is lower than the 
        custom threshold defined in custom 
        configuration <Condtype> RX_PWR_LOW_CRIT_1 
        <Probcause> receiveFailure (41) 
        <Alarmtype> equipmentAlarm (5)
         <Polarity> (2) 
        "
	::= { pm1004vdcAlmsfpCritDdmEntry 16 }


pm1004vdcAlmTxPwrHighCritPortn OBJECT-TYPE
	SYNTAX  EkiOnOff
	MAX-ACCESS read-only
	STATUS current
	DESCRIPTION
        "
        Client SFP Custom Tx Power High 
        :Custom Alarm indicating that the 
        SFP output power of port is higher 
        than the custom threshold defined 
        in configuration  <Help>  Custom 
        Alarm indicating that the SFP output 
        power of port is higher than the 
        custom threshold defined in custom 
        configuration <Condtype> TX_PWR_HIGH_CRIT_1 
        <Probcause> transmitterFailure
         (56) <Alarmtype> equipmentAlarm 
        (5) <Polarity> (2) 
        "
	::= { pm1004vdcAlmsfpCritDdmEntry 3 }


pm1004vdcAlmTxPwrLowCritPortn OBJECT-TYPE
	SYNTAX  EkiOnOff
	MAX-ACCESS read-only
	STATUS current
	DESCRIPTION
        "
        Client SFP Custom Tx Power Low 
        :Custom Alarm indicating that the 
        SFP output power of port is lower 
        than the custom threshold defined 
        in configuration  <Help>  Custom 
        Alarm indicating that the SFP output 
        power of port is lower than the 
        custom threshold defined in custom 
        configuration <Condtype> TX_PWR_LOW_CRIT_1 
        <Probcause> transmitterFailure
         (56) <Alarmtype> equipmentAlarm 
        (5) <Polarity> (2) 
        "
	::= { pm1004vdcAlmsfpCritDdmEntry 2 }


--- *********************************************************
---     TABLE for the pm1004vdcAlmmapperDeAlm articles
--- *********************************************************

pm1004vdcAlmmapperDeAlmTable OBJECT-TYPE
	SYNTAX  SEQUENCE OF Pm1004vdcAlmmapperDeAlmEntry
	MAX-ACCESS not-accessible
	STATUS current
	DESCRIPTION
        "
        List of pm1004vdcAlmmapperDeAlm 
        Article
        "
	::= { pm1004vdcAlmClientCrit 72 }


pm1004vdcAlmmapperDeAlmEntry OBJECT-TYPE
	SYNTAX Pm1004vdcAlmmapperDeAlmEntry
	MAX-ACCESS not-accessible
	STATUS current
	DESCRIPTION
        "
        Row definition for the pm1004vdcAlmmapperDeAlm 
        table
        "
	INDEX   { pm1004vdcAlmmapperDeAlmIndex }
	::= { pm1004vdcAlmmapperDeAlmTable 1 }


Pm1004vdcAlmmapperDeAlmEntry ::=
	SEQUENCE {
	pm1004vdcAlmmapperDeAlmIndex
		INTEGER,
	pm1004vdcAlmDwBufferOvlPortn
		EkiOnOff,
	pm1004vdcAlmDwCsfDetPortn
		EkiOnOff,
	pm1004vdcAlmUpBufferOvlPortn
		EkiOnOff,
	pm1004vdcAlmUpAccOosPortn
		EkiOnOff
	}


pm1004vdcAlmmapperDeAlmIndex OBJECT-TYPE
	SYNTAX  INTEGER(0..128)
	MAX-ACCESS  read-only
	STATUS current
	DESCRIPTION
        "
        Index definition for the pm1004vdcAlmmapperDeAlm 
        table
        "
	::= { pm1004vdcAlmmapperDeAlmEntry 1 }


pm1004vdcAlmDwBufferOvlPortn OBJECT-TYPE
	SYNTAX  EkiOnOff
	MAX-ACCESS read-only
	STATUS current
	DESCRIPTION
        "
        Client Downstream Buffer Overload 
        :This OID indicates that the de-mapper 
        buffer for client port is in overload. 
         <Help>  This alarm indicates if 
        there is a downstream FIFO overload 
        for this client port <Condtype> 
        DW_BUFFER_OVL_1 <Probcause> equipmentMalfunction 
        (16) <Alarmtype> equipmentAlarm 
        (5) <Polarity> (2) 
        "
	::= { pm1004vdcAlmmapperDeAlmEntry 15 }


pm1004vdcAlmDwCsfDetPortn OBJECT-TYPE
	SYNTAX  EkiOnOff
	MAX-ACCESS read-only
	STATUS current
	DESCRIPTION
        "
        Client Signal Fail Detected :This 
        OID indicates that a CSF has been 
        detected on client port in the
         downstream direction   <Help>
          This alarm indicates if a Client 
        Signal Fail has been detected in 
        the incoming line frame for this 
        client port <Condtype> DW_CSF_DET_1 
        <Probcause> receiveFailure (41) 
        <Alarmtype> equipmentAlarm (5)
         <Polarity> (2) 
        "
	::= { pm1004vdcAlmmapperDeAlmEntry 12 }


pm1004vdcAlmUpBufferOvlPortn OBJECT-TYPE
	SYNTAX  EkiOnOff
	MAX-ACCESS read-only
	STATUS current
	DESCRIPTION
        "
        Client Upstream Buffer Overload 
        :This OID indicates that the rate 
        adaptation buffer for client port 
        is in overload.  <Help>  This alarm 
        indicates if there is a upstream 
        FIFO overload for this client port 
        <Condtype> UP_BUFFER_OVL_1 <Probcause> 
        receiveFailure (41) <Alarmtype> 
        integrityViolation (7) <Polarity> 
        (2) 
        "
	::= { pm1004vdcAlmmapperDeAlmEntry 11 }


pm1004vdcAlmUpAccOosPortn OBJECT-TYPE
	SYNTAX  EkiOnOff
	MAX-ACCESS read-only
	STATUS current
	DESCRIPTION
        "
        Client Loss Of Synchro :This OID 
        indicates the upstream client input 
        port has lost synchronization on 
        its decoder   <Help>   This alarms 
        indicates if the input client signal 
        is correctly synchronized with
         the decoder <Condtype> UP_ACC_OOS_1 
        <Probcause> receiveFailure (41) 
        <Alarmtype> integrityViolation
         (7) <Polarity> (2) 
        "
	::= { pm1004vdcAlmmapperDeAlmEntry 2 }


--- *********************************************************
---     TABLE for the pm1004vdcAlmvideoProtocolStatus articles
--- *********************************************************

pm1004vdcAlmvideoProtocolStatusTable OBJECT-TYPE
	SYNTAX  SEQUENCE OF Pm1004vdcAlmvideoProtocolStatusEntry
	MAX-ACCESS not-accessible
	STATUS current
	DESCRIPTION
        "
        List of pm1004vdcAlmvideoProtocolStatus 
        Article
        "
	::= { pm1004vdcAlmClientCrit 112 }


pm1004vdcAlmvideoProtocolStatusEntry OBJECT-TYPE
	SYNTAX Pm1004vdcAlmvideoProtocolStatusEntry
	MAX-ACCESS not-accessible
	STATUS current
	DESCRIPTION
        "
        Row definition for the pm1004vdcAlmvideoProtocolStatus 
        table
        "
	INDEX   { pm1004vdcAlmvideoProtocolStatusIndex }
	::= { pm1004vdcAlmvideoProtocolStatusTable 1 }


Pm1004vdcAlmvideoProtocolStatusEntry ::=
	SEQUENCE {
	pm1004vdcAlmvideoProtocolStatusIndex
		INTEGER,
	pm1004vdcAlmGbeRxPortn
		EkiOnOff,
	pm1004vdcAlmFastEtherRxPortn
		EkiOnOff,
	pm1004vdcAlmDvbAsiRxPortn
		EkiOnOff,
	pm1004vdcAlmHdSdiNtscRxPortn
		EkiOnOff,
	pm1004vdcAlmHdSdiPalRxPortn
		EkiOnOff,
	pm1004vdcAlmSdiRxPortn
		EkiOnOff,
	pm1004vdcAlmGbeTxPortn
		EkiOnOff,
	pm1004vdcAlmFastEtherTxPortn
		EkiOnOff,
	pm1004vdcAlmDvbAsiTxPortn
		EkiOnOff,
	pm1004vdcAlmHdSdiNtscTxPortn
		EkiOnOff,
	pm1004vdcAlmHdSdiPalTxPortn
		EkiOnOff,
	pm1004vdcAlmSdiTxPortn
		EkiOnOff
	}


pm1004vdcAlmvideoProtocolStatusIndex OBJECT-TYPE
	SYNTAX  INTEGER(0..128)
	MAX-ACCESS  read-only
	STATUS current
	DESCRIPTION
        "
        Index definition for the pm1004vdcAlmvideoProtocolStatus 
        table
        "
	::= { pm1004vdcAlmvideoProtocolStatusEntry 1 }


pm1004vdcAlmGbeRxPortn OBJECT-TYPE
	SYNTAX  EkiOnOff
	MAX-ACCESS read-only
	STATUS current
	DESCRIPTION
        "
        Gigabit Ethernet Detected On Rx 
        
 :This OID indicates that the
         Gigabit Ethernet protocol has
         been detected on the port (only 
        significant on Client6-GbE port)
 
         <Help>   This status indicates 
        that the Gigabit Ethernet protocol 
        has been detected on the port (only 
        significant on Client6-GbE port) 
        <Condtype> GBE_RX_1 <Probcause> 
        informationalStatus(1000) <Alarmtype> 
        other (1) <Polarity> (2) 
        "
	::= { pm1004vdcAlmvideoProtocolStatusEntry 15 }


pm1004vdcAlmFastEtherRxPortn OBJECT-TYPE
	SYNTAX  EkiOnOff
	MAX-ACCESS read-only
	STATUS current
	DESCRIPTION
        "
        Fast Ethernet Detected On Rx :This 
        OID indicates that the Fast Ethernet 
        protocol has been detected on the 
        port (only significant on Client1-RJ45 
        port)
  <Help>   This status indicates 
        that the Fast Ethernet protocol 
        has been detected on the port (only 
        significant on Client1-RJ45 port) 
        <Condtype> FAST_ETHER_RX_1 <Probcause> 
        informationalStatus(1000) <Alarmtype> 
        other (1) <Polarity> (2) 
        "
	::= { pm1004vdcAlmvideoProtocolStatusEntry 14 }


pm1004vdcAlmDvbAsiRxPortn OBJECT-TYPE
	SYNTAX  EkiOnOff
	MAX-ACCESS read-only
	STATUS current
	DESCRIPTION
        "
        DVB-ASI Detected On Rx :This OID 
        indicates that the DVB-ASI protocol 
        has been detected on the receive 
        side of the port (only significant 
        on Video2 to Video 5 ports)  <Help> 
          This status indicates that the 
        DVB-ASI protocol has been detected 
        on the receive side of the port 
        (only significant on Video2 to
         Video 5 ports) <Condtype> DVB_ASI_RX_1 
        <Probcause> informationalStatus(1000) 
        <Alarmtype> other (1) <Polarity> 
        (2) 
        "
	::= { pm1004vdcAlmvideoProtocolStatusEntry 13 }


pm1004vdcAlmHdSdiNtscRxPortn OBJECT-TYPE
	SYNTAX  EkiOnOff
	MAX-ACCESS read-only
	STATUS current
	DESCRIPTION
        "
        HD-SDI-NTSC Detected On Rx :This 
        OID indicates that the HD-SDI-NTSC 
        protocol has been detected on the 
        receive side of the port (only
         significant on Video2 to Video 
        5 ports)
  <Help>   This status 
        indicates that the HD-SDI-NTSC
         protocol has been detected on
         the receive side of the port (only 
        significant on Video2 to Video
         5 ports) <Condtype> HD_SDI_NTSC_RX_1 
        <Probcause> informationalStatus(1000) 
        <Alarmtype> other (1) <Polarity> 
        (2) 
        "
	::= { pm1004vdcAlmvideoProtocolStatusEntry 12 }


pm1004vdcAlmHdSdiPalRxPortn OBJECT-TYPE
	SYNTAX  EkiOnOff
	MAX-ACCESS read-only
	STATUS current
	DESCRIPTION
        "
        HD-SDI-PAL Detected On Rx :This 
        OID indicates that the HD-SDI-PAL 
        protocol has been detected on the 
        receive side of the port (only
         significant on Video2 to Video 
        5 ports)
  <Help>   This status 
        indicates that the HD-SDI-PAL protocol 
        has been detected on the receive 
        side of the port (only significant 
        on Video2 to Video 5 ports) <Condtype> 
        HD_SDI_PAL_RX_1 <Probcause> informationalStatus(1000) 
        <Alarmtype> other (1) <Polarity> 
        (2) 
        "
	::= { pm1004vdcAlmvideoProtocolStatusEntry 11 }


pm1004vdcAlmSdiRxPortn OBJECT-TYPE
	SYNTAX  EkiOnOff
	MAX-ACCESS read-only
	STATUS current
	DESCRIPTION
        "
        SDI Detected On Rx :This OID indicates 
        that the SDI protocol has been
         detected on the receive side of 
        the port (only significant on Video2 
        to Video 5 ports)
  <Help>   This 
        status indicates that the SDI protocol 
        has been detected on the receive 
        side of the port (only significant 
        on Video2 to Video 5 ports) <Condtype> 
        SDI_RX_1 <Probcause> informationalStatus(1000) 
        <Alarmtype> other (1) <Polarity> 
        (2) 
        "
	::= { pm1004vdcAlmvideoProtocolStatusEntry 10 }


pm1004vdcAlmGbeTxPortn OBJECT-TYPE
	SYNTAX  EkiOnOff
	MAX-ACCESS read-only
	STATUS current
	DESCRIPTION
        "
        Gigabit Ethernet Detected On Tx 
        
 :This OID indicates that the
         Gigabit Ethernet protocol has
         been detected on the port (only 
        significant on Client6-GbE port)
 
         <Help>   This status indicates 
        that the Gigabit Ethernet protocol 
        has been detected on the port (only 
        significant on Client6-GbE port) 
        <Condtype> GBE_TX_1 <Probcause> 
        informationalStatus(1000) <Alarmtype> 
        other (1) <Polarity> (2) 
        "
	::= { pm1004vdcAlmvideoProtocolStatusEntry 7 }


pm1004vdcAlmFastEtherTxPortn OBJECT-TYPE
	SYNTAX  EkiOnOff
	MAX-ACCESS read-only
	STATUS current
	DESCRIPTION
        "
        Fast Ethernet Detected On Tx :This 
        OID indicates that the Fast Ethernet 
        protocol has been detected on the 
        port (only significant on Client1-RJ45 
        port)
  <Help>   This status indicates 
        that the Fast Ethernet protocol 
        has been detected on the port (only 
        significant on Client1-RJ45 port) 
        <Condtype> FAST_ETHER_TX_1 <Probcause> 
        informationalStatus(1000) <Alarmtype> 
        other (1) <Polarity> (2) 
        "
	::= { pm1004vdcAlmvideoProtocolStatusEntry 6 }


pm1004vdcAlmDvbAsiTxPortn OBJECT-TYPE
	SYNTAX  EkiOnOff
	MAX-ACCESS read-only
	STATUS current
	DESCRIPTION
        "
        DVB-ASI Detected On Tx :This OID 
        indicates that the DVB-ASI protocol 
        has been detected on the transmit 
        side of the port (only significant 
        on Video2 to Video 5 ports)
  <Help> 
          This status indicates that the 
        DVB-ASI protocol has been detected 
        on the transmit side of the port 
        (only significant on Video2 to
         Video 5 ports) <Condtype> DVB_ASI_TX_1 
        <Probcause> informationalStatus(1000) 
        <Alarmtype> other (1) <Polarity> 
        (2) 
        "
	::= { pm1004vdcAlmvideoProtocolStatusEntry 5 }


pm1004vdcAlmHdSdiNtscTxPortn OBJECT-TYPE
	SYNTAX  EkiOnOff
	MAX-ACCESS read-only
	STATUS current
	DESCRIPTION
        "
        HD-SDI-NTSC Detected On Tx :This 
        OID indicates that the HD-SDI-NTSC 
        protocol has been detected on the 
        transmit side of the port (only 
        significant on Video2 to Video
         5 ports)
  <Help>   This status 
        indicates that the HD-SDI-NTSC
         protocol has been detected on
         the transmit side of the port
         (only significant on Video2 to 
        Video 5 ports) <Condtype> HD_SDI_NTSC_TX_1 
        <Probcause> informationalStatus(1000) 
        <Alarmtype> other (1) <Polarity> 
        (2) 
        "
	::= { pm1004vdcAlmvideoProtocolStatusEntry 4 }


pm1004vdcAlmHdSdiPalTxPortn OBJECT-TYPE
	SYNTAX  EkiOnOff
	MAX-ACCESS read-only
	STATUS current
	DESCRIPTION
        "
        HD-SDI-PAL Detected On Tx :This 
        OID indicates that the HD-SDI-PAL 
        protocol has been detected on the 
        transmit side of the port (only 
        significant on Video2 to Video
         5 ports)  <Help>   This status 
        indicates that the HD-SDI-PAL protocol 
        has been detected on the transmit 
        side of the port (only significant 
        on Video2 to Video 5 ports) <Condtype> 
        HD_SDI_PAL_TX_1 <Probcause> informationalStatus(1000) 
        <Alarmtype> other (1) <Polarity> 
        (2) 
        "
	::= { pm1004vdcAlmvideoProtocolStatusEntry 3 }


pm1004vdcAlmSdiTxPortn OBJECT-TYPE
	SYNTAX  EkiOnOff
	MAX-ACCESS read-only
	STATUS current
	DESCRIPTION
        "
        SDI Detected On Tx :This OID indicates 
        that the SDI protocol has been
         detected on the transmit side
         of the port (only significant
         on Video2 to Video 5 ports)  
         <Help>   This status indicates 
        that the SDI protocol has been
         detected on the transmit side
         of the port (only significant
         on Video2 to Video 5 ports) <Condtype> 
        SDI_TX_1 <Probcause> informationalStatus(1000) 
        <Alarmtype> other (1) <Polarity> 
        (2) 
        "
	::= { pm1004vdcAlmvideoProtocolStatusEntry 2 }


--- *********************************************************
---     TABLE for the pm1004vdcAlmdfrmAlm articles
--- *********************************************************

pm1004vdcAlmdfrmAlmTable OBJECT-TYPE
	SYNTAX  SEQUENCE OF Pm1004vdcAlmdfrmAlmEntry
	MAX-ACCESS not-accessible
	STATUS current
	DESCRIPTION
        "
        List of pm1004vdcAlmdfrmAlm Article
        "
	::= { pm1004vdcAlmLineCrit 128 }


pm1004vdcAlmdfrmAlmEntry OBJECT-TYPE
	SYNTAX Pm1004vdcAlmdfrmAlmEntry
	MAX-ACCESS not-accessible
	STATUS current
	DESCRIPTION
        "
        Row definition for the pm1004vdcAlmdfrmAlm 
        table
        "
	INDEX   { pm1004vdcAlmdfrmAlmIndex }
	::= { pm1004vdcAlmdfrmAlmTable 1 }


Pm1004vdcAlmdfrmAlmEntry ::=
	SEQUENCE {
	pm1004vdcAlmdfrmAlmIndex
		INTEGER,
	pm1004vdcAlmDwLossofsyncPortn
		EkiOnOff
	}


pm1004vdcAlmdfrmAlmIndex OBJECT-TYPE
	SYNTAX  INTEGER(0..128)
	MAX-ACCESS  read-only
	STATUS current
	DESCRIPTION
        "
        Index definition for the pm1004vdcAlmdfrmAlm 
        table
        "
	::= { pm1004vdcAlmdfrmAlmEntry 1 }


pm1004vdcAlmDwLossofsyncPortn OBJECT-TYPE
	SYNTAX  EkiOnOff
	MAX-ACCESS read-only
	STATUS current
	DESCRIPTION
        "
        Loss Of Synchronisation :This
         OID indicates the upstream line 
        input port is in Loss of Synchronization. 
         <Help>  This alarms indicates
         if the input signal is correctly 
        synchronized <Condtype> DW_LOSSOFSYNC_1 
        <Probcause> receiveFailure (41) 
        <Alarmtype>  physicalViolation
         (9) <Polarity> (2) 
        "
	::= { pm1004vdcAlmdfrmAlmEntry 5 }


--- *********************************************************
---     TABLE for the pm1004vdcAlmlineSyncAlarms articles
--- *********************************************************

pm1004vdcAlmlineSyncAlarmsTable OBJECT-TYPE
	SYNTAX  SEQUENCE OF Pm1004vdcAlmlineSyncAlarmsEntry
	MAX-ACCESS not-accessible
	STATUS current
	DESCRIPTION
        "
        List of pm1004vdcAlmlineSyncAlarms 
        Article
        "
	::= { pm1004vdcAlmLineCrit 133 }


pm1004vdcAlmlineSyncAlarmsEntry OBJECT-TYPE
	SYNTAX Pm1004vdcAlmlineSyncAlarmsEntry
	MAX-ACCESS not-accessible
	STATUS current
	DESCRIPTION
        "
        Row definition for the pm1004vdcAlmlineSyncAlarms 
        table
        "
	INDEX   { pm1004vdcAlmlineSyncAlarmsIndex }
	::= { pm1004vdcAlmlineSyncAlarmsTable 1 }


Pm1004vdcAlmlineSyncAlarmsEntry ::=
	SEQUENCE {
	pm1004vdcAlmlineSyncAlarmsIndex
		INTEGER,
	pm1004vdcAlmDwLosPortn
		EkiOnOff,
	pm1004vdcAlmUpLockerrPortn
		EkiOnOff,
	pm1004vdcAlmDwLockerrPortn
		EkiOnOff
	}


pm1004vdcAlmlineSyncAlarmsIndex OBJECT-TYPE
	SYNTAX  INTEGER(0..128)
	MAX-ACCESS  read-only
	STATUS current
	DESCRIPTION
        "
        Index definition for the pm1004vdcAlmlineSyncAlarms 
        table
        "
	::= { pm1004vdcAlmlineSyncAlarmsEntry 1 }


pm1004vdcAlmDwLosPortn OBJECT-TYPE
	SYNTAX  EkiOnOff
	MAX-ACCESS read-only
	STATUS current
	DESCRIPTION
        "
        Line Input Loss Of Signal :This 
        OID indicates a loss of signal
         on the 10 Gb/s input.  <Help>
          This alarm indicates if an optical 
        signal is detected on the line
         transceiver input <Condtype> DW_LOS 
        <Probcause> receiveFailure (41) 
        <Alarmtype> physicalViolation (9) 
        <Polarity> (2) 
        "
	::= { pm1004vdcAlmlineSyncAlarmsEntry 17 }


pm1004vdcAlmUpLockerrPortn OBJECT-TYPE
	SYNTAX  EkiOnOff
	MAX-ACCESS read-only
	STATUS current
	DESCRIPTION
        "
        Upstream Clock Lock Error :This 
        OID indicates that the serializer 
        output 10 Gb/s clock multiplier 
        unit is not locked. <Condtype>
         UP_LOCKERR <Probcause> receiveFailure 
        (41) <Alarmtype> equipmentAlarm 
        (5) <Polarity> (2) 
        "
	::= { pm1004vdcAlmlineSyncAlarmsEntry 14 }


pm1004vdcAlmDwLockerrPortn OBJECT-TYPE
	SYNTAX  EkiOnOff
	MAX-ACCESS read-only
	STATUS current
	DESCRIPTION
        "
        Downstream Clock Lock Error :This 
        OID indicates that the deserializer 
        input 10 Gb/s clock recovery is 
        not locked. <Condtype> DW_LOCKERR 
        <Probcause> receiveFailure (41) 
        <Alarmtype> equipmentAlarm (5)
         <Polarity> (2) 
        "
	::= { pm1004vdcAlmlineSyncAlarmsEntry 13 }


--- *****************************************************
---     LEAF for the modInitFailLevel2 article
--- *****************************************************
pm1004vdcAlmmodInitFailLevel2 OBJECT IDENTIFIER ::= { pm1004vdcAlmOtherUrg 194 }




pm1004vdcAlmSwInitFail OBJECT-TYPE
	  SYNTAX EkiOnOff
	  MAX-ACCESS read-only
	  STATUS current
	  DESCRIPTION
        "
        SW Init Fail :This OID indicates 
        that the SW intialization has caused 
        unknown intial conditions  <Help> 
         This alarm indicates if the SW 
        module is correctly initialized 
        <Condtype> SW_INIT_FAIL <Probcause> 
        softwareError (47) <Alarmtype>
         processingErrorAlarm (4) <Polarity> 
        (2) 
        "
	  ::= { pm1004vdcAlmmodInitFailLevel2 5 }



pm1004vdcAlmResetHwInitFail OBJECT-TYPE
	  SYNTAX EkiOnOff
	  MAX-ACCESS read-only
	  STATUS current
	  DESCRIPTION
        "
        Reset HW Init Fail :This OID indicates 
        that the HW intialization has caused 
        unknown intial conditions  <Help> 
         This alarm indicates if the HW 
        has been correctly initialized
         <Condtype> RESET_HW_INIT_FAIL
         <Probcause> softwareError (47) 
        <Alarmtype> processingErrorAlarm 
        (4) <Polarity> (2) 
        "
	  ::= { pm1004vdcAlmmodInitFailLevel2 4 }



pm1004vdcAlmBootUndone OBJECT-TYPE
	  SYNTAX EkiOnOff
	  MAX-ACCESS read-only
	  STATUS current
	  DESCRIPTION
        "
        Boot Undone :This OID indicates 
        that the boot has not been correctly 
        achieved  <Help>  This alarm indicates 
        if the module has correctly boot 
        <Condtype> BOOT_UNDONE <Probcause> 
        softwareError (47) <Alarmtype>
         processingErrorAlarm (4) <Polarity> 
        (2) 
        "
	  ::= { pm1004vdcAlmmodInitFailLevel2 3 }



pm1004vdcAlmNextColdBootForced OBJECT-TYPE
	  SYNTAX EkiOnOff
	  MAX-ACCESS read-only
	  STATUS current
	  DESCRIPTION
        "
        Next Cold Boot Forced :This OID 
        indicates that the next Reset will 
        be forced Cold  <Help>  This alarm 
        indicates that the next reset of 
        the module will be forced to cold 
        reset <Condtype> NEXT_COLD_BOOT_FORCED 
        <Probcause> informationalStatus(1000) 
        <Alarmtype> other (1) <Polarity> 
        (2) 
        "
	  ::= { pm1004vdcAlmmodInitFailLevel2 2 }



pm1004vdcAlmLedFail OBJECT-TYPE
	  SYNTAX EkiOnOff
	  MAX-ACCESS read-only
	  STATUS current
	  DESCRIPTION
        "
        Led Fail :This OID indicates that 
        Led register has not been correctly 
        initalized  <Help>  This alarm
         indicates if the module LEDs are 
        correctly initialized <Condtype> 
        LED_FAIL <Probcause> softwareError 
        (47) <Alarmtype> processingErrorAlarm 
        (4) <Polarity> (2) 
        "
	  ::= { pm1004vdcAlmmodInitFailLevel2 1 }



--- *****************************************************
---     LEAF for the modInitFailLevel3 article
--- *****************************************************
pm1004vdcAlmmodInitFailLevel3 OBJECT IDENTIFIER ::= { pm1004vdcAlmOtherUrg 195 }




pm1004vdcAlmClient6InitFail OBJECT-TYPE
	  SYNTAX EkiOnOff
	  MAX-ACCESS read-only
	  STATUS current
	  DESCRIPTION
        "
        Client6 Init Fail :This OID indicates 
        that Client 6 registers subset
         has not been correctly initialized 
         <Help>  This alarm indicates if 
        the client port 6 is correctly
         initialized <Condtype> CLIENT6_INIT_FAIL 
        <Probcause> softwareError (47)
         <Alarmtype> processingErrorAlarm 
        (4) <Polarity> (2) 
        "
	  ::= { pm1004vdcAlmmodInitFailLevel3 14 }



pm1004vdcAlmClient5InitFail OBJECT-TYPE
	  SYNTAX EkiOnOff
	  MAX-ACCESS read-only
	  STATUS current
	  DESCRIPTION
        "
        Client5 Init Fail :This OID indicates 
        that Client 5 registers subset
         has not been correctly initialized 
         <Help>  This alarm indicates if 
        the client port 5 is correctly
         initialized <Condtype> CLIENT5_INIT_FAIL 
        <Probcause> softwareError (47)
         <Alarmtype> processingErrorAlarm 
        (4) <Polarity> (2) 
        "
	  ::= { pm1004vdcAlmmodInitFailLevel3 13 }



pm1004vdcAlmClient4InitFail OBJECT-TYPE
	  SYNTAX EkiOnOff
	  MAX-ACCESS read-only
	  STATUS current
	  DESCRIPTION
        "
        Client4 Init Fail :This OID indicates 
        that Client 4 registers subset
         has not been correctly initialized 
         <Help>  This alarm indicates if 
        the client port 4 is correctly
         initialized <Condtype> CLIENT4_INIT_FAIL 
        <Probcause> softwareError (47)
         <Alarmtype> processingErrorAlarm 
        (4) <Polarity> (2) 
        "
	  ::= { pm1004vdcAlmmodInitFailLevel3 12 }



pm1004vdcAlmClient3InitFail OBJECT-TYPE
	  SYNTAX EkiOnOff
	  MAX-ACCESS read-only
	  STATUS current
	  DESCRIPTION
        "
        Client3 Init Fail :This OID indicates 
        that Client 3 registers subset
         has not been correctly initialized 
         <Help>  This alarm indicates if 
        the client port 3 is correctly
         initialized <Condtype> CLIENT3_INIT_FAIL 
        <Probcause> softwareError (47)
         <Alarmtype> processingErrorAlarm 
        (4) <Polarity> (2) 
        "
	  ::= { pm1004vdcAlmmodInitFailLevel3 11 }



pm1004vdcAlmClient2InitFail OBJECT-TYPE
	  SYNTAX EkiOnOff
	  MAX-ACCESS read-only
	  STATUS current
	  DESCRIPTION
        "
        Client2 Init Fail :This OID indicates 
        that Client 2 registers subset
         has not been correctly initialized 
         <Help>  This alarm indicates if 
        the client port 2 is correctly
         initialized <Condtype> CLIENT2_INIT_FAIL 
        <Probcause> softwareError (47)
         <Alarmtype> processingErrorAlarm 
        (4) <Polarity> (2) 
        "
	  ::= { pm1004vdcAlmmodInitFailLevel3 10 }



pm1004vdcAlmClient1InitFail OBJECT-TYPE
	  SYNTAX EkiOnOff
	  MAX-ACCESS read-only
	  STATUS current
	  DESCRIPTION
        "
        Client1 Init Fail :This OID indicates 
        that Client 1 registers subset
         has not been correctly initialized 
         <Help>  This alarm indicates if 
        the client port 1 is correctly
         initialized <Condtype> CLIENT1_INIT_FAIL 
        <Probcause> softwareError (47)
         <Alarmtype> processingErrorAlarm 
        (4) <Polarity> (2) 
        "
	  ::= { pm1004vdcAlmmodInitFailLevel3 9 }



pm1004vdcAlmLine2InitFail OBJECT-TYPE
	  SYNTAX EkiOnOff
	  MAX-ACCESS read-only
	  STATUS current
	  DESCRIPTION
        "
        Line2 Init Fail :This OID indicates 
        that the Line register subset has 
        not been correctly initialized
          <Help>  This alarm indicates
         if the line port 2 is correctly 
        initialized <Condtype> LINE2_INIT_FAIL 
        <Probcause> softwareError (47)
         <Alarmtype> processingErrorAlarm 
        (4) <Polarity> (2) 
        "
	  ::= { pm1004vdcAlmmodInitFailLevel3 8 }



pm1004vdcAlmLine1InitFail OBJECT-TYPE
	  SYNTAX EkiOnOff
	  MAX-ACCESS read-only
	  STATUS current
	  DESCRIPTION
        "
        Line1 Init Fail :This OID indicates 
        that the Line registersvsubset
         has not been correctly initialized 
         <Help>  This alarm indicates if 
        the line port 1 is correctly initialized 
        <Condtype> LINE1_INIT_FAIL <Probcause> 
        softwareError (47) <Alarmtype>
         processingErrorAlarm (4) <Polarity> 
        (2) 
        "
	  ::= { pm1004vdcAlmmodInitFailLevel3 7 }



pm1004vdcAlmXfp2InitFail OBJECT-TYPE
	  SYNTAX EkiOnOff
	  MAX-ACCESS read-only
	  STATUS current
	  DESCRIPTION
        "
        XFP2 Init Fail :This OID indicates 
        that the XFP has not been correctly 
        initialized  <Help>  This alarm 
        indicates if the line transceiver 
        2 is correctly initialized <Condtype> 
        XFP2_INIT_FAIL <Probcause> softwareError 
        (47) <Alarmtype> processingErrorAlarm 
        (4) <Polarity> (2) 
        "
	  ::= { pm1004vdcAlmmodInitFailLevel3 6 }



pm1004vdcAlmXfp1InitFail OBJECT-TYPE
	  SYNTAX EkiOnOff
	  MAX-ACCESS read-only
	  STATUS current
	  DESCRIPTION
        "
        XFP1 Init Fail :This OID indicates 
        that the XFP has not been correctly 
        initialized  <Help>  This alarm 
        indicates if the line transceiver 
        1 is correctly initialized <Condtype> 
        XFP1_INIT_FAIL <Probcause> softwareError 
        (47) <Alarmtype> processingErrorAlarm 
        (4) <Polarity> (2) 
        "
	  ::= { pm1004vdcAlmmodInitFailLevel3 5 }



pm1004vdcAlmInitModuleFail OBJECT-TYPE
	  SYNTAX EkiOnOff
	  MAX-ACCESS read-only
	  STATUS current
	  DESCRIPTION
        "
        Init Module Fail :This OID indicates 
        that the Module has not been correctly 
        initialized  <Help>  This alarm 
        indicates if the SW module is correctly 
        initialized <Condtype> INIT_MODULE_FAIL 
        <Probcause> softwareError (47)
         <Alarmtype> processingErrorAlarm 
        (4) <Polarity> (2) 
        "
	  ::= { pm1004vdcAlmmodInitFailLevel3 3 }



pm1004vdcAlmObmTypeReadFail OBJECT-TYPE
	  SYNTAX EkiOnOff
	  MAX-ACCESS read-only
	  STATUS current
	  DESCRIPTION
        "
        OBM Type Read Fail :This OID indicates 
        that OBM type has not been recognized 
         <Help>  This alarm indicates if 
        the OBM board has been correctly 
        identified <Condtype> OBM_TYPE_READ_FAIL 
        <Probcause> softwareError (47)
         <Alarmtype> processingErrorAlarm 
        (4) <Polarity> (2) 
        "
	  ::= { pm1004vdcAlmmodInitFailLevel3 2 }



pm1004vdcAlmGwIdentFail OBJECT-TYPE
	  SYNTAX EkiOnOff
	  MAX-ACCESS read-only
	  STATUS current
	  DESCRIPTION
        "
        GW Ident Fail :This OID indicates 
        that GW identification has not
         been read  <Help>  This alarm
         indicates if the GW has been correctly 
        identified <Condtype> GW_IDENT_FAIL 
        <Probcause> softwareError (47)
         <Alarmtype> processingErrorAlarm 
        (4) <Polarity> (2) 
        "
	  ::= { pm1004vdcAlmmodInitFailLevel3 1 }



--- *****************************************************
---     LEAF for the clientRxProt article
--- *****************************************************
pm1004vdcAlmclientRxProt OBJECT IDENTIFIER ::= { pm1004vdcAlmOtherUrg 198 }




pm1004vdcAlmAdddropClient6East OBJECT-TYPE
	  SYNTAX EkiOnOff
	  MAX-ACCESS read-only
	  STATUS current
	  DESCRIPTION
        "
        Client East Rx Side Active :This 
        OID indicates the Client is active 
        on East receiving side <Condtype> 
        ADDDROP_CLIENT6_EAST <Probcause> 
        other (1) <Alarmtype> other (1) 
        <Polarity> (2) 
        "
	  ::= { pm1004vdcAlmclientRxProt 14 }



pm1004vdcAlmAdddropClient5East OBJECT-TYPE
	  SYNTAX EkiOnOff
	  MAX-ACCESS read-only
	  STATUS current
	  DESCRIPTION
        "
        Client East Rx Side Active :This 
        OID indicates the Client is active 
        on East receiving side <Condtype> 
        ADDDROP_CLIENT5_EAST <Probcause> 
        other (1) <Alarmtype> other (1) 
        <Polarity> (2) 
        "
	  ::= { pm1004vdcAlmclientRxProt 13 }



pm1004vdcAlmAdddropClient4East OBJECT-TYPE
	  SYNTAX EkiOnOff
	  MAX-ACCESS read-only
	  STATUS current
	  DESCRIPTION
        "
        Client East Rx Side Active :This 
        OID indicates the Client is active 
        on East receiving side <Condtype> 
        ADDDROP_CLIENT4_EAST <Probcause> 
        other (1) <Alarmtype> other (1) 
        <Polarity> (2) 
        "
	  ::= { pm1004vdcAlmclientRxProt 12 }



pm1004vdcAlmAdddropClient3East OBJECT-TYPE
	  SYNTAX EkiOnOff
	  MAX-ACCESS read-only
	  STATUS current
	  DESCRIPTION
        "
        Client East Rx Side Active :This 
        OID indicates the Client is active 
        on East receiving side <Condtype> 
        ADDDROP_CLIENT3_EAST <Probcause> 
        other (1) <Alarmtype> other (1) 
        <Polarity> (2) 
        "
	  ::= { pm1004vdcAlmclientRxProt 11 }



pm1004vdcAlmAdddropClient2East OBJECT-TYPE
	  SYNTAX EkiOnOff
	  MAX-ACCESS read-only
	  STATUS current
	  DESCRIPTION
        "
        Client East Rx Side Active :This 
        OID indicates the Client is active 
        on East receiving side <Condtype> 
        ADDDROP_CLIENT2_EAST <Probcause> 
        other (1) <Alarmtype> other (1) 
        <Polarity> (2) 
        "
	  ::= { pm1004vdcAlmclientRxProt 10 }



pm1004vdcAlmAdddropClient1East OBJECT-TYPE
	  SYNTAX EkiOnOff
	  MAX-ACCESS read-only
	  STATUS current
	  DESCRIPTION
        "
        Client East Rx Side Active :This 
        OID indicates the Client is active 
        on East receiving side <Condtype> 
        ADDDROP_CLIENT1_EAST <Probcause> 
        other (1) <Alarmtype> other (1) 
        <Polarity> (2) 
        "
	  ::= { pm1004vdcAlmclientRxProt 9 }



pm1004vdcAlmAdddropClient6West OBJECT-TYPE
	  SYNTAX EkiOnOff
	  MAX-ACCESS read-only
	  STATUS current
	  DESCRIPTION
        "
        Client West Rx Side Active :This 
        OID indicates the Client is active 
        on West receiving side <Condtype> 
        ADDDROP_CLIENT6_WEST <Probcause> 
        other (1) <Alarmtype> other (1) 
        <Polarity> (2) 
        "
	  ::= { pm1004vdcAlmclientRxProt 6 }



pm1004vdcAlmAdddropClient5West OBJECT-TYPE
	  SYNTAX EkiOnOff
	  MAX-ACCESS read-only
	  STATUS current
	  DESCRIPTION
        "
        Client West Rx Side Active :This 
        OID indicates the Client is active 
        on West receiving side <Condtype> 
        ADDDROP_CLIENT5_WEST <Probcause> 
        other (1) <Alarmtype> other (1) 
        <Polarity> (2) 
        "
	  ::= { pm1004vdcAlmclientRxProt 5 }



pm1004vdcAlmAdddropClient4West OBJECT-TYPE
	  SYNTAX EkiOnOff
	  MAX-ACCESS read-only
	  STATUS current
	  DESCRIPTION
        "
        Client West Rx Side Active :This 
        OID indicates the Client is active 
        on West receiving side <Condtype> 
        ADDDROP_CLIENT4_WEST <Probcause> 
        other (1) <Alarmtype> other (1) 
        <Polarity> (2) 
        "
	  ::= { pm1004vdcAlmclientRxProt 4 }



pm1004vdcAlmAdddropClient3West OBJECT-TYPE
	  SYNTAX EkiOnOff
	  MAX-ACCESS read-only
	  STATUS current
	  DESCRIPTION
        "
        Client West Rx Side Active :This 
        OID indicates the Client is active 
        on West receiving side <Condtype> 
        ADDDROP_CLIENT3_WEST <Probcause> 
        other (1) <Alarmtype> other (1) 
        <Polarity> (2) 
        "
	  ::= { pm1004vdcAlmclientRxProt 3 }



pm1004vdcAlmAdddropClient2West OBJECT-TYPE
	  SYNTAX EkiOnOff
	  MAX-ACCESS read-only
	  STATUS current
	  DESCRIPTION
        "
        Client West Rx Side Active :This 
        OID indicates the Client is active 
        on West receiving side <Condtype> 
        ADDDROP_CLIENT2_WEST <Probcause> 
        other (1) <Alarmtype> other (1) 
        <Polarity> (2) 
        "
	  ::= { pm1004vdcAlmclientRxProt 2 }



pm1004vdcAlmAdddropClient1West OBJECT-TYPE
	  SYNTAX EkiOnOff
	  MAX-ACCESS read-only
	  STATUS current
	  DESCRIPTION
        "
        Client West Rx Side Active :This 
        OID indicates the Client is active 
        on West receiving side <Condtype> 
        ADDDROP_CLIENT1_WEST <Probcause> 
        other (1) <Alarmtype> other (1) 
        <Polarity> (2) 
        "
	  ::= { pm1004vdcAlmclientRxProt 1 }



--- *********************************************************
---     TABLE for the pm1004vdcAlmlineXfp1Alarm articles
--- *********************************************************

pm1004vdcAlmlineXfp1AlarmTable OBJECT-TYPE
	SYNTAX  SEQUENCE OF Pm1004vdcAlmlineXfp1AlarmEntry
	MAX-ACCESS not-accessible
	STATUS current
	DESCRIPTION
        "
        List of pm1004vdcAlmlineXfp1Alarm 
        Article
        "
	::= { pm1004vdcAlmLineUrg 208 }


pm1004vdcAlmlineXfp1AlarmEntry OBJECT-TYPE
	SYNTAX Pm1004vdcAlmlineXfp1AlarmEntry
	MAX-ACCESS not-accessible
	STATUS current
	DESCRIPTION
        "
        Row definition for the pm1004vdcAlmlineXfp1Alarm 
        table
        "
	INDEX   { pm1004vdcAlmlineXfp1AlarmIndex }
	::= { pm1004vdcAlmlineXfp1AlarmTable 1 }


Pm1004vdcAlmlineXfp1AlarmEntry ::=
	SEQUENCE {
	pm1004vdcAlmlineXfp1AlarmIndex
		INTEGER,
	pm1004vdcAlmRxPowerHighAlarmPortn
		EkiOnOff,
	pm1004vdcAlmRxPowerLowAlarmPortn
		EkiOnOff,
	pm1004vdcAlmTempHighAlarmPortn
		EkiOnOff,
	pm1004vdcAlmTempLowAlarmPortn
		EkiOnOff,
	pm1004vdcAlmTxBiasHighAlarmPortn
		EkiOnOff,
	pm1004vdcAlmTxBiasLowAlarmPortn
		EkiOnOff,
	pm1004vdcAlmTxPowerHighAlarmPortn
		EkiOnOff,
	pm1004vdcAlmTxPowerLowAlarmPortn
		EkiOnOff
	}


pm1004vdcAlmlineXfp1AlarmIndex OBJECT-TYPE
	SYNTAX  INTEGER(0..128)
	MAX-ACCESS  read-only
	STATUS current
	DESCRIPTION
        "
        Index definition for the pm1004vdcAlmlineXfp1Alarm 
        table
        "
	::= { pm1004vdcAlmlineXfp1AlarmEntry 1 }


pm1004vdcAlmRxPowerHighAlarmPortn OBJECT-TYPE
	SYNTAX  EkiOnOff
	MAX-ACCESS read-only
	STATUS current
	DESCRIPTION
        "
        Line Optical Rx Power High :Alarm 
        indicating that the XFP received 
        optical power is higher than the 
        threshold value written in the
         XFP EEPROM <Condtype> RX_POWER_HIGH_ALARM_1 
        <Probcause> receiveFailure (41) 
        <Alarmtype> equipmentAlarm (5)
         <Polarity> (2) 
        "
	::= { pm1004vdcAlmlineXfp1AlarmEntry 17 }


pm1004vdcAlmRxPowerLowAlarmPortn OBJECT-TYPE
	SYNTAX  EkiOnOff
	MAX-ACCESS read-only
	STATUS current
	DESCRIPTION
        "
        Line Optical Rx Power Low :Alarm 
        indicating that the XFP received 
        optical power is lower than the 
        threshold value written in the
         XFP EEPROM  <Condtype> RX_POWER_LOW_ALARM_1 
        <Probcause> receiveFailure (41) 
        <Alarmtype> equipmentAlarm (5)
         <Polarity> (2) 
        "
	::= { pm1004vdcAlmlineXfp1AlarmEntry 16 }


pm1004vdcAlmTempHighAlarmPortn OBJECT-TYPE
	SYNTAX  EkiOnOff
	MAX-ACCESS read-only
	STATUS current
	DESCRIPTION
        "
        Line Transceiver Temp High :Alarm 
        indicating that the XFP/OTX temperature 
        is higher than the threshold value 
        written in the XFP EEPROM <Condtype> 
        TEMP_HIGH_ALARM_1 <Probcause> temperatureUnacceptable 
        (51) <Alarmtype> equipmentAlarm 
        (5) <Polarity> (2) 
        "
	::= { pm1004vdcAlmlineXfp1AlarmEntry 9 }


pm1004vdcAlmTempLowAlarmPortn OBJECT-TYPE
	SYNTAX  EkiOnOff
	MAX-ACCESS read-only
	STATUS current
	DESCRIPTION
        "
        Line Transceiver Temp Low :Alarm 
        indicating that the XFP/OTX temperature 
        is lower than the threshold value 
        written in the XFP/OTX EEPROM <Condtype> 
        TEMP_LOW_ALARM_1 <Probcause> temperatureUnacceptable 
        (51) <Alarmtype> equipmentAlarm 
        (5) <Polarity> (2) 
        "
	::= { pm1004vdcAlmlineXfp1AlarmEntry 8 }


pm1004vdcAlmTxBiasHighAlarmPortn OBJECT-TYPE
	SYNTAX  EkiOnOff
	MAX-ACCESS read-only
	STATUS current
	DESCRIPTION
        "
        Line Transceiver Bias High :Alarm 
        indicating that the XFP/OTX transmitter 
        laser bias current is higher than 
        the threshold value written in
         the XFP EEPROM <Condtype> TX_BIAS_HIGH_ALARM_1 
        <Probcause> transmitterFailure
         (56) <Alarmtype> equipmentAlarm 
        (5) <Polarity> (2) 
        "
	::= { pm1004vdcAlmlineXfp1AlarmEntry 5 }


pm1004vdcAlmTxBiasLowAlarmPortn OBJECT-TYPE
	SYNTAX  EkiOnOff
	MAX-ACCESS read-only
	STATUS current
	DESCRIPTION
        "
        Line Transceiver Bias Low :Alarm 
        indicating that the XFP/OTX transmitter 
        laser bias current is lower than 
        the threshold value written in
         the XFP/OTX EEPROM <Condtype>
         TX_BIAS_LOW_ALARM_1 <Probcause> 
        transmitterFailure (56) <Alarmtype> 
        equipmentAlarm (5) <Polarity> (2) 
        "
	::= { pm1004vdcAlmlineXfp1AlarmEntry 4 }


pm1004vdcAlmTxPowerHighAlarmPortn OBJECT-TYPE
	SYNTAX  EkiOnOff
	MAX-ACCESS read-only
	STATUS current
	DESCRIPTION
        "
        Line Optical Tx Power High :Alarm 
        indicating that the XFP/OTX transmitter 
        transmitter output power is higher 
        than the threshold value written 
        in the XFP EEPROM <Condtype> TX_POWER_HIGH_ALARM_1 
        <Probcause> transmitterFailure
         (56) <Alarmtype> equipmentAlarm 
        (5) <Polarity> (2) 
        "
	::= { pm1004vdcAlmlineXfp1AlarmEntry 3 }


pm1004vdcAlmTxPowerLowAlarmPortn OBJECT-TYPE
	SYNTAX  EkiOnOff
	MAX-ACCESS read-only
	STATUS current
	DESCRIPTION
        "
        Line Optical Tx Power Low :Alarm 
        indicating that the XFP/OTX transmitter 
        transmitter output power is lower 
        than the threshold value written 
        in the XFP/OTX EEPROM <Condtype> 
        TX_POWER_LOW_ALARM_1 <Probcause> 
        transmitterFailure (56) <Alarmtype> 
        equipmentAlarm (5) <Polarity> (2) 
        "
	::= { pm1004vdcAlmlineXfp1AlarmEntry 2 }


--- *********************************************************
---     TABLE for the pm1004vdcAlmlineXfp1Warnings articles
--- *********************************************************

pm1004vdcAlmlineXfp1WarningsTable OBJECT-TYPE
	SYNTAX  SEQUENCE OF Pm1004vdcAlmlineXfp1WarningsEntry
	MAX-ACCESS not-accessible
	STATUS current
	DESCRIPTION
        "
        List of pm1004vdcAlmlineXfp1Warnings 
        Article
        "
	::= { pm1004vdcAlmLineNurg 209 }


pm1004vdcAlmlineXfp1WarningsEntry OBJECT-TYPE
	SYNTAX Pm1004vdcAlmlineXfp1WarningsEntry
	MAX-ACCESS not-accessible
	STATUS current
	DESCRIPTION
        "
        Row definition for the pm1004vdcAlmlineXfp1Warnings 
        table
        "
	INDEX   { pm1004vdcAlmlineXfp1WarningsIndex }
	::= { pm1004vdcAlmlineXfp1WarningsTable 1 }


Pm1004vdcAlmlineXfp1WarningsEntry ::=
	SEQUENCE {
	pm1004vdcAlmlineXfp1WarningsIndex
		INTEGER,
	pm1004vdcAlmRxPowerHighWarningPortn
		EkiOnOff,
	pm1004vdcAlmRxPowerLowWarningPortn
		EkiOnOff,
	pm1004vdcAlmTempHighWarningPortn
		EkiOnOff,
	pm1004vdcAlmTempLowWarningPortn
		EkiOnOff,
	pm1004vdcAlmTxBiasHighWarningPortn
		EkiOnOff,
	pm1004vdcAlmTxBiasLowWarningPortn
		EkiOnOff,
	pm1004vdcAlmTxPowerHighWarningPortn
		EkiOnOff,
	pm1004vdcAlmTxPowerLowWarningPortn
		EkiOnOff
	}


pm1004vdcAlmlineXfp1WarningsIndex OBJECT-TYPE
	SYNTAX  INTEGER(0..128)
	MAX-ACCESS  read-only
	STATUS current
	DESCRIPTION
        "
        Index definition for the pm1004vdcAlmlineXfp1Warnings 
        table
        "
	::= { pm1004vdcAlmlineXfp1WarningsEntry 1 }


pm1004vdcAlmRxPowerHighWarningPortn OBJECT-TYPE
	SYNTAX  EkiOnOff
	MAX-ACCESS read-only
	STATUS current
	DESCRIPTION
        "
        Line Optical Rx Power High Warning 
        :Warning indicating that the XFP 
        received optical power is higher 
        than the threshold value written 
        in the XFP EEPROM <Condtype> RX_POWER_HIGH_WARNING_1 
        <Probcause> receiveFailure (41) 
        <Alarmtype> equipmentAlarm (5)
         <Polarity> (2) 
        "
	::= { pm1004vdcAlmlineXfp1WarningsEntry 17 }


pm1004vdcAlmRxPowerLowWarningPortn OBJECT-TYPE
	SYNTAX  EkiOnOff
	MAX-ACCESS read-only
	STATUS current
	DESCRIPTION
        "
        Line Optical Rx Power Low Warning 
        :Warning indicating that the XFP 
        received optical power is lower 
        than the threshold value written 
        in the XFP EEPROM  <Condtype> RX_POWER_LOW_WARNING_1 
        <Probcause> receiveFailure (41) 
        <Alarmtype> equipmentAlarm (5)
         <Polarity> (2) 
        "
	::= { pm1004vdcAlmlineXfp1WarningsEntry 16 }


pm1004vdcAlmTempHighWarningPortn OBJECT-TYPE
	SYNTAX  EkiOnOff
	MAX-ACCESS read-only
	STATUS current
	DESCRIPTION
        "
        Line Transceiver Temp High Warning 
        :Warning indicating that the XFP/OTX 
        temperature is higher than the
         threshold value written in the 
        XFP EEPROM <Condtype> TEMP_HIGH_WARNING_1 
        <Probcause> temperatureUnacceptable 
        (51) <Alarmtype> equipmentAlarm 
        (5) <Polarity> (2) 
        "
	::= { pm1004vdcAlmlineXfp1WarningsEntry 9 }


pm1004vdcAlmTempLowWarningPortn OBJECT-TYPE
	SYNTAX  EkiOnOff
	MAX-ACCESS read-only
	STATUS current
	DESCRIPTION
        "
        Line Transceiver Temp Low Warning 
        :Warning indicating that the XFP/OTX 
        temperature is lower than the threshold 
        value written in the XFP/OTX EEPROM 
        <Condtype> TEMP_LOW_WARNING_1 <Probcause> 
        temperatureUnacceptable (51) <Alarmtype> 
        equipmentAlarm (5) <Polarity> (2) 
        "
	::= { pm1004vdcAlmlineXfp1WarningsEntry 8 }


pm1004vdcAlmTxBiasHighWarningPortn OBJECT-TYPE
	SYNTAX  EkiOnOff
	MAX-ACCESS read-only
	STATUS current
	DESCRIPTION
        "
        Line Transceiver Bias High Warning 
        :Warning indicating that the XFP/OTX 
        transmitter laser bias current
         is higher than the threshold value 
        written in the XFP EEPROM <Condtype> 
        TX_BIAS_HIGH_WARNING_1 <Probcause> 
        transmitterFailure (56) <Alarmtype> 
        equipmentAlarm (5) <Polarity> (2) 
        "
	::= { pm1004vdcAlmlineXfp1WarningsEntry 5 }


pm1004vdcAlmTxBiasLowWarningPortn OBJECT-TYPE
	SYNTAX  EkiOnOff
	MAX-ACCESS read-only
	STATUS current
	DESCRIPTION
        "
        Line Transceiver Bias Low Warning 
        :Warning indicating that the XFP/OTX 
        transmitter laser bias current
         is lower than the threshold value 
        written in the XFP/OTX EEPROM <Condtype> 
        TX_BIAS_LOW_WARNING_1 <Probcause> 
        transmitterFailure (56) <Alarmtype> 
        equipmentAlarm (5) <Polarity> (2) 
        "
	::= { pm1004vdcAlmlineXfp1WarningsEntry 4 }


pm1004vdcAlmTxPowerHighWarningPortn OBJECT-TYPE
	SYNTAX  EkiOnOff
	MAX-ACCESS read-only
	STATUS current
	DESCRIPTION
        "
        Line Optical Tx Power High Warning 
        :Warning indicating that the XFP/OTX 
        transmitter transmitter output
         power is higher than the threshold 
        value written in the XFP EEPROM 
        <Condtype> TX_POWER_HIGH_WARNING_1 
        <Probcause> transmitterFailure
         (56) <Alarmtype> equipmentAlarm 
        (5) <Polarity> (2) 
        "
	::= { pm1004vdcAlmlineXfp1WarningsEntry 3 }


pm1004vdcAlmTxPowerLowWarningPortn OBJECT-TYPE
	SYNTAX  EkiOnOff
	MAX-ACCESS read-only
	STATUS current
	DESCRIPTION
        "
        Line Optical Tx Power Low Warning 
        :Warning indicating that the XFP/OTX 
        transmitter transmitter output
         power is lower than the threshold 
        value written in the XFP/OTX EEPROM 
        <Condtype> TX_POWER_LOW_WARNING_1 
        <Probcause> transmitterFailure
         (56) <Alarmtype> equipmentAlarm 
        (5) <Polarity> (2) 
        "
	::= { pm1004vdcAlmlineXfp1WarningsEntry 2 }


--- *********************************************************
---     TABLE for the pm1004vdcAlmlineXfp1Crit articles
--- *********************************************************

pm1004vdcAlmlineXfp1CritTable OBJECT-TYPE
	SYNTAX  SEQUENCE OF Pm1004vdcAlmlineXfp1CritEntry
	MAX-ACCESS not-accessible
	STATUS current
	DESCRIPTION
        "
        List of pm1004vdcAlmlineXfp1Crit 
        Article
        "
	::= { pm1004vdcAlmLineUrg 210 }


pm1004vdcAlmlineXfp1CritEntry OBJECT-TYPE
	SYNTAX Pm1004vdcAlmlineXfp1CritEntry
	MAX-ACCESS not-accessible
	STATUS current
	DESCRIPTION
        "
        Row definition for the pm1004vdcAlmlineXfp1Crit 
        table
        "
	INDEX   { pm1004vdcAlmlineXfp1CritIndex }
	::= { pm1004vdcAlmlineXfp1CritTable 1 }


Pm1004vdcAlmlineXfp1CritEntry ::=
	SEQUENCE {
	pm1004vdcAlmlineXfp1CritIndex
		INTEGER,
	pm1004vdcAlmRxPowerHighCritPortn
		EkiOnOff,
	pm1004vdcAlmRxPowerLowCritPortn
		EkiOnOff,
	pm1004vdcAlmTxPowerHighCritPortn
		EkiOnOff,
	pm1004vdcAlmTxPowerLowCritPortn
		EkiOnOff
	}


pm1004vdcAlmlineXfp1CritIndex OBJECT-TYPE
	SYNTAX  INTEGER(0..128)
	MAX-ACCESS  read-only
	STATUS current
	DESCRIPTION
        "
        Index definition for the pm1004vdcAlmlineXfp1Crit 
        table
        "
	::= { pm1004vdcAlmlineXfp1CritEntry 1 }


pm1004vdcAlmRxPowerHighCritPortn OBJECT-TYPE
	SYNTAX  EkiOnOff
	MAX-ACCESS read-only
	STATUS current
	DESCRIPTION
        "
        Line Custom Rx Power High :Custom 
        Alarm indicating that the XFP/OTX 
        input power of port is higher than 
        the custom threshold defined in 
        configuration  <Help>  Custom Alarm 
        indicating that the XFP/OTX input 
        power of port is higher than the 
        custom threshold defined in custom 
        configuration <Condtype> RX_POWER_HIGH_CRIT_1 
        <Probcause> receiveFailure (41) 
        <Alarmtype> equipmentAlarm (5)
         <Polarity> (2) 
        "
	::= { pm1004vdcAlmlineXfp1CritEntry 17 }


pm1004vdcAlmRxPowerLowCritPortn OBJECT-TYPE
	SYNTAX  EkiOnOff
	MAX-ACCESS read-only
	STATUS current
	DESCRIPTION
        "
        Line Custom Rx Power Low :Custom 
        Alarm indicating that the XFP/OTX 
        input power of port is lower than 
        the custom threshold defined in 
        configuration  <Help>  Custom Alarm 
        indicating that the XFP/OTX input 
        power of port is lower than the 
        custom threshold defined in custom 
        configuration <Condtype> RX_POWER_LOW_CRIT_1 
        <Probcause> receiveFailure (41) 
        <Alarmtype> equipmentAlarm (5)
         <Polarity> (2) 
        "
	::= { pm1004vdcAlmlineXfp1CritEntry 16 }


pm1004vdcAlmTxPowerHighCritPortn OBJECT-TYPE
	SYNTAX  EkiOnOff
	MAX-ACCESS read-only
	STATUS current
	DESCRIPTION
        "
        Line Custom Tx Power High :Custom 
        Alarm indicating that the XFP/OTX 
        output power of port is higher
         than the custom threshold defined 
        in configuration  <Help>  Custom 
        Alarm indicating that the XFP/OTX 
        output power of port is higher
         than the custom threshold defined 
        in custom configuration <Condtype> 
        TX_POWER_HIGH_CRIT_1 <Probcause> 
        transmitterFailure (56) <Alarmtype> 
        equipmentAlarm (5) <Polarity> (2) 
        "
	::= { pm1004vdcAlmlineXfp1CritEntry 3 }


pm1004vdcAlmTxPowerLowCritPortn OBJECT-TYPE
	SYNTAX  EkiOnOff
	MAX-ACCESS read-only
	STATUS current
	DESCRIPTION
        "
        Line Custom Tx Power Low :Custom 
        Alarm indicating that the XFP/OTX 
        output power of port is lower than 
        the custom threshold defined in 
        configuration  <Help>  Custom Alarm 
        indicating that the XFP/OTX output 
        power of port is lower than the 
        custom threshold defined in custom 
        configuration <Condtype> TX_POWER_LOW_CRIT_1 
        <Probcause> transmitterFailure
         (56) <Alarmtype> equipmentAlarm 
        (5) <Polarity> (2) 
        "
	::= { pm1004vdcAlmlineXfp1CritEntry 2 }


--- *********************************************************
---     TABLE for the pm1004vdcAlmlineXfp1Alarms articles
--- *********************************************************

pm1004vdcAlmlineXfp1AlarmsTable OBJECT-TYPE
	SYNTAX  SEQUENCE OF Pm1004vdcAlmlineXfp1AlarmsEntry
	MAX-ACCESS not-accessible
	STATUS current
	DESCRIPTION
        "
        List of pm1004vdcAlmlineXfp1Alarms 
        Article
        "
	::= { pm1004vdcAlmLineCrit 211 }


pm1004vdcAlmlineXfp1AlarmsEntry OBJECT-TYPE
	SYNTAX Pm1004vdcAlmlineXfp1AlarmsEntry
	MAX-ACCESS not-accessible
	STATUS current
	DESCRIPTION
        "
        Row definition for the pm1004vdcAlmlineXfp1Alarms 
        table
        "
	INDEX   { pm1004vdcAlmlineXfp1AlarmsIndex }
	::= { pm1004vdcAlmlineXfp1AlarmsTable 1 }


Pm1004vdcAlmlineXfp1AlarmsEntry ::=
	SEQUENCE {
	pm1004vdcAlmlineXfp1AlarmsIndex
		INTEGER,
	pm1004vdcAlmApdSupplyFaultPortn
		EkiOnOff,
	pm1004vdcAlmTecFaultPortn
		EkiOnOff,
	pm1004vdcAlmWavelengthUnlockedPortn
		EkiOnOff,
	pm1004vdcAlmTxNrPortn
		EkiOnOff,
	pm1004vdcAlmTxFaultPortn
		EkiOnOff,
	pm1004vdcAlmTxCdrNotLockedPortn
		EkiOnOff,
	pm1004vdcAlmRxNrPortn
		EkiOnOff,
	pm1004vdcAlmRxCdrNotLockedPortn
		EkiOnOff,
	pm1004vdcAlmModNrPortn
		EkiOnOff
	}


pm1004vdcAlmlineXfp1AlarmsIndex OBJECT-TYPE
	SYNTAX  INTEGER(0..128)
	MAX-ACCESS  read-only
	STATUS current
	DESCRIPTION
        "
        Index definition for the pm1004vdcAlmlineXfp1Alarms 
        table
        "
	::= { pm1004vdcAlmlineXfp1AlarmsEntry 1 }


pm1004vdcAlmApdSupplyFaultPortn OBJECT-TYPE
	SYNTAX  EkiOnOff
	MAX-ACCESS read-only
	STATUS current
	DESCRIPTION
        "
        Line Rx Photodiode Power Failed 
        :This OID indicates a failure on 
        the APD power supply  <Help>  This 
        alarm indicates if the APD power 
        supply is in fail condition <Condtype> 
        APD_SUPPLY_FAULT_1 <Probcause>
         receiverFailure (42) <Alarmtype> 
        equipmentAlarm (5) <Polarity> (2) 
        "
	::= { pm1004vdcAlmlineXfp1AlarmsEntry 17 }


pm1004vdcAlmTecFaultPortn OBJECT-TYPE
	SYNTAX  EkiOnOff
	MAX-ACCESS read-only
	STATUS current
	DESCRIPTION
        "
        Line Optical Tx Temp Regul Failed 
        :This OID indicates a failure on 
        the TEC module  <Help>  This alarm 
        indicates if the TEC of the line 
        transceiver is in fail condition 
        <Condtype> TEC_FAULT_1 <Probcause> 
        transmitterFailure (56) <Alarmtype> 
        equipmentAlarm (5) <Polarity> (2) 
        "
	::= { pm1004vdcAlmlineXfp1AlarmsEntry 16 }


pm1004vdcAlmWavelengthUnlockedPortn OBJECT-TYPE
	SYNTAX  EkiOnOff
	MAX-ACCESS read-only
	STATUS current
	DESCRIPTION
        "
        Line Optical Tx Wavelength Unlocked 
        :This OID indicates that the wavelength 
        error is exceeding the manufacturer 
        tolerance  <Help>  This alarm indicates 
        if the wavelenght of the line transceiver 
        is locked <Condtype> WAVELENGTH_UNLOCKED_1 
        <Probcause> transmitterFailure
         (56) <Alarmtype> equipmentAlarm 
        (5) <Polarity> (2) 
        "
	::= { pm1004vdcAlmlineXfp1AlarmsEntry 15 }


pm1004vdcAlmTxNrPortn OBJECT-TYPE
	SYNTAX  EkiOnOff
	MAX-ACCESS read-only
	STATUS current
	DESCRIPTION
        "
        Line Optical Tx Not Ready :This 
        OID indicates a condition has arisen 
        leading to invalid data on the
         transmitting side  <Help>  This 
        alarm indicates if the Tx part
         of the line transceiver is ready 
        <Condtype> TX_NR_1 <Probcause>
         transmitterFailure (56) <Alarmtype> 
        equipmentAlarm (5) <Polarity> (2) 
        "
	::= { pm1004vdcAlmlineXfp1AlarmsEntry 9 }


pm1004vdcAlmTxFaultPortn OBJECT-TYPE
	SYNTAX  EkiOnOff
	MAX-ACCESS read-only
	STATUS current
	DESCRIPTION
        "
        Line Optical Tx Failure :This
         OID indicates a fault condition 
        on the laser detected by the safety 
        syste  <Help>  This alarm indicates 
        if the laser of the line transceiver 
        is in fail condition <Condtype> 
        TX_FAULT_1 <Probcause> transmitterFailure 
        (56) <Alarmtype> equipmentAlarm 
        (5) <Polarity> (2) 
        "
	::= { pm1004vdcAlmlineXfp1AlarmsEntry 8 }


pm1004vdcAlmTxCdrNotLockedPortn OBJECT-TYPE
	SYNTAX  EkiOnOff
	MAX-ACCESS read-only
	STATUS current
	DESCRIPTION
        "
        Line Optical Tx CDR Unlocked :This 
        OID indicates a loss of lock on 
        the transmitting side CDR has been 
        detected.  <Help>  This alarm indicates 
        if the Tx CDR is locked in the
         line transceiver <Condtype> TX_CDR_NOT_LOCKED1_1 
        <Probcause> transmitterFailure
         (56) <Alarmtype> equipmentAlarm 
        (5) <Polarity> (2) 
        "
	::= { pm1004vdcAlmlineXfp1AlarmsEntry 7 }


pm1004vdcAlmRxNrPortn OBJECT-TYPE
	SYNTAX  EkiOnOff
	MAX-ACCESS read-only
	STATUS current
	DESCRIPTION
        "
        Line Optical Rx Not Ready :This 
        OID indicates that a condition
         has arisen leading to invalid
         data on the receiving side.  <Help> 
         This alarm indicates if the Rx 
        part of the line transceiver is 
        ready <Condtype> RX_NR_1 <Probcause> 
        receiveFailure (41) <Alarmtype> 
        equipmentAlarm (5) <Polarity> (2) 
        "
	::= { pm1004vdcAlmlineXfp1AlarmsEntry 6 }


pm1004vdcAlmRxCdrNotLockedPortn OBJECT-TYPE
	SYNTAX  EkiOnOff
	MAX-ACCESS read-only
	STATUS current
	DESCRIPTION
        "
        Line Optical Rx CDR Unlocked :This 
        OID indicates that a loss of lock 
        on the receiving side CDR has been 
        detected  <Help>  This alarm indicates 
        if the Rx CDR is locked in the
         line transceiver <Condtype> RX_CDR_NOT_LOCKED1_1 
        <Probcause> receiveFailure (41) 
        <Alarmtype> equipmentAlarm (5)
         <Polarity> (2) 
        "
	::= { pm1004vdcAlmlineXfp1AlarmsEntry 4 }


pm1004vdcAlmModNrPortn OBJECT-TYPE
	SYNTAX  EkiOnOff
	MAX-ACCESS read-only
	STATUS current
	DESCRIPTION
        "
        Line Optical Module Not Ready
         :This OID indicates that the module 
        is unable to determine correct
         data.  <Help>  This alarm indicates 
        if the line transceiver is ready 
        <Condtype> MOD_NR_1 <Probcause> 
        receiveFailure (41) <Alarmtype> 
        equipmentAlarm (5) <Polarity> (2) 
        "
	::= { pm1004vdcAlmlineXfp1AlarmsEntry 3 }


--- *********************************************************
---     TABLE for the pm1004vdcAlmlineXfp1SupplyAlarm articles
--- *********************************************************

pm1004vdcAlmlineXfp1SupplyAlarmTable OBJECT-TYPE
	SYNTAX  SEQUENCE OF Pm1004vdcAlmlineXfp1SupplyAlarmEntry
	MAX-ACCESS not-accessible
	STATUS current
	DESCRIPTION
        "
        List of pm1004vdcAlmlineXfp1SupplyAlarm 
        Article
        "
	::= { pm1004vdcAlmLineUrg 212 }


pm1004vdcAlmlineXfp1SupplyAlarmEntry OBJECT-TYPE
	SYNTAX Pm1004vdcAlmlineXfp1SupplyAlarmEntry
	MAX-ACCESS not-accessible
	STATUS current
	DESCRIPTION
        "
        Row definition for the pm1004vdcAlmlineXfp1SupplyAlarm 
        table
        "
	INDEX   { pm1004vdcAlmlineXfp1SupplyAlarmIndex }
	::= { pm1004vdcAlmlineXfp1SupplyAlarmTable 1 }


Pm1004vdcAlmlineXfp1SupplyAlarmEntry ::=
	SEQUENCE {
	pm1004vdcAlmlineXfp1SupplyAlarmIndex
		INTEGER,
	pm1004vdcAlmVcc5HighWarningPortn
		EkiOnOff,
	pm1004vdcAlmVcc5LowWarningPortn
		EkiOnOff,
	pm1004vdcAlmVcc3HighWarningPortn
		EkiOnOff,
	pm1004vdcAlmVcc3LowWarningPortn
		EkiOnOff,
	pm1004vdcAlmVcc2HighWarningPortn
		EkiOnOff,
	pm1004vdcAlmVcc2LowWarningPortn
		EkiOnOff,
	pm1004vdcAlmVee5HighWarningPortn
		EkiOnOff,
	pm1004vdcAlmVee5LowWarningPortn
		EkiOnOff,
	pm1004vdcAlmVcc5HighAlarmPortn
		EkiOnOff,
	pm1004vdcAlmVcc5LowAlarmPortn
		EkiOnOff,
	pm1004vdcAlmVcc3HighAlarmPortn
		EkiOnOff,
	pm1004vdcAlmVcc3LowAlarmPortn
		EkiOnOff,
	pm1004vdcAlmVcc2HighAlarmPortn
		EkiOnOff,
	pm1004vdcAlmVcc2LowAlarmPortn
		EkiOnOff,
	pm1004vdcAlmVee5HighAlarmPortn
		EkiOnOff,
	pm1004vdcAlmVee5LowAlarmPortn
		EkiOnOff
	}


pm1004vdcAlmlineXfp1SupplyAlarmIndex OBJECT-TYPE
	SYNTAX  INTEGER(0..128)
	MAX-ACCESS  read-only
	STATUS current
	DESCRIPTION
        "
        Index definition for the pm1004vdcAlmlineXfp1SupplyAlarm 
        table
        "
	::= { pm1004vdcAlmlineXfp1SupplyAlarmEntry 1 }


pm1004vdcAlmVcc5HighWarningPortn OBJECT-TYPE
	SYNTAX  EkiOnOff
	MAX-ACCESS read-only
	STATUS current
	DESCRIPTION
        "
        VCC5 Power Supply High Warning 
        :Warning indicating the XFP/OTX 
        VCC5 power supply is higher than 
        the threshold written in the EEPROM 
        <Condtype> VCC5_HIGH_WARNING_1
         <Probcause> powerProblem (36)
         <Alarmtype> equipmentAlarm (5) 
        <Polarity> (2) 
        "
	::= { pm1004vdcAlmlineXfp1SupplyAlarmEntry 17 }


pm1004vdcAlmVcc5LowWarningPortn OBJECT-TYPE
	SYNTAX  EkiOnOff
	MAX-ACCESS read-only
	STATUS current
	DESCRIPTION
        "
        VCC5 Power Supply Low Warning
         :Warning indicating the XFP/OTX 
        VCC5 power supply is lower than 
        the threshold written in the EEPROM 
        <Condtype> VCC5_LOW_WARNING_1 <Probcause> 
        powerProblem (36) <Alarmtype> equipmentAlarm 
        (5) <Polarity> (2) 
        "
	::= { pm1004vdcAlmlineXfp1SupplyAlarmEntry 16 }


pm1004vdcAlmVcc3HighWarningPortn OBJECT-TYPE
	SYNTAX  EkiOnOff
	MAX-ACCESS read-only
	STATUS current
	DESCRIPTION
        "
        VCC3 Power Supply High Warning 
        :Warning indicating the XFP/OTX 
        VCC3 power supply is higher than 
        the threshold written in the EEPROM 
        <Condtype> VCC3_HIGH_WARNING_1
         <Probcause> powerProblem (36)
         <Alarmtype> equipmentAlarm (5) 
        <Polarity> (2) 
        "
	::= { pm1004vdcAlmlineXfp1SupplyAlarmEntry 15 }


pm1004vdcAlmVcc3LowWarningPortn OBJECT-TYPE
	SYNTAX  EkiOnOff
	MAX-ACCESS read-only
	STATUS current
	DESCRIPTION
        "
        VCC3 Power Supply Low Warning
         :Warning indicating the XFP/OTX 
        VCC3 power supply is lower than 
        the threshold written in the EEPROM 
        <Condtype> VCC3_LOW_WARNING_1 <Probcause> 
        powerProblem (36) <Alarmtype> equipmentAlarm 
        (5) <Polarity> (2) 
        "
	::= { pm1004vdcAlmlineXfp1SupplyAlarmEntry 14 }


pm1004vdcAlmVcc2HighWarningPortn OBJECT-TYPE
	SYNTAX  EkiOnOff
	MAX-ACCESS read-only
	STATUS current
	DESCRIPTION
        "
        VCC2 Power Supply High Warning 
        :Warning indicating the XFP/OTX 
        VCC2 power supply is higher than 
        the threshold written in the EEPROM 
        <Condtype> VCC2_HIGH_WARNING_1
         <Probcause> powerProblem (36)
         <Alarmtype> equipmentAlarm (5) 
        <Polarity> (2) 
        "
	::= { pm1004vdcAlmlineXfp1SupplyAlarmEntry 13 }


pm1004vdcAlmVcc2LowWarningPortn OBJECT-TYPE
	SYNTAX  EkiOnOff
	MAX-ACCESS read-only
	STATUS current
	DESCRIPTION
        "
        VCC2 Power Supply Low Warning
         :Warning indicating the XFP/OTX 
        VCC2 power supply is lower than 
        the threshold written in the EEPROM 
        <Condtype> VCC2_LOW_WARNING_1 <Probcause> 
        powerProblem (36) <Alarmtype> equipmentAlarm 
        (5) <Polarity> (2) 
        "
	::= { pm1004vdcAlmlineXfp1SupplyAlarmEntry 12 }


pm1004vdcAlmVee5HighWarningPortn OBJECT-TYPE
	SYNTAX  EkiOnOff
	MAX-ACCESS read-only
	STATUS current
	DESCRIPTION
        "
        VEE5 Power Supply High Warning 
        :Warning indicating the XFP/OTX 
        VEE5 power supply is higher than 
        the threshold written in the EEPROM 
        <Condtype> VEE5_HIGH_WARNING_1
         <Probcause> powerProblem (36)
         <Alarmtype> equipmentAlarm (5) 
        <Polarity> (2) 
        "
	::= { pm1004vdcAlmlineXfp1SupplyAlarmEntry 11 }


pm1004vdcAlmVee5LowWarningPortn OBJECT-TYPE
	SYNTAX  EkiOnOff
	MAX-ACCESS read-only
	STATUS current
	DESCRIPTION
        "
        VEE5 Power Supply Low Warning
         :Warning indicating the XFP/OTX 
        VEE5 power supply is lower than 
        the threshold written in the EEPROM 
        <Condtype> VEE5_LOW_WARNING_1 <Probcause> 
        powerProblem (36) <Alarmtype> equipmentAlarm 
        (5) <Polarity> (2) 
        "
	::= { pm1004vdcAlmlineXfp1SupplyAlarmEntry 10 }


pm1004vdcAlmVcc5HighAlarmPortn OBJECT-TYPE
	SYNTAX  EkiOnOff
	MAX-ACCESS read-only
	STATUS current
	DESCRIPTION
        "
        VCC5 Power Supply High :Alarm
         indicating the XFP/OTX VCC5 power 
        supply is higher than the threshold 
        written in the EEPROM <Condtype> 
        VCC5_HIGH_ALARM_1 <Probcause> powerProblem 
        (36) <Alarmtype> equipmentAlarm 
        (5) <Polarity> (2) 
        "
	::= { pm1004vdcAlmlineXfp1SupplyAlarmEntry 9 }


pm1004vdcAlmVcc5LowAlarmPortn OBJECT-TYPE
	SYNTAX  EkiOnOff
	MAX-ACCESS read-only
	STATUS current
	DESCRIPTION
        "
        VCC5 Power Supply Low :Alarm indicating 
        the XFP/OTX VCC5 power supply is 
        lower than the threshold written 
        in the EEPROM <Condtype> VCC5_LOW_ALARM_1 
        <Probcause> powerProblem (36) <Alarmtype> 
        equipmentAlarm (5) <Polarity> (2) 
        "
	::= { pm1004vdcAlmlineXfp1SupplyAlarmEntry 8 }


pm1004vdcAlmVcc3HighAlarmPortn OBJECT-TYPE
	SYNTAX  EkiOnOff
	MAX-ACCESS read-only
	STATUS current
	DESCRIPTION
        "
        VCC3 Power Supply High :Alarm
         indicating the XFP/OTX VCC3 power 
        supply is higher than the threshold 
        written in the EEPROM <Condtype> 
        VCC3_HIGH_ALARM_1 <Probcause> powerProblem 
        (36) <Alarmtype> equipmentAlarm 
        (5) <Polarity> (2) 
        "
	::= { pm1004vdcAlmlineXfp1SupplyAlarmEntry 7 }


pm1004vdcAlmVcc3LowAlarmPortn OBJECT-TYPE
	SYNTAX  EkiOnOff
	MAX-ACCESS read-only
	STATUS current
	DESCRIPTION
        "
        VCC3 Power Supply Low :Alarm indicating 
        the XFP/OTX VCC3 power supply is 
        lower than the threshold written 
        in the EEPROM <Condtype> VCC3_LOW_ALARM_1 
        <Probcause> powerProblem (36) <Alarmtype> 
        equipmentAlarm (5) <Polarity> (2) 
        "
	::= { pm1004vdcAlmlineXfp1SupplyAlarmEntry 6 }


pm1004vdcAlmVcc2HighAlarmPortn OBJECT-TYPE
	SYNTAX  EkiOnOff
	MAX-ACCESS read-only
	STATUS current
	DESCRIPTION
        "
        VCC2 Power Supply High :Alarm
         indicating the XFP/OTX VCC2 power 
        supply is higher than the threshold 
        written in the EEPROM <Condtype> 
        VCC2_HIGH_ALARM_1 <Probcause> powerProblem 
        (36) <Alarmtype> equipmentAlarm 
        (5) <Polarity> (2) 
        "
	::= { pm1004vdcAlmlineXfp1SupplyAlarmEntry 5 }


pm1004vdcAlmVcc2LowAlarmPortn OBJECT-TYPE
	SYNTAX  EkiOnOff
	MAX-ACCESS read-only
	STATUS current
	DESCRIPTION
        "
        VCC2 Power Supply Low :Alarm indicating 
        the XFP/OTX VCC2 power supply is 
        lower than the threshold written 
        in the EEPROM <Condtype> VCC2_LOW_ALARM_1 
        <Probcause> powerProblem (36) <Alarmtype> 
        equipmentAlarm (5) <Polarity> (2) 
        "
	::= { pm1004vdcAlmlineXfp1SupplyAlarmEntry 4 }


pm1004vdcAlmVee5HighAlarmPortn OBJECT-TYPE
	SYNTAX  EkiOnOff
	MAX-ACCESS read-only
	STATUS current
	DESCRIPTION
        "
        VEE5 Power Supply High :Alarm
         indicating the XFP/OTX VEE5 power 
        supply is higher than the threshold 
        written in the EEPROM <Condtype> 
        VEE5_HIGH_ALARM_1 <Probcause> powerProblem 
        (36) <Alarmtype> equipmentAlarm 
        (5) <Polarity> (2) 
        "
	::= { pm1004vdcAlmlineXfp1SupplyAlarmEntry 3 }


pm1004vdcAlmVee5LowAlarmPortn OBJECT-TYPE
	SYNTAX  EkiOnOff
	MAX-ACCESS read-only
	STATUS current
	DESCRIPTION
        "
        VEE5 Power Supply Low :Alarm indicating 
        the XFP/OTX VEE5 power supply is 
        lower than the threshold written 
        in the EEPROM <Condtype> VEE5_LOW_ALARM_1 
        <Probcause> powerProblem (36) <Alarmtype> 
        equipmentAlarm (5) <Polarity> (2) 
        "
	::= { pm1004vdcAlmlineXfp1SupplyAlarmEntry 2 }


--- *********************************************************
---     TABLE for the pm1004vdcAlmlineOtx1TlhAlarms articles
--- *********************************************************

pm1004vdcAlmlineOtx1TlhAlarmsTable OBJECT-TYPE
	SYNTAX  SEQUENCE OF Pm1004vdcAlmlineOtx1TlhAlarmsEntry
	MAX-ACCESS not-accessible
	STATUS current
	DESCRIPTION
        "
        List of pm1004vdcAlmlineOtx1TlhAlarms 
        Article
        "
	::= { pm1004vdcAlmLineUrg 224 }


pm1004vdcAlmlineOtx1TlhAlarmsEntry OBJECT-TYPE
	SYNTAX Pm1004vdcAlmlineOtx1TlhAlarmsEntry
	MAX-ACCESS not-accessible
	STATUS current
	DESCRIPTION
        "
        Row definition for the pm1004vdcAlmlineOtx1TlhAlarms 
        table
        "
	INDEX   { pm1004vdcAlmlineOtx1TlhAlarmsIndex }
	::= { pm1004vdcAlmlineOtx1TlhAlarmsTable 1 }


Pm1004vdcAlmlineOtx1TlhAlarmsEntry ::=
	SEQUENCE {
	pm1004vdcAlmlineOtx1TlhAlarmsIndex
		INTEGER,
	pm1004vdcAlmLineLaserTempHighAlaPortn
		EkiOnOff,
	pm1004vdcAlmLineFreqDevHighAlaPortn
		EkiOnOff,
	pm1004vdcAlmLineAgingHighAlaPortn
		EkiOnOff,
	pm1004vdcAlmLineModulatorAgingHighAlaPortn
		EkiOnOff
	}


pm1004vdcAlmlineOtx1TlhAlarmsIndex OBJECT-TYPE
	SYNTAX  INTEGER(0..128)
	MAX-ACCESS  read-only
	STATUS current
	DESCRIPTION
        "
        Index definition for the pm1004vdcAlmlineOtx1TlhAlarms 
        table
        "
	::= { pm1004vdcAlmlineOtx1TlhAlarmsEntry 1 }


pm1004vdcAlmLineLaserTempHighAlaPortn OBJECT-TYPE
	SYNTAX  EkiOnOff
	MAX-ACCESS read-only
	STATUS current
	DESCRIPTION
        "
        Line Laser Temp. High Alarm :Alarm 
        indicating the Line OTX TLH laser 
        temperature is higher than the
         threshold written in the EEPROM 
        <Condtype> LINE_LASER_TEMP_HIGH_ALA_1 
        <Probcause> temperatureUnacceptable 
        (51) <Alarmtype> equipmentAlarm 
        (5) <Polarity> (2) 
        "
	::= { pm1004vdcAlmlineOtx1TlhAlarmsEntry 15 }


pm1004vdcAlmLineFreqDevHighAlaPortn OBJECT-TYPE
	SYNTAX  EkiOnOff
	MAX-ACCESS read-only
	STATUS current
	DESCRIPTION
        "
        Line Freq. Deviation High Alarm 
        :Alarm indicating the Line OTX
         TLH frequency deviation is higher 
        than the threshold written in the 
        EEPROM <Condtype> LINE_FREQ_DEV_HIGH_ALA_1 
        <Probcause> transmitterFailure
         (56) <Alarmtype> equipmentAlarm 
        (5) <Polarity> (2) 
        "
	::= { pm1004vdcAlmlineOtx1TlhAlarmsEntry 13 }


pm1004vdcAlmLineAgingHighAlaPortn OBJECT-TYPE
	SYNTAX  EkiOnOff
	MAX-ACCESS read-only
	STATUS current
	DESCRIPTION
        "
        Line OTX TLH Aging High Alarm
         :Alarm indicating the Line OTX 
        TLH aging is higher than the threshold 
        written in the EEPROM <Condtype> 
        LINE_AGING_HIGH_ALA_1 <Probcause> 
        transmitterFailure (56) <Alarmtype> 
        equipmentAlarm (5) <Polarity> (2) 
        "
	::= { pm1004vdcAlmlineOtx1TlhAlarmsEntry 7 }


pm1004vdcAlmLineModulatorAgingHighAlaPortn OBJECT-TYPE
	SYNTAX  EkiOnOff
	MAX-ACCESS read-only
	STATUS current
	DESCRIPTION
        "
        Line Modulator Aging High Alarm 
        :Alarm indicating the Line OTX
         TLH modulator aging is higher
         than the threshold written in
         the EEPROM <Condtype> LINE_MODULATOR_AGING_HIGH_ALA_1 
        <Probcause> transmitterFailure
         (56) <Alarmtype> equipmentAlarm 
        (5) <Polarity> (2) 
        "
	::= { pm1004vdcAlmlineOtx1TlhAlarmsEntry 6 }


--- *********************************************************
---     TABLE for the pm1004vdcAlmlineOtx1TlhWarnings articles
--- *********************************************************

pm1004vdcAlmlineOtx1TlhWarningsTable OBJECT-TYPE
	SYNTAX  SEQUENCE OF Pm1004vdcAlmlineOtx1TlhWarningsEntry
	MAX-ACCESS not-accessible
	STATUS current
	DESCRIPTION
        "
        List of pm1004vdcAlmlineOtx1TlhWarnings 
        Article
        "
	::= { pm1004vdcAlmLineNurg 225 }


pm1004vdcAlmlineOtx1TlhWarningsEntry OBJECT-TYPE
	SYNTAX Pm1004vdcAlmlineOtx1TlhWarningsEntry
	MAX-ACCESS not-accessible
	STATUS current
	DESCRIPTION
        "
        Row definition for the pm1004vdcAlmlineOtx1TlhWarnings 
        table
        "
	INDEX   { pm1004vdcAlmlineOtx1TlhWarningsIndex }
	::= { pm1004vdcAlmlineOtx1TlhWarningsTable 1 }


Pm1004vdcAlmlineOtx1TlhWarningsEntry ::=
	SEQUENCE {
	pm1004vdcAlmlineOtx1TlhWarningsIndex
		INTEGER,
	pm1004vdcAlmLineLaserTempHighWarningPortn
		EkiOnOff,
	pm1004vdcAlmLineFreqDevHighWarningPortn
		EkiOnOff,
	pm1004vdcAlmLineAgingHighWarningPortn
		EkiOnOff,
	pm1004vdcAlmLineModulatorAgingHighWarningPortn
		EkiOnOff
	}


pm1004vdcAlmlineOtx1TlhWarningsIndex OBJECT-TYPE
	SYNTAX  INTEGER(0..128)
	MAX-ACCESS  read-only
	STATUS current
	DESCRIPTION
        "
        Index definition for the pm1004vdcAlmlineOtx1TlhWarnings 
        table
        "
	::= { pm1004vdcAlmlineOtx1TlhWarningsEntry 1 }


pm1004vdcAlmLineLaserTempHighWarningPortn OBJECT-TYPE
	SYNTAX  EkiOnOff
	MAX-ACCESS read-only
	STATUS current
	DESCRIPTION
        "
        Line Laser Temp. High Warning
         :Warning indicating the Line OTX 
        TLH laser temperature is higher 
        than the threshold written in the 
        EEPROM <Condtype> LINE_LASER_TEMP_HIGH_WARNING_1 
        <Probcause> temperatureUnacceptable 
        (51) <Alarmtype> equipmentAlarm 
        (5) <Polarity> (2) 
        "
	::= { pm1004vdcAlmlineOtx1TlhWarningsEntry 15 }


pm1004vdcAlmLineFreqDevHighWarningPortn OBJECT-TYPE
	SYNTAX  EkiOnOff
	MAX-ACCESS read-only
	STATUS current
	DESCRIPTION
        "
        Line Freq. Deviation High Warning 
        :Warning indicating the Line OTX 
        TLH frequency deviation is higher 
        than the threshold written in the 
        EEPROM <Condtype> LINE_FREQ_DEV_HIGH_WARNING_1 
        <Probcause> transmitterFailure
         (56) <Alarmtype> equipmentAlarm 
        (5) <Polarity> (2) 
        "
	::= { pm1004vdcAlmlineOtx1TlhWarningsEntry 13 }


pm1004vdcAlmLineAgingHighWarningPortn OBJECT-TYPE
	SYNTAX  EkiOnOff
	MAX-ACCESS read-only
	STATUS current
	DESCRIPTION
        "
        Line OTX TLH Aging High Warning 
        :Warning indicating the Line OTX 
        TLH aging is higher than the threshold 
        written in the EEPROM <Condtype> 
        LINE_AGING_HIGH_WARNING_1 <Probcause> 
        transmitterFailure (56) <Alarmtype> 
        equipmentAlarm (5) <Polarity> (2) 
        "
	::= { pm1004vdcAlmlineOtx1TlhWarningsEntry 7 }


pm1004vdcAlmLineModulatorAgingHighWarningPortn OBJECT-TYPE
	SYNTAX  EkiOnOff
	MAX-ACCESS read-only
	STATUS current
	DESCRIPTION
        "
        Line Modulator Aging High Warning 
        :Warning indicating the Line OTX 
        TLH modulator aging is higher than 
        the threshold written in the EEPROM 
        <Condtype> LINE_MODULATOR_AGING_HIGH_WARNING_1 
        <Probcause> transmitterFailure
         (56) <Alarmtype> equipmentAlarm 
        (5) <Polarity> (2) 
        "
	::= { pm1004vdcAlmlineOtx1TlhWarningsEntry 6 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm1004vdcCtrlconfMgnt1 OBJECT IDENTIFIER ::= { pm1004vdcCtrlOther 1 }




pm1004vdcCtrlConf2Clear1 OBJECT-TYPE
	  SYNTAX EkiOnOff
	  MAX-ACCESS read-write
	  STATUS current
	  DESCRIPTION
        "
        Clear Configuration Tables :This 
        OID clears the configuration tables 
        from configuration2 in the flash. 
         <Help>  This control restores
         the default configuration of the 
        module
        "
	  ::= { pm1004vdcCtrlconfMgnt1 14 }



pm1004vdcCtrlConf2Flash1 OBJECT-TYPE
	  SYNTAX EkiOnOff
	  MAX-ACCESS read-write
	  STATUS current
	  DESCRIPTION
        "
        Write Configuration Tables :This 
        OID saves the current configuration 
        of the PM as configuration2 in
         the flash.  <Help>  This control 
        saves the customer configuration 
        on the module
        "
	  ::= { pm1004vdcCtrlconfMgnt1 10 }



pm1004vdcCtrlConf2Load1 OBJECT-TYPE
	  SYNTAX EkiOnOff
	  MAX-ACCESS read-write
	  STATUS current
	  DESCRIPTION
        "
        Load Configuration Tables Set
         Nb 2 :When set this OID enables 
        loading from flash configuration2 
        into the PM.
        "
	  ::= { pm1004vdcCtrlconfMgnt1 2 }



pm1004vdcCtrlConf1Load1 OBJECT-TYPE
	  SYNTAX EkiOnOff
	  MAX-ACCESS read-write
	  STATUS current
	  DESCRIPTION
        "
        Load Configuration Tables Set
         Nb 1 :When set this OID enables 
        loading from flash configuration1 
        into the PM.
        "
	  ::= { pm1004vdcCtrlconfMgnt1 1 }



--- *****************************************************
---     LEAF for the synth4 article
--- *****************************************************
pm1004vdcCtrlsynth4 OBJECT IDENTIFIER ::= { pm1004vdcCtrlOther 4 }




pm1004vdcCtrlCorrelatOff OBJECT-TYPE
	  SYNTAX EkiOnOff
	  MAX-ACCESS read-write
	  STATUS current
	  DESCRIPTION
        "
        Disable Alarm Correlation :This 
        OID disables the alarm correlation 
        in the PM.
        "
	  ::= { pm1004vdcCtrlsynth4 2 }



pm1004vdcCtrlCorrelatOn OBJECT-TYPE
	  SYNTAX EkiOnOff
	  MAX-ACCESS read-write
	  STATUS current
	  DESCRIPTION
        "
        Enable Alarm Correlation :This 
        OID enables the alarm correlation 
        in the PM.
        "
	  ::= { pm1004vdcCtrlsynth4 1 }



--- *****************************************************
---     LEAF for the swMgnt article
--- *****************************************************
pm1004vdcCtrlswMgnt OBJECT IDENTIFIER ::= { pm1004vdcCtrlOther 5 }




pm1004vdcCtrlLoadSwBank2 OBJECT-TYPE
	  SYNTAX EkiOnOff
	  MAX-ACCESS read-write
	  STATUS current
	  DESCRIPTION
        "
        Set Software Nb 2 As Active :This 
        OID, when set, loads the SW from 
        bank2 into the PM. It must be followed 
        by a reset.  <Help>  This controls 
        selects the second SW bank as the 
        active bank for the next module 
        reset
        "
	  ::= { pm1004vdcCtrlswMgnt 6 }



pm1004vdcCtrlLoadSwBank1 OBJECT-TYPE
	  SYNTAX EkiOnOff
	  MAX-ACCESS read-write
	  STATUS current
	  DESCRIPTION
        "
        Set Software Nb 1 As Active :This 
        OID, when set, loads the SW from 
        bank1 into the PM. It must be followed 
        by a reset.  <Help>  This controls 
        selects the first SW bank as the 
        active bank for the next module 
        reset
        "
	  ::= { pm1004vdcCtrlswMgnt 5 }



pm1004vdcCtrlWarmReset OBJECT-TYPE
	  SYNTAX EkiOnOff
	  MAX-ACCESS read-write
	  STATUS current
	  DESCRIPTION
        "
        PM Warm Reset :This OID, when
         set, causes a warm reset of the 
        PM. This reset is not traffic affecting, 
        and the configuration of PM remains 
        unchanged.  <Help>  This control 
        initiates a warm reset of the module. 
        "
	  ::= { pm1004vdcCtrlswMgnt 3 }



pm1004vdcCtrlColdReset OBJECT-TYPE
	  SYNTAX EkiOnOff
	  MAX-ACCESS read-write
	  STATUS current
	  DESCRIPTION
        "
        PM Cold Reset :This OID, when
         set, causes a cold reset of the 
        PM. This reset is traffic affecting, 
        and the configuration of PM is
         reloaded on start-up.  <Help>
          This control initiates a cold 
        reset of the module. 
        "
	  ::= { pm1004vdcCtrlswMgnt 2 }



--- *****************************************************
---     LEAF for the gwMgnt article
--- *****************************************************
pm1004vdcCtrlgwMgnt OBJECT IDENTIFIER ::= { pm1004vdcCtrlOther 6 }




pm1004vdcCtrlLoadGwBank4 OBJECT-TYPE
	  SYNTAX EkiOnOff
	  MAX-ACCESS read-write
	  STATUS current
	  DESCRIPTION
        "
        Set Gateware Nb 4 As Active :This 
        OID, when set, loads the GW from 
        bank4 (Flash) into the PM. It is 
        followed by an automatic gateware 
        cold reset.
        "
	  ::= { pm1004vdcCtrlgwMgnt 8 }



pm1004vdcCtrlLoadGwBank3 OBJECT-TYPE
	  SYNTAX EkiOnOff
	  MAX-ACCESS read-write
	  STATUS current
	  DESCRIPTION
        "
        Set Gateware Nb 3 As Active :This 
        OID, when set, loads the GW from 
        bank3 (Flash) into the PM. It is 
        followed by an automatic gateware 
        cold reset.  <Help>  This controls 
        initiates a cold reset of the module 
        and select the third GW bank as 
        the active bank
        "
	  ::= { pm1004vdcCtrlgwMgnt 7 }



pm1004vdcCtrlLoadGwBank2 OBJECT-TYPE
	  SYNTAX EkiOnOff
	  MAX-ACCESS read-write
	  STATUS current
	  DESCRIPTION
        "
        Set Gateware Nb 2 As Active :This 
        OID, when set, loads the GW from 
        bank2 (Flash) into the PM. It is 
        followed by an automatic gateware 
        cold reset.
        "
	  ::= { pm1004vdcCtrlgwMgnt 6 }



pm1004vdcCtrlLoadGwBank1 OBJECT-TYPE
	  SYNTAX EkiOnOff
	  MAX-ACCESS read-write
	  STATUS current
	  DESCRIPTION
        "
        Set Gateware Nb 1 As Active :This 
        OID, when set, loads the GW from 
        bank1 (Flash) into the PM. It is 
        followed by an automatic gateware 
        cold reset.  <Help>  This controls 
        initiates a cold reset of the module 
        and select the first GW bank as 
        the active bank
        "
	  ::= { pm1004vdcCtrlgwMgnt 5 }



pm1004vdcCtrlCurrentGwReset OBJECT-TYPE
	  SYNTAX EkiOnOff
	  MAX-ACCESS read-write
	  STATUS current
	  DESCRIPTION
        "
        Active Gateware Reset :This OID, 
        when set, resets the active gateware. 
        It is traffic affecting.
        "
	  ::= { pm1004vdcCtrlgwMgnt 1 }



--- *********************************************************
---     TABLE for the pm1004vdcCtrlaccessLoop articles
--- *********************************************************

pm1004vdcCtrlaccessLoopTable OBJECT-TYPE
	SYNTAX  SEQUENCE OF Pm1004vdcCtrlaccessLoopEntry
	MAX-ACCESS not-accessible
	STATUS current
	DESCRIPTION
        "
        List of pm1004vdcCtrlaccessLoop 
        Article
        "
	::= { pm1004vdcCtrlClient 16 }


pm1004vdcCtrlaccessLoopEntry OBJECT-TYPE
	SYNTAX Pm1004vdcCtrlaccessLoopEntry
	MAX-ACCESS not-accessible
	STATUS current
	DESCRIPTION
        "
        Row definition for the pm1004vdcCtrlaccessLoop 
        table
        "
	INDEX   { pm1004vdcCtrlaccessLoopIndex }
	::= { pm1004vdcCtrlaccessLoopTable 1 }


Pm1004vdcCtrlaccessLoopEntry ::=
	SEQUENCE {
	pm1004vdcCtrlaccessLoopIndex
		INTEGER,
	pm1004vdcCtrlaccessLoopPortn
		EkiState
	}


pm1004vdcCtrlaccessLoopIndex OBJECT-TYPE
	SYNTAX  INTEGER(0..128)
	MAX-ACCESS  read-only
	STATUS current
	DESCRIPTION
        "
        Index definition for the pm1004vdcCtrlaccessLoop 
        table
        "
	::= { pm1004vdcCtrlaccessLoopEntry 1 }


pm1004vdcCtrlaccessLoopPortn OBJECT-TYPE
	SYNTAX  EkiState
	MAX-ACCESS read-write
	STATUS current
	DESCRIPTION
        "
        Client Facility Loopback :This 
        OID operates a Client Facility
         Loopback, looping client input 
        signal on the client output port. 
        The loop is located on the client 
        transceiver  <Help> This maintenance 
        parameter operates a Client Facility 
        Loopback, looping client input
         signal on the client output port. 
        The loop is located on the client 
        transceiver
        "
	::= { pm1004vdcCtrlaccessLoopEntry 2 }


--- *********************************************************
---     TABLE for the pm1004vdcCtrlportOosMode articles
--- *********************************************************

pm1004vdcCtrlportOosModeTable OBJECT-TYPE
	SYNTAX  SEQUENCE OF Pm1004vdcCtrlportOosModeEntry
	MAX-ACCESS not-accessible
	STATUS current
	DESCRIPTION
        "
        List of pm1004vdcCtrlportOosMode 
        Article
        "
	::= { pm1004vdcCtrlClient 18 }


pm1004vdcCtrlportOosModeEntry OBJECT-TYPE
	SYNTAX Pm1004vdcCtrlportOosModeEntry
	MAX-ACCESS not-accessible
	STATUS current
	DESCRIPTION
        "
        Row definition for the pm1004vdcCtrlportOosMode 
        table
        "
	INDEX   { pm1004vdcCtrlportOosModeIndex }
	::= { pm1004vdcCtrlportOosModeTable 1 }


Pm1004vdcCtrlportOosModeEntry ::=
	SEQUENCE {
	pm1004vdcCtrlportOosModeIndex
		INTEGER,
	pm1004vdcCtrlportOosModePortn
		Pm1004vdcClientOosMode
	}


pm1004vdcCtrlportOosModeIndex OBJECT-TYPE
	SYNTAX  INTEGER(0..128)
	MAX-ACCESS  read-only
	STATUS current
	DESCRIPTION
        "
        Index definition for the pm1004vdcCtrlportOosMode 
        table
        "
	::= { pm1004vdcCtrlportOosModeEntry 1 }


pm1004vdcCtrlportOosModePortn OBJECT-TYPE
	SYNTAX  Pm1004vdcClientOosMode
	MAX-ACCESS read-write
	STATUS current
	DESCRIPTION
        "
        Client Out Of Service :This OID 
        sets the Service state of the client 
        port (In Service, Tx Out of Service, 
        Rx Out of Service or Port (Rx and 
        Tx) Out of Service)  <Help>  This 
        controls defines the service state 
        of the client port (In Service, 
        Tx Out of Service, Rx Out of Service 
         or Port (Rx and Tx) Out of Service)
        "
	::= { pm1004vdcCtrlportOosModeEntry 2 }


--- *********************************************************
---     TABLE for the pm1004vdcCtrlsfpOffCtrl articles
--- *********************************************************

pm1004vdcCtrlsfpOffCtrlTable OBJECT-TYPE
	SYNTAX  SEQUENCE OF Pm1004vdcCtrlsfpOffCtrlEntry
	MAX-ACCESS not-accessible
	STATUS current
	DESCRIPTION
        "
        List of pm1004vdcCtrlsfpOffCtrl 
        Article
        "
	::= { pm1004vdcCtrlClient 20 }


pm1004vdcCtrlsfpOffCtrlEntry OBJECT-TYPE
	SYNTAX Pm1004vdcCtrlsfpOffCtrlEntry
	MAX-ACCESS not-accessible
	STATUS current
	DESCRIPTION
        "
        Row definition for the pm1004vdcCtrlsfpOffCtrl 
        table
        "
	INDEX   { pm1004vdcCtrlsfpOffCtrlIndex }
	::= { pm1004vdcCtrlsfpOffCtrlTable 1 }


Pm1004vdcCtrlsfpOffCtrlEntry ::=
	SEQUENCE {
	pm1004vdcCtrlsfpOffCtrlIndex
		INTEGER,
	pm1004vdcCtrlsfpOffCtrlPortn
		EkiState
	}


pm1004vdcCtrlsfpOffCtrlIndex OBJECT-TYPE
	SYNTAX  INTEGER(0..128)
	MAX-ACCESS  read-only
	STATUS current
	DESCRIPTION
        "
        Index definition for the pm1004vdcCtrlsfpOffCtrl 
        table
        "
	::= { pm1004vdcCtrlsfpOffCtrlEntry 1 }


pm1004vdcCtrlsfpOffCtrlPortn OBJECT-TYPE
	SYNTAX  EkiState
	MAX-ACCESS read-write
	STATUS current
	DESCRIPTION
        "
        Signal OFF :This OID switches
         off the SFP.  <Help>   This control 
        defines the laser state of the
         client transceiver
        "
	::= { pm1004vdcCtrlsfpOffCtrlEntry 2 }


--- *********************************************************
---     TABLE for the pm1004vdcCtrlcsfUpIns articles
--- *********************************************************

pm1004vdcCtrlcsfUpInsTable OBJECT-TYPE
	SYNTAX  SEQUENCE OF Pm1004vdcCtrlcsfUpInsEntry
	MAX-ACCESS not-accessible
	STATUS current
	DESCRIPTION
        "
        List of pm1004vdcCtrlcsfUpIns
         Article
        "
	::= { pm1004vdcCtrlClient 21 }


pm1004vdcCtrlcsfUpInsEntry OBJECT-TYPE
	SYNTAX Pm1004vdcCtrlcsfUpInsEntry
	MAX-ACCESS not-accessible
	STATUS current
	DESCRIPTION
        "
        Row definition for the pm1004vdcCtrlcsfUpIns 
        table
        "
	INDEX   { pm1004vdcCtrlcsfUpInsIndex }
	::= { pm1004vdcCtrlcsfUpInsTable 1 }


Pm1004vdcCtrlcsfUpInsEntry ::=
	SEQUENCE {
	pm1004vdcCtrlcsfUpInsIndex
		INTEGER,
	pm1004vdcCtrlcsfUpInsPortn
		EkiState
	}


pm1004vdcCtrlcsfUpInsIndex OBJECT-TYPE
	SYNTAX  INTEGER(0..128)
	MAX-ACCESS  read-only
	STATUS current
	DESCRIPTION
        "
        Index definition for the pm1004vdcCtrlcsfUpIns 
        table
        "
	::= { pm1004vdcCtrlcsfUpInsEntry 1 }


pm1004vdcCtrlcsfUpInsPortn OBJECT-TYPE
	SYNTAX  EkiState
	MAX-ACCESS read-write
	STATUS current
	DESCRIPTION
        "
        Client Signal Fail Insertion :This 
        OID, when set, inserts  a client 
        signal fail in the upstream client 
        Port.  <Help>  This control inserts 
        a Client Signal Fail for the client 
        port
        "
	::= { pm1004vdcCtrlcsfUpInsEntry 2 }


--- *********************************************************
---     TABLE for the pm1004vdcCtrlcaisDwIns articles
--- *********************************************************

pm1004vdcCtrlcaisDwInsTable OBJECT-TYPE
	SYNTAX  SEQUENCE OF Pm1004vdcCtrlcaisDwInsEntry
	MAX-ACCESS not-accessible
	STATUS current
	DESCRIPTION
        "
        List of pm1004vdcCtrlcaisDwIns 
        Article
        "
	::= { pm1004vdcCtrlClient 22 }


pm1004vdcCtrlcaisDwInsEntry OBJECT-TYPE
	SYNTAX Pm1004vdcCtrlcaisDwInsEntry
	MAX-ACCESS not-accessible
	STATUS current
	DESCRIPTION
        "
        Row definition for the pm1004vdcCtrlcaisDwIns 
        table
        "
	INDEX   { pm1004vdcCtrlcaisDwInsIndex }
	::= { pm1004vdcCtrlcaisDwInsTable 1 }


Pm1004vdcCtrlcaisDwInsEntry ::=
	SEQUENCE {
	pm1004vdcCtrlcaisDwInsIndex
		INTEGER,
	pm1004vdcCtrlcaisDwInsPortn
		EkiState
	}


pm1004vdcCtrlcaisDwInsIndex OBJECT-TYPE
	SYNTAX  INTEGER(0..128)
	MAX-ACCESS  read-only
	STATUS current
	DESCRIPTION
        "
        Index definition for the pm1004vdcCtrlcaisDwIns 
        table
        "
	::= { pm1004vdcCtrlcaisDwInsEntry 1 }


pm1004vdcCtrlcaisDwInsPortn OBJECT-TYPE
	SYNTAX  EkiState
	MAX-ACCESS read-write
	STATUS current
	DESCRIPTION
        "
        Client AIS Insertion :This OID, 
        when set, inserts a client AIS
         on the downstream client Port. 
         <Help>  This control inserts a 
        Client AIS for the client port
        "
	::= { pm1004vdcCtrlcaisDwInsEntry 2 }


--- *********************************************************
---     TABLE for the pm1004vdcCtrlclientAccessTermLoop articles
--- *********************************************************

pm1004vdcCtrlclientAccessTermLoopTable OBJECT-TYPE
	SYNTAX  SEQUENCE OF Pm1004vdcCtrlclientAccessTermLoopEntry
	MAX-ACCESS not-accessible
	STATUS current
	DESCRIPTION
        "
        List of pm1004vdcCtrlclientAccessTermLoop 
        Article
        "
	::= { pm1004vdcCtrlClient 26 }


pm1004vdcCtrlclientAccessTermLoopEntry OBJECT-TYPE
	SYNTAX Pm1004vdcCtrlclientAccessTermLoopEntry
	MAX-ACCESS not-accessible
	STATUS current
	DESCRIPTION
        "
        Row definition for the pm1004vdcCtrlclientAccessTermLoop 
        table
        "
	INDEX   { pm1004vdcCtrlclientAccessTermLoopIndex }
	::= { pm1004vdcCtrlclientAccessTermLoopTable 1 }


Pm1004vdcCtrlclientAccessTermLoopEntry ::=
	SEQUENCE {
	pm1004vdcCtrlclientAccessTermLoopIndex
		INTEGER,
	pm1004vdcCtrlclientAccessTermLoopPortn
		EkiState
	}


pm1004vdcCtrlclientAccessTermLoopIndex OBJECT-TYPE
	SYNTAX  INTEGER(0..128)
	MAX-ACCESS  read-only
	STATUS current
	DESCRIPTION
        "
        Index definition for the pm1004vdcCtrlclientAccessTermLoop 
        table
        "
	::= { pm1004vdcCtrlclientAccessTermLoopEntry 1 }


pm1004vdcCtrlclientAccessTermLoopPortn OBJECT-TYPE
	SYNTAX  EkiState
	MAX-ACCESS read-write
	STATUS current
	DESCRIPTION
        "
        Client Terminal Loopback :This 
        OID operates a Client Terminal
         Loopback, looping client input 
        signal on the client output port. 
        The loop is located on the line 
        transceiver  <Help> This maintenance 
        parameter operates a Client Terminal 
        Loopback, looping client input
         signal on the client output port. 
        The loop is located on the line 
        transceiver
        "
	::= { pm1004vdcCtrlclientAccessTermLoopEntry 2 }


--- *********************************************************
---     TABLE for the pm1004vdcCtrlrxVideoProtocol articles
--- *********************************************************

pm1004vdcCtrlrxVideoProtocolTable OBJECT-TYPE
	SYNTAX  SEQUENCE OF Pm1004vdcCtrlrxVideoProtocolEntry
	MAX-ACCESS not-accessible
	STATUS current
	DESCRIPTION
        "
        List of pm1004vdcCtrlrxVideoProtocol 
        Article
        "
	::= { pm1004vdcCtrlClient 43 }


pm1004vdcCtrlrxVideoProtocolEntry OBJECT-TYPE
	SYNTAX Pm1004vdcCtrlrxVideoProtocolEntry
	MAX-ACCESS not-accessible
	STATUS current
	DESCRIPTION
        "
        Row definition for the pm1004vdcCtrlrxVideoProtocol 
        table
        "
	INDEX   { pm1004vdcCtrlrxVideoProtocolIndex }
	::= { pm1004vdcCtrlrxVideoProtocolTable 1 }


Pm1004vdcCtrlrxVideoProtocolEntry ::=
	SEQUENCE {
	pm1004vdcCtrlrxVideoProtocolIndex
		INTEGER,
	pm1004vdcCtrlrxVideoProtocolPortn
		EkiState
	}


pm1004vdcCtrlrxVideoProtocolIndex OBJECT-TYPE
	SYNTAX  INTEGER(0..128)
	MAX-ACCESS  read-only
	STATUS current
	DESCRIPTION
        "
        Index definition for the pm1004vdcCtrlrxVideoProtocol 
        table
        "
	::= { pm1004vdcCtrlrxVideoProtocolEntry 1 }


pm1004vdcCtrlrxVideoProtocolPortn OBJECT-TYPE
	SYNTAX  EkiState
	MAX-ACCESS read-write
	STATUS current
	DESCRIPTION
        "
        Force DVB ASI On RX Side
 :This 
        OID selects the DVB ASI protocol 
        on the client port and disable
         the auto-sensing feature
  <Help> 
         This control selects the DVB ASI 
        protocol on the client port and 
        disable the auto-sensing feature

        "
	::= { pm1004vdcCtrlrxVideoProtocolEntry 2 }


--- *****************************************************
---     LEAF for the commAccessLoop article
--- *****************************************************
pm1004vdcCtrlcommAccessLoop OBJECT IDENTIFIER ::= { pm1004vdcCtrlLine 64 }




pm1004vdcCtrlCommAccessloop OBJECT-TYPE
	  SYNTAX EkiOnOff
	  MAX-ACCESS read-write
	  STATUS deprecated
	  DESCRIPTION
        "
        PM Full Access Loop Mode :This 
        OID, when set, puts the module
         in common access loop back, looping 
        the 10 Gb/s output signal on the 
        10 Gb/s input.
        "
	  ::= { pm1004vdcCtrlcommAccessLoop 1 }



--- *****************************************************
---     LEAF for the lineLoop article
--- *****************************************************
pm1004vdcCtrllineLoop OBJECT IDENTIFIER ::= { pm1004vdcCtrlLine 66 }




pm1004vdcCtrlLineLoop OBJECT-TYPE
	  SYNTAX EkiOnOff
	  MAX-ACCESS read-write
	  STATUS deprecated
	  DESCRIPTION
        "
        PM Line Loop Mode :This OID, when 
        set at '1' puts the module in line 
        loopback mode, looping the received 
        10 Gb/s signal on the transmit
         10 Gb/s output. The Upstream part 
        of the module is timed on the 10 
        Gb/s recovered clock in that case.
        "
	  ::= { pm1004vdcCtrllineLoop 1 }



--- *****************************************************
---     LEAF for the protMgnt article
--- *****************************************************
pm1004vdcCtrlProtMgnt OBJECT IDENTIFIER ::= { pm1004vdcCtrlLine 73 }




pm1004vdcCtrlLineNumber OBJECT-TYPE
	  SYNTAX Unsigned32 (0..3)
	  MAX-ACCESS read-write
	  STATUS current
	  DESCRIPTION
        "
        Active Line Number : This OID
         sets the active line number
        "
	  ::= { pm1004vdcCtrlProtMgnt 1 }



pm1004vdcCtrlProtMode OBJECT-TYPE
	  SYNTAX EkiMode
	  MAX-ACCESS read-write
	  STATUS current
	  DESCRIPTION
        "
        Line Switch Mode (Auto Or Manual) 
        :This bit selects the manual (1) 
        or automatic (0) switch method
          <Help>  This control defines
         the protection switch mode on
         the line interface
        "
	  ::= { pm1004vdcCtrlProtMgnt 2 }



--- *********************************************************
---     TABLE for the pm1004vdcCtrllineOosMode articles
--- *********************************************************

pm1004vdcCtrllineOosModeTable OBJECT-TYPE
	SYNTAX  SEQUENCE OF Pm1004vdcCtrllineOosModeEntry
	MAX-ACCESS not-accessible
	STATUS current
	DESCRIPTION
        "
        List of pm1004vdcCtrllineOosMode 
        Article
        "
	::= { pm1004vdcCtrlLine 74 }


pm1004vdcCtrllineOosModeEntry OBJECT-TYPE
	SYNTAX Pm1004vdcCtrllineOosModeEntry
	MAX-ACCESS not-accessible
	STATUS current
	DESCRIPTION
        "
        Row definition for the pm1004vdcCtrllineOosMode 
        table
        "
	INDEX   { pm1004vdcCtrllineOosModeIndex }
	::= { pm1004vdcCtrllineOosModeTable 1 }


Pm1004vdcCtrllineOosModeEntry ::=
	SEQUENCE {
	pm1004vdcCtrllineOosModeIndex
		INTEGER,
	pm1004vdcCtrllineOosModePortn
		EkiState
	}


pm1004vdcCtrllineOosModeIndex OBJECT-TYPE
	SYNTAX  INTEGER(0..128)
	MAX-ACCESS  read-only
	STATUS current
	DESCRIPTION
        "
        Index definition for the pm1004vdcCtrllineOosMode 
        table
        "
	::= { pm1004vdcCtrllineOosModeEntry 1 }


pm1004vdcCtrllineOosModePortn OBJECT-TYPE
	SYNTAX  EkiState
	MAX-ACCESS read-write
	STATUS current
	DESCRIPTION
        "
        Line Out Of Service (!Laser OFF!) 
        :This OID sets the line port Out 
        Of Service  <Help>  This control 
        defines the service state of the 
        line port
        "
	::= { pm1004vdcCtrllineOosModeEntry 2 }


--- *********************************************************
---     TABLE for the pm1004vdcCtrladddropClientRxProtect articles
--- *********************************************************

pm1004vdcCtrladddropClientRxProtectTable OBJECT-TYPE
	SYNTAX  SEQUENCE OF Pm1004vdcCtrladddropClientRxProtectEntry
	MAX-ACCESS not-accessible
	STATUS current
	DESCRIPTION
        "
        List of pm1004vdcCtrladddropClientRxProtect 
        Article
        "
	::= { pm1004vdcCtrlClient 128 }


pm1004vdcCtrladddropClientRxProtectEntry OBJECT-TYPE
	SYNTAX Pm1004vdcCtrladddropClientRxProtectEntry
	MAX-ACCESS not-accessible
	STATUS current
	DESCRIPTION
        "
        Row definition for the pm1004vdcCtrladddropClientRxProtect 
        table
        "
	INDEX   { pm1004vdcCtrladddropClientRxProtectIndex }
	::= { pm1004vdcCtrladddropClientRxProtectTable 1 }


Pm1004vdcCtrladddropClientRxProtectEntry ::=
	SEQUENCE {
	pm1004vdcCtrladddropClientRxProtectIndex
		INTEGER,
	pm1004vdcCtrladddropClientRxProtectPortn
		Pm1004vdcProtectionTimeSlot
	}


pm1004vdcCtrladddropClientRxProtectIndex OBJECT-TYPE
	SYNTAX  INTEGER(0..128)
	MAX-ACCESS  read-only
	STATUS current
	DESCRIPTION
        "
        Index definition for the pm1004vdcCtrladddropClientRxProtect 
        table
        "
	::= { pm1004vdcCtrladddropClientRxProtectEntry 1 }


pm1004vdcCtrladddropClientRxProtectPortn OBJECT-TYPE
	SYNTAX  Pm1004vdcProtectionTimeSlot
	MAX-ACCESS read-write
	STATUS current
	DESCRIPTION
        "
        Client Switch Mode :This bit selects 
        the manual (1) or automatic (0) 
        switch method  <Help>  This control 
        defines the protection switch mode 
        on the client interface
        "
	::= { pm1004vdcCtrladddropClientRxProtectEntry 2 }


--- *********************************************************
---     TABLE for the pm1004vdcCtrladddropTsClientMode articles
--- *********************************************************

pm1004vdcCtrladddropTsClientModeTable OBJECT-TYPE
	SYNTAX  SEQUENCE OF Pm1004vdcCtrladddropTsClientModeEntry
	MAX-ACCESS not-accessible
	STATUS current
	DESCRIPTION
        "
        List of pm1004vdcCtrladddropTsClientMode 
        Article
        "
	::= { pm1004vdcCtrlClient 136 }


pm1004vdcCtrladddropTsClientModeEntry OBJECT-TYPE
	SYNTAX Pm1004vdcCtrladddropTsClientModeEntry
	MAX-ACCESS not-accessible
	STATUS current
	DESCRIPTION
        "
        Row definition for the pm1004vdcCtrladddropTsClientMode 
        table
        "
	INDEX   { pm1004vdcCtrladddropTsClientModeIndex }
	::= { pm1004vdcCtrladddropTsClientModeTable 1 }


Pm1004vdcCtrladddropTsClientModeEntry ::=
	SEQUENCE {
	pm1004vdcCtrladddropTsClientModeIndex
		INTEGER,
	pm1004vdcCtrladddropTsClientModePortn
		Pm1004vdcModeTimeSlot
	}


pm1004vdcCtrladddropTsClientModeIndex OBJECT-TYPE
	SYNTAX  INTEGER(0..128)
	MAX-ACCESS  read-only
	STATUS current
	DESCRIPTION
        "
        Index definition for the pm1004vdcCtrladddropTsClientMode 
        table
        "
	::= { pm1004vdcCtrladddropTsClientModeEntry 1 }


pm1004vdcCtrladddropTsClientModePortn OBJECT-TYPE
	SYNTAX  Pm1004vdcModeTimeSlot
	MAX-ACCESS read-write
	STATUS current
	DESCRIPTION
        "
        Client Mode :This OID selects
         the mode on the client  <Help> 
          This control defines the mode 
        (Add/Drop or Split&Select) of the 
        Client
        "
	::= { pm1004vdcCtrladddropTsClientModeEntry 2 }


--- *****************************************************
---     LEAF for the ledTest article
--- *****************************************************
pm1004vdcCtrlledTest OBJECT IDENTIFIER ::= { pm1004vdcCtrlOther 192 }




pm1004vdcCtrlLedOff OBJECT-TYPE
	  SYNTAX EkiOnOff
	  MAX-ACCESS read-write
	  STATUS current
	  DESCRIPTION
        "
        Leds Off :This OID switches off 
        all the Leds as a test feature. 
         <Help>  This control initiates 
        a test leds turning all the LEDs 
        to OFF
        "
	  ::= { pm1004vdcCtrlledTest 3 }



pm1004vdcCtrlRedLed OBJECT-TYPE
	  SYNTAX EkiOnOff
	  MAX-ACCESS read-write
	  STATUS current
	  DESCRIPTION
        "
        Red Leds Test :This OID switches 
        on all the red Leds as a test feature. 
         <Help>  This control initiates 
        a test leds turning all the LEDs 
        to red
        "
	  ::= { pm1004vdcCtrlledTest 2 }



pm1004vdcCtrlGreenLed OBJECT-TYPE
	  SYNTAX EkiOnOff
	  MAX-ACCESS read-write
	  STATUS current
	  DESCRIPTION
        "
        Green Leds Test :This OID switches 
        on all the green Leds as a test 
        feature.  <Help>  This control
         initiates a test leds turning
         all the LEDs to green
        "
	  ::= { pm1004vdcCtrlledTest 1 }



--- *****************************************************
---     LEAF for the moduleOosMode article
--- *****************************************************
pm1004vdcCtrlmoduleOosMode OBJECT IDENTIFIER ::= { pm1004vdcCtrlOther 193 }




pm1004vdcCtrlModuleOosMode OBJECT-TYPE
	  SYNTAX EkiOnOff
	  MAX-ACCESS read-write
	  STATUS current
	  DESCRIPTION
        "
        PM Out Of Service :This OID sets 
        the PM Out Of Service  <Help> 
         This control defines the service 
        state of the complete module
        "
	  ::= { pm1004vdcCtrlmoduleOosMode 1 }



--- *****************************************************
---     LEAF for the maintenanceMode article
--- *****************************************************
pm1004vdcCtrlmaintenanceMode OBJECT IDENTIFIER ::= { pm1004vdcCtrlOther 197 }




pm1004vdcCtrlMaintenanceMode OBJECT-TYPE
	  SYNTAX EkiOnOff
	  MAX-ACCESS read-write
	  STATUS current
	  DESCRIPTION
        "
        Enable Maintenance :This OID enables 
        the maintenance mode on the PM. 
         <Help>  This control enables the 
        maintenance mode on the PM.
        "
	  ::= { pm1004vdcCtrlmaintenanceMode 1 }



--- *********************************************************
---     TABLE for the pm1004vdcCtrldccEnable articles
--- *********************************************************

pm1004vdcCtrldccEnableTable OBJECT-TYPE
	SYNTAX  SEQUENCE OF Pm1004vdcCtrldccEnableEntry
	MAX-ACCESS not-accessible
	STATUS current
	DESCRIPTION
        "
        List of pm1004vdcCtrldccEnable 
        Article
        "
	::= { pm1004vdcCtrlLine 198 }


pm1004vdcCtrldccEnableEntry OBJECT-TYPE
	SYNTAX Pm1004vdcCtrldccEnableEntry
	MAX-ACCESS not-accessible
	STATUS current
	DESCRIPTION
        "
        Row definition for the pm1004vdcCtrldccEnable 
        table
        "
	INDEX   { pm1004vdcCtrldccEnableIndex }
	::= { pm1004vdcCtrldccEnableTable 1 }


Pm1004vdcCtrldccEnableEntry ::=
	SEQUENCE {
	pm1004vdcCtrldccEnableIndex
		INTEGER,
	pm1004vdcCtrldccEnablePortn
		EkiState
	}


pm1004vdcCtrldccEnableIndex OBJECT-TYPE
	SYNTAX  INTEGER(0..128)
	MAX-ACCESS  read-only
	STATUS current
	DESCRIPTION
        "
        Index definition for the pm1004vdcCtrldccEnable 
        table
        "
	::= { pm1004vdcCtrldccEnableEntry 1 }


pm1004vdcCtrldccEnablePortn OBJECT-TYPE
	SYNTAX  EkiState
	MAX-ACCESS read-write
	STATUS current
	DESCRIPTION
        "
        DCC Mode : This OID enables the 
        DCC mode on the PM  <Help>   This 
        control enables the DCC mode on 
        the PM
        "
	::= { pm1004vdcCtrldccEnableEntry 2 }


--- *********************************************************
---     TABLE for the pm1004vdcCtrlxfpOnoff articles
--- *********************************************************

pm1004vdcCtrlxfpOnoffTable OBJECT-TYPE
	SYNTAX  SEQUENCE OF Pm1004vdcCtrlxfpOnoffEntry
	MAX-ACCESS not-accessible
	STATUS current
	DESCRIPTION
        "
        List of pm1004vdcCtrlxfpOnoff
         Article
        "
	::= { pm1004vdcCtrlLine 208 }


pm1004vdcCtrlxfpOnoffEntry OBJECT-TYPE
	SYNTAX Pm1004vdcCtrlxfpOnoffEntry
	MAX-ACCESS not-accessible
	STATUS current
	DESCRIPTION
        "
        Row definition for the pm1004vdcCtrlxfpOnoff 
        table
        "
	INDEX   { pm1004vdcCtrlxfpOnoffIndex }
	::= { pm1004vdcCtrlxfpOnoffTable 1 }


Pm1004vdcCtrlxfpOnoffEntry ::=
	SEQUENCE {
	pm1004vdcCtrlxfpOnoffIndex
		INTEGER,
	pm1004vdcCtrlxfpOnoffPortn
		EkiState
	}


pm1004vdcCtrlxfpOnoffIndex OBJECT-TYPE
	SYNTAX  INTEGER(0..128)
	MAX-ACCESS  read-only
	STATUS current
	DESCRIPTION
        "
        Index definition for the pm1004vdcCtrlxfpOnoff 
        table
        "
	::= { pm1004vdcCtrlxfpOnoffEntry 1 }


pm1004vdcCtrlxfpOnoffPortn OBJECT-TYPE
	SYNTAX  EkiState
	MAX-ACCESS read-write
	STATUS current
	DESCRIPTION
        "
        XFP/OTX Optical Laser OFF :This 
        OID switches off the XFP or the 
        OTX  <Help>  This control defines 
        the laser state of the line transceiver
        "
	::= { pm1004vdcCtrlxfpOnoffEntry 2 }


--- *********************************************************
---     TABLE for the pm1004vdcCtrlxfpLineLoop articles
--- *********************************************************

pm1004vdcCtrlxfpLineLoopTable OBJECT-TYPE
	SYNTAX  SEQUENCE OF Pm1004vdcCtrlxfpLineLoopEntry
	MAX-ACCESS not-accessible
	STATUS current
	DESCRIPTION
        "
        List of pm1004vdcCtrlxfpLineLoop 
        Article
        "
	::= { pm1004vdcCtrlLine 209 }


pm1004vdcCtrlxfpLineLoopEntry OBJECT-TYPE
	SYNTAX Pm1004vdcCtrlxfpLineLoopEntry
	MAX-ACCESS not-accessible
	STATUS current
	DESCRIPTION
        "
        Row definition for the pm1004vdcCtrlxfpLineLoop 
        table
        "
	INDEX   { pm1004vdcCtrlxfpLineLoopIndex }
	::= { pm1004vdcCtrlxfpLineLoopTable 1 }


Pm1004vdcCtrlxfpLineLoopEntry ::=
	SEQUENCE {
	pm1004vdcCtrlxfpLineLoopIndex
		INTEGER,
	pm1004vdcCtrlxfpLineLoopPortn
		EkiState
	}


pm1004vdcCtrlxfpLineLoopIndex OBJECT-TYPE
	SYNTAX  INTEGER(0..128)
	MAX-ACCESS  read-only
	STATUS current
	DESCRIPTION
        "
        Index definition for the pm1004vdcCtrlxfpLineLoop 
        table
        "
	::= { pm1004vdcCtrlxfpLineLoopEntry 1 }


pm1004vdcCtrlxfpLineLoopPortn OBJECT-TYPE
	SYNTAX  EkiState
	MAX-ACCESS read-write
	STATUS current
	DESCRIPTION
        "
        Line Facility Loopback :This OID 
        operates a Line Facility Loopback, 
        looping line input signal on the 
        line output port. The loop is located 
        on the line transceiver. If the 
        Line signal carries DCC, the management 
        network is impacted  <Help> This 
        maintenance parameter operates
         a Line Facility Loopback, looping 
        line input signal on the line output 
        port. The loop is located on the 
        line transceiver. If the Line signal 
        carries DCC, the management network 
        is impacted
        "
	::= { pm1004vdcCtrlxfpLineLoopEntry 2 }


--- *********************************************************
---     TABLE for the pm1004vdcCtrlxfpXfiLoop articles
--- *********************************************************

pm1004vdcCtrlxfpXfiLoopTable OBJECT-TYPE
	SYNTAX  SEQUENCE OF Pm1004vdcCtrlxfpXfiLoopEntry
	MAX-ACCESS not-accessible
	STATUS current
	DESCRIPTION
        "
        List of pm1004vdcCtrlxfpXfiLoop 
        Article
        "
	::= { pm1004vdcCtrlLine 210 }


pm1004vdcCtrlxfpXfiLoopEntry OBJECT-TYPE
	SYNTAX Pm1004vdcCtrlxfpXfiLoopEntry
	MAX-ACCESS not-accessible
	STATUS current
	DESCRIPTION
        "
        Row definition for the pm1004vdcCtrlxfpXfiLoop 
        table
        "
	INDEX   { pm1004vdcCtrlxfpXfiLoopIndex }
	::= { pm1004vdcCtrlxfpXfiLoopTable 1 }


Pm1004vdcCtrlxfpXfiLoopEntry ::=
	SEQUENCE {
	pm1004vdcCtrlxfpXfiLoopIndex
		INTEGER,
	pm1004vdcCtrlxfpXfiLoopPortn
		EkiState
	}


pm1004vdcCtrlxfpXfiLoopIndex OBJECT-TYPE
	SYNTAX  INTEGER(0..128)
	MAX-ACCESS  read-only
	STATUS current
	DESCRIPTION
        "
        Index definition for the pm1004vdcCtrlxfpXfiLoop 
        table
        "
	::= { pm1004vdcCtrlxfpXfiLoopEntry 1 }


pm1004vdcCtrlxfpXfiLoopPortn OBJECT-TYPE
	SYNTAX  EkiState
	MAX-ACCESS read-write
	STATUS current
	DESCRIPTION
        "
        Line Terminal Loopback :This OID 
        operates a Line Terminal Loopback, 
        looping line input signal on the 
        line output port. The loop is located 
        on all client transceivers  <Help> 
        This maintenance parameter operates 
        a Line Terminal Loopback, looping 
        line input signal on the line output 
        port. The loop is located on all 
        client transceivers.
        "
	::= { pm1004vdcCtrlxfpXfiLoopEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm1004vdcCntdfrmB1ErrCnt articles
--- *********************************************************

pm1004vdcCntdfrmB1ErrCntTable OBJECT-TYPE
	SYNTAX  SEQUENCE OF Pm1004vdcCntdfrmB1ErrCntEntry
	MAX-ACCESS not-accessible
	STATUS current
	DESCRIPTION
        "
        List of pm1004vdcCntdfrmB1ErrCnt 
        Article
        "
	::= { pm1004vdcCntLine 152 }


pm1004vdcCntdfrmB1ErrCntEntry OBJECT-TYPE
	SYNTAX Pm1004vdcCntdfrmB1ErrCntEntry
	MAX-ACCESS not-accessible
	STATUS current
	DESCRIPTION
        "
        Row definition for the pm1004vdcCntdfrmB1ErrCnt 
        table
        "
	INDEX   { pm1004vdcCntdfrmB1ErrCntIndex }
	::= { pm1004vdcCntdfrmB1ErrCntTable 1 }


Pm1004vdcCntdfrmB1ErrCntEntry ::=
	SEQUENCE {
	pm1004vdcCntdfrmB1ErrCntIndex
		INTEGER,
	pm1004vdcCntdfrmB1ErrCntValuePortn
		Counter32,
	pm1004vdcCntdfrmB1ErrCntErrorPortn
		EkiOnOff,
	pm1004vdcCntdfrmB1ErrCntOverloadPortn
		EkiOnOff
	}


pm1004vdcCntdfrmB1ErrCntIndex OBJECT-TYPE
	SYNTAX  INTEGER(0..128)
	MAX-ACCESS  read-only
	STATUS current
	DESCRIPTION
        "
        Index definition for the pm1004vdcCntdfrmB1ErrCnt 
        table
        "
	::= { pm1004vdcCntdfrmB1ErrCntEntry 1 }


pm1004vdcCntdfrmB1ErrCntValuePortn OBJECT-TYPE
	SYNTAX  Counter32
	MAX-ACCESS read-only
	STATUS current
	DESCRIPTION
        "
        Line Input SM-BIP8 Errors :This 
        counter is incremented each time 
        a B1 error is detected on the Deframer 
        input stream.  <Help>  This counter 
        gives the number of B1 errors on 
        the line port
        "
	::= { pm1004vdcCntdfrmB1ErrCntEntry 2 }


pm1004vdcCntdfrmB1ErrCntErrorPortn OBJECT-TYPE
	SYNTAX  EkiOnOff
	MAX-ACCESS read-only
	STATUS current
	DESCRIPTION
        "
        Line Counter Error :This OID when 
        set indicates the B1 error counter 
        value is invalid on Port
        "
	::= { pm1004vdcCntdfrmB1ErrCntEntry 3 }


pm1004vdcCntdfrmB1ErrCntOverloadPortn OBJECT-TYPE
	SYNTAX  EkiOnOff
	MAX-ACCESS read-only
	STATUS current
	DESCRIPTION
        "
        Line Counter Overload :This OID 
        when set indicates a B1 error counter 
        overload on Port
        "
	::= { pm1004vdcCntdfrmB1ErrCntEntry 4 }


--- *********************************************************
---     TABLE for the pm1004vdcCntdfrmTimCnt articles
--- *********************************************************

pm1004vdcCntdfrmTimCntTable OBJECT-TYPE
	SYNTAX  SEQUENCE OF Pm1004vdcCntdfrmTimCntEntry
	MAX-ACCESS not-accessible
	STATUS current
	DESCRIPTION
        "
        List of pm1004vdcCntdfrmTimCnt 
        Article
        "
	::= { pm1004vdcCntLine 153 }


pm1004vdcCntdfrmTimCntEntry OBJECT-TYPE
	SYNTAX Pm1004vdcCntdfrmTimCntEntry
	MAX-ACCESS not-accessible
	STATUS current
	DESCRIPTION
        "
        Row definition for the pm1004vdcCntdfrmTimCnt 
        table
        "
	INDEX   { pm1004vdcCntdfrmTimCntIndex }
	::= { pm1004vdcCntdfrmTimCntTable 1 }


Pm1004vdcCntdfrmTimCntEntry ::=
	SEQUENCE {
	pm1004vdcCntdfrmTimCntIndex
		INTEGER,
	pm1004vdcCntdfrmTimCntValuePortn
		Counter32,
	pm1004vdcCntdfrmTimCntErrorPortn
		EkiOnOff,
	pm1004vdcCntdfrmTimCntOverloadPortn
		EkiOnOff
	}


pm1004vdcCntdfrmTimCntIndex OBJECT-TYPE
	SYNTAX  INTEGER(0..128)
	MAX-ACCESS  read-only
	STATUS current
	DESCRIPTION
        "
        Index definition for the pm1004vdcCntdfrmTimCnt 
        table
        "
	::= { pm1004vdcCntdfrmTimCntEntry 1 }


pm1004vdcCntdfrmTimCntValuePortn OBJECT-TYPE
	SYNTAX  Counter32
	MAX-ACCESS read-only
	STATUS current
	DESCRIPTION
        "
        Line Timer Counter :This is the 
        timing counter dedicated to the 
        downstream deframer counters. It 
        is incremented every 125 us.
        "
	::= { pm1004vdcCntdfrmTimCntEntry 2 }


pm1004vdcCntdfrmTimCntErrorPortn OBJECT-TYPE
	SYNTAX  EkiOnOff
	MAX-ACCESS read-only
	STATUS current
	DESCRIPTION
        "
        Line Counter Error :This OID when 
        set indicates the deframer timer 
        counter value is invalid on Port
        "
	::= { pm1004vdcCntdfrmTimCntEntry 3 }


pm1004vdcCntdfrmTimCntOverloadPortn OBJECT-TYPE
	SYNTAX  EkiOnOff
	MAX-ACCESS read-only
	STATUS current
	DESCRIPTION
        "
        Line Counter Overload :This OID 
        when set indicates a deframer timer 
        counter overload on Port
        "
	::= { pm1004vdcCntdfrmTimCntEntry 4 }


pm1004vdcCntCountersReset  OBJECT-TYPE
	SYNTAX EkiOnOff
	MAX-ACCESS read-write
	STATUS current
	DESCRIPTION
	"Counters Reset:This OID resets and restarts all the counters"
	::= { pm1004vdccounters  259 }

pm1004vdcCntCountersStop  OBJECT-TYPE
	SYNTAX EkiOnOff
	MAX-ACCESS read-write
	STATUS current
	DESCRIPTION
	"Counters stop:This OID stops all the counters"
	::= { pm1004vdccounters 260 }






--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pm1004vdcMonupRmonByteCnt articles
--- *********************************************************

pm1004vdcMonupRmonByteCntTable OBJECT-TYPE
	SYNTAX  SEQUENCE OF Pm1004vdcMonupRmonByteCntEntry
	MAX-ACCESS not-accessible
	STATUS current
	DESCRIPTION
        "
        List of pm1004vdcMonupRmonByteCnt 
        Article
        "
	::= { pm1004vdcMonClientRmonCounter 16 }


pm1004vdcMonupRmonByteCntEntry OBJECT-TYPE
	SYNTAX Pm1004vdcMonupRmonByteCntEntry
	MAX-ACCESS not-accessible
	STATUS current
	DESCRIPTION
        "
        Row definition for the pm1004vdcMonupRmonByteCnt 
        table
        "
	INDEX   { pm1004vdcMonupRmonByteCntIndex }
	::= { pm1004vdcMonupRmonByteCntTable 1 }


Pm1004vdcMonupRmonByteCntEntry ::=
	SEQUENCE {
	pm1004vdcMonupRmonByteCntIndex
		INTEGER,
	pm1004vdcMonupRmonByteCntValuePortn
		Counter64,
	pm1004vdcMonupRmonByteCntErrorPortn
		EkiOnOff,
	pm1004vdcMonupRmonByteCntOverloadPortn
		EkiOnOff
	}


pm1004vdcMonupRmonByteCntIndex OBJECT-TYPE
	SYNTAX  INTEGER(0..128)
	MAX-ACCESS  read-only
	STATUS current
	DESCRIPTION
        "
        Index definition for the pm1004vdcMonupRmonByteCnt 
        table
        "
	::= { pm1004vdcMonupRmonByteCntEntry 1 }


pm1004vdcMonupRmonByteCntValuePortn OBJECT-TYPE
	SYNTAX  Counter64
	MAX-ACCESS read-only
	STATUS current
	DESCRIPTION
        "
        Client Input Bytes :This counter 
        is increased each time a data byte 
        is received on the client port
          <Help>  This counter gives the 
        number of bytes received on the 
        client port
        "
	::= { pm1004vdcMonupRmonByteCntEntry 2 }


pm1004vdcMonupRmonByteCntErrorPortn OBJECT-TYPE
	SYNTAX  EkiOnOff
	MAX-ACCESS read-only
	STATUS current
	DESCRIPTION
        "
        Bytes Counter Error :This OID
         when set indicates the Bytes counter 
        value is invalid on clinet port
        "
	::= { pm1004vdcMonupRmonByteCntEntry 3 }


pm1004vdcMonupRmonByteCntOverloadPortn OBJECT-TYPE
	SYNTAX  EkiOnOff
	MAX-ACCESS read-only
	STATUS current
	DESCRIPTION
        "
        Bytes Counter Overload :This OID 
        when set indicates a Bytes counter 
        overload on client port
        "
	::= { pm1004vdcMonupRmonByteCntEntry 4 }


--- *********************************************************
---     TABLE for the pm1004vdcMonupRmonCrcErrorCnt articles
--- *********************************************************

pm1004vdcMonupRmonCrcErrorCntTable OBJECT-TYPE
	SYNTAX  SEQUENCE OF Pm1004vdcMonupRmonCrcErrorCntEntry
	MAX-ACCESS not-accessible
	STATUS current
	DESCRIPTION
        "
        List of pm1004vdcMonupRmonCrcErrorCnt 
        Article
        "
	::= { pm1004vdcMonClientRmonCounter 24 }


pm1004vdcMonupRmonCrcErrorCntEntry OBJECT-TYPE
	SYNTAX Pm1004vdcMonupRmonCrcErrorCntEntry
	MAX-ACCESS not-accessible
	STATUS current
	DESCRIPTION
        "
        Row definition for the pm1004vdcMonupRmonCrcErrorCnt 
        table
        "
	INDEX   { pm1004vdcMonupRmonCrcErrorCntIndex }
	::= { pm1004vdcMonupRmonCrcErrorCntTable 1 }


Pm1004vdcMonupRmonCrcErrorCntEntry ::=
	SEQUENCE {
	pm1004vdcMonupRmonCrcErrorCntIndex
		INTEGER,
	pm1004vdcMonupRmonCrcErrorCntValuePortn
		Counter64,
	pm1004vdcMonupRmonCrcErrorCntErrorPortn
		EkiOnOff,
	pm1004vdcMonupRmonCrcErrorCntOverloadPortn
		EkiOnOff
	}


pm1004vdcMonupRmonCrcErrorCntIndex OBJECT-TYPE
	SYNTAX  INTEGER(0..128)
	MAX-ACCESS  read-only
	STATUS current
	DESCRIPTION
        "
        Index definition for the pm1004vdcMonupRmonCrcErrorCnt 
        table
        "
	::= { pm1004vdcMonupRmonCrcErrorCntEntry 1 }


pm1004vdcMonupRmonCrcErrorCntValuePortn OBJECT-TYPE
	SYNTAX  Counter64
	MAX-ACCESS read-only
	STATUS current
	DESCRIPTION
        "
        Client Input CRC Errors :This
         counter is increased each time 
        a CRC error is detected on the
         client port  <Help>  This counter 
        gives the number of CRC Errors
         received on the client port
        "
	::= { pm1004vdcMonupRmonCrcErrorCntEntry 2 }


pm1004vdcMonupRmonCrcErrorCntErrorPortn OBJECT-TYPE
	SYNTAX  EkiOnOff
	MAX-ACCESS read-only
	STATUS current
	DESCRIPTION
        "
        CRC Errors Counter Error :This 
        OID when set indicates the CRC
         Errors counter value is invalid 
        on clinet port
        "
	::= { pm1004vdcMonupRmonCrcErrorCntEntry 3 }


pm1004vdcMonupRmonCrcErrorCntOverloadPortn OBJECT-TYPE
	SYNTAX  EkiOnOff
	MAX-ACCESS read-only
	STATUS current
	DESCRIPTION
        "
        CRC Errors Counter Overload :This 
        OID when set indicates a CRC Errors 
        counter overload on client port
        "
	::= { pm1004vdcMonupRmonCrcErrorCntEntry 4 }


--- *********************************************************
---     TABLE for the pm1004vdcMonupRmonPacketsCnt articles
--- *********************************************************

pm1004vdcMonupRmonPacketsCntTable OBJECT-TYPE
	SYNTAX  SEQUENCE OF Pm1004vdcMonupRmonPacketsCntEntry
	MAX-ACCESS not-accessible
	STATUS current
	DESCRIPTION
        "
        List of pm1004vdcMonupRmonPacketsCnt 
        Article
        "
	::= { pm1004vdcMonClientRmonCounter 32 }


pm1004vdcMonupRmonPacketsCntEntry OBJECT-TYPE
	SYNTAX Pm1004vdcMonupRmonPacketsCntEntry
	MAX-ACCESS not-accessible
	STATUS current
	DESCRIPTION
        "
        Row definition for the pm1004vdcMonupRmonPacketsCnt 
        table
        "
	INDEX   { pm1004vdcMonupRmonPacketsCntIndex }
	::= { pm1004vdcMonupRmonPacketsCntTable 1 }


Pm1004vdcMonupRmonPacketsCntEntry ::=
	SEQUENCE {
	pm1004vdcMonupRmonPacketsCntIndex
		INTEGER,
	pm1004vdcMonupRmonPacketsCntValuePortn
		Counter64,
	pm1004vdcMonupRmonPacketsCntErrorPortn
		EkiOnOff,
	pm1004vdcMonupRmonPacketsCntOverloadPortn
		EkiOnOff
	}


pm1004vdcMonupRmonPacketsCntIndex OBJECT-TYPE
	SYNTAX  INTEGER(0..128)
	MAX-ACCESS  read-only
	STATUS current
	DESCRIPTION
        "
        Index definition for the pm1004vdcMonupRmonPacketsCnt 
        table
        "
	::= { pm1004vdcMonupRmonPacketsCntEntry 1 }


pm1004vdcMonupRmonPacketsCntValuePortn OBJECT-TYPE
	SYNTAX  Counter64
	MAX-ACCESS read-only
	STATUS current
	DESCRIPTION
        "
        Client Input Packets :This counter 
        is increased each time a packet 
        is received on the client port
          <Help>  This counter gives the 
        number of packets received on the 
        client port
        "
	::= { pm1004vdcMonupRmonPacketsCntEntry 2 }


pm1004vdcMonupRmonPacketsCntErrorPortn OBJECT-TYPE
	SYNTAX  EkiOnOff
	MAX-ACCESS read-only
	STATUS current
	DESCRIPTION
        "
        Packets Counter Error :This OID 
        when set indicates the Packets
         counter value is invalid on clinet 
        port
        "
	::= { pm1004vdcMonupRmonPacketsCntEntry 3 }


pm1004vdcMonupRmonPacketsCntOverloadPortn OBJECT-TYPE
	SYNTAX  EkiOnOff
	MAX-ACCESS read-only
	STATUS current
	DESCRIPTION
        "
        Packets Counter Overload :This 
        OID when set indicates a Packets 
        counter overload on client port
        "
	::= { pm1004vdcMonupRmonPacketsCntEntry 4 }


--- *********************************************************
---     TABLE for the pm1004vdcMonupRmonBroadcastCnt articles
--- *********************************************************

pm1004vdcMonupRmonBroadcastCntTable OBJECT-TYPE
	SYNTAX  SEQUENCE OF Pm1004vdcMonupRmonBroadcastCntEntry
	MAX-ACCESS not-accessible
	STATUS current
	DESCRIPTION
        "
        List of pm1004vdcMonupRmonBroadcastCnt 
        Article
        "
	::= { pm1004vdcMonClientRmonCounter 40 }


pm1004vdcMonupRmonBroadcastCntEntry OBJECT-TYPE
	SYNTAX Pm1004vdcMonupRmonBroadcastCntEntry
	MAX-ACCESS not-accessible
	STATUS current
	DESCRIPTION
        "
        Row definition for the pm1004vdcMonupRmonBroadcastCnt 
        table
        "
	INDEX   { pm1004vdcMonupRmonBroadcastCntIndex }
	::= { pm1004vdcMonupRmonBroadcastCntTable 1 }


Pm1004vdcMonupRmonBroadcastCntEntry ::=
	SEQUENCE {
	pm1004vdcMonupRmonBroadcastCntIndex
		INTEGER,
	pm1004vdcMonupRmonBroadcastCntValuePortn
		Counter64,
	pm1004vdcMonupRmonBroadcastCntErrorPortn
		EkiOnOff,
	pm1004vdcMonupRmonBroadcastCntOverloadPortn
		EkiOnOff
	}


pm1004vdcMonupRmonBroadcastCntIndex OBJECT-TYPE
	SYNTAX  INTEGER(0..128)
	MAX-ACCESS  read-only
	STATUS current
	DESCRIPTION
        "
        Index definition for the pm1004vdcMonupRmonBroadcastCnt 
        table
        "
	::= { pm1004vdcMonupRmonBroadcastCntEntry 1 }


pm1004vdcMonupRmonBroadcastCntValuePortn OBJECT-TYPE
	SYNTAX  Counter64
	MAX-ACCESS read-only
	STATUS current
	DESCRIPTION
        "
        Client Input Broadcast Packets 
        :This counter is increased each 
        time a broadcast packet is received 
        on the client port  <Help>  This 
        counter gives the number of Broadcast 
        packets received on the client
         port
        "
	::= { pm1004vdcMonupRmonBroadcastCntEntry 2 }


pm1004vdcMonupRmonBroadcastCntErrorPortn OBJECT-TYPE
	SYNTAX  EkiOnOff
	MAX-ACCESS read-only
	STATUS current
	DESCRIPTION
        "
        Broadcast Counter Error :This
         OID when set indicates the Broadcast 
        counter value is invalid on clinet 
        port
        "
	::= { pm1004vdcMonupRmonBroadcastCntEntry 3 }


pm1004vdcMonupRmonBroadcastCntOverloadPortn OBJECT-TYPE
	SYNTAX  EkiOnOff
	MAX-ACCESS read-only
	STATUS current
	DESCRIPTION
        "
        Broadcast Counter Overload :This 
        OID when set indicates a Broadcast 
        counter overload on client port
        "
	::= { pm1004vdcMonupRmonBroadcastCntEntry 4 }


--- *********************************************************
---     TABLE for the pm1004vdcMonupRmonMulticastCnt articles
--- *********************************************************

pm1004vdcMonupRmonMulticastCntTable OBJECT-TYPE
	SYNTAX  SEQUENCE OF Pm1004vdcMonupRmonMulticastCntEntry
	MAX-ACCESS not-accessible
	STATUS current
	DESCRIPTION
        "
        List of pm1004vdcMonupRmonMulticastCnt 
        Article
        "
	::= { pm1004vdcMonClientRmonCounter 48 }


pm1004vdcMonupRmonMulticastCntEntry OBJECT-TYPE
	SYNTAX Pm1004vdcMonupRmonMulticastCntEntry
	MAX-ACCESS not-accessible
	STATUS current
	DESCRIPTION
        "
        Row definition for the pm1004vdcMonupRmonMulticastCnt 
        table
        "
	INDEX   { pm1004vdcMonupRmonMulticastCntIndex }
	::= { pm1004vdcMonupRmonMulticastCntTable 1 }


Pm1004vdcMonupRmonMulticastCntEntry ::=
	SEQUENCE {
	pm1004vdcMonupRmonMulticastCntIndex
		INTEGER,
	pm1004vdcMonupRmonMulticastCntValuePortn
		Counter64,
	pm1004vdcMonupRmonMulticastCntErrorPortn
		EkiOnOff,
	pm1004vdcMonupRmonMulticastCntOverloadPortn
		EkiOnOff
	}


pm1004vdcMonupRmonMulticastCntIndex OBJECT-TYPE
	SYNTAX  INTEGER(0..128)
	MAX-ACCESS  read-only
	STATUS current
	DESCRIPTION
        "
        Index definition for the pm1004vdcMonupRmonMulticastCnt 
        table
        "
	::= { pm1004vdcMonupRmonMulticastCntEntry 1 }


pm1004vdcMonupRmonMulticastCntValuePortn OBJECT-TYPE
	SYNTAX  Counter64
	MAX-ACCESS read-only
	STATUS current
	DESCRIPTION
        "
        Client Input Multicast Packets 
        :This counter is increased each 
        time a Multicast packet is received 
        on the client port  <Help>  This 
        counter gives the number of Multicast 
        packets received on the client
         port
        "
	::= { pm1004vdcMonupRmonMulticastCntEntry 2 }


pm1004vdcMonupRmonMulticastCntErrorPortn OBJECT-TYPE
	SYNTAX  EkiOnOff
	MAX-ACCESS read-only
	STATUS current
	DESCRIPTION
        "
        Multicast Counter Error :This
         OID when set indicates the Multicast 
        counter value is invalid on clinet 
        port
        "
	::= { pm1004vdcMonupRmonMulticastCntEntry 3 }


pm1004vdcMonupRmonMulticastCntOverloadPortn OBJECT-TYPE
	SYNTAX  EkiOnOff
	MAX-ACCESS read-only
	STATUS current
	DESCRIPTION
        "
        Multicast Counter Overload :This 
        OID when set indicates a Multicast 
        counter overload on client port
        "
	::= { pm1004vdcMonupRmonMulticastCntEntry 4 }


--- *********************************************************
---     TABLE for the pm1004vdcMonupLineRmonByteCnt articles
--- *********************************************************

pm1004vdcMonupLineRmonByteCntTable OBJECT-TYPE
	SYNTAX  SEQUENCE OF Pm1004vdcMonupLineRmonByteCntEntry
	MAX-ACCESS not-accessible
	STATUS current
	DESCRIPTION
        "
        List of pm1004vdcMonupLineRmonByteCnt 
        Article
        "
	::= { pm1004vdcMonClientRmonCounter 208 }


pm1004vdcMonupLineRmonByteCntEntry OBJECT-TYPE
	SYNTAX Pm1004vdcMonupLineRmonByteCntEntry
	MAX-ACCESS not-accessible
	STATUS current
	DESCRIPTION
        "
        Row definition for the pm1004vdcMonupLineRmonByteCnt 
        table
        "
	INDEX   { pm1004vdcMonupLineRmonByteCntIndex }
	::= { pm1004vdcMonupLineRmonByteCntTable 1 }


Pm1004vdcMonupLineRmonByteCntEntry ::=
	SEQUENCE {
	pm1004vdcMonupLineRmonByteCntIndex
		INTEGER,
	pm1004vdcMonupLineRmonByteCntValuePortn
		Counter64,
	pm1004vdcMonupLineRmonByteCntErrorPortn
		EkiOnOff,
	pm1004vdcMonupLineRmonByteCntOverloadPortn
		EkiOnOff
	}


pm1004vdcMonupLineRmonByteCntIndex OBJECT-TYPE
	SYNTAX  INTEGER(0..128)
	MAX-ACCESS  read-only
	STATUS current
	DESCRIPTION
        "
        Index definition for the pm1004vdcMonupLineRmonByteCnt 
        table
        "
	::= { pm1004vdcMonupLineRmonByteCntEntry 1 }


pm1004vdcMonupLineRmonByteCntValuePortn OBJECT-TYPE
	SYNTAX  Counter64
	MAX-ACCESS read-only
	STATUS current
	DESCRIPTION
        "
        Line Input Bytes :This counter 
        is increased each time a data byte 
        is received on the Line port  <Help> 
         This counter gives the number
         of bytes received on the Line
         port
        "
	::= { pm1004vdcMonupLineRmonByteCntEntry 2 }


pm1004vdcMonupLineRmonByteCntErrorPortn OBJECT-TYPE
	SYNTAX  EkiOnOff
	MAX-ACCESS read-only
	STATUS current
	DESCRIPTION
        "
        Bytes Counter Error :This OID
         when set indicates the Bytes counter 
        value is invalid on line port
        "
	::= { pm1004vdcMonupLineRmonByteCntEntry 3 }


pm1004vdcMonupLineRmonByteCntOverloadPortn OBJECT-TYPE
	SYNTAX  EkiOnOff
	MAX-ACCESS read-only
	STATUS current
	DESCRIPTION
        "
        Bytes Counter Overload :This OID 
        when set indicates a Bytes counter 
        overload on line port
        "
	::= { pm1004vdcMonupLineRmonByteCntEntry 4 }


--- *********************************************************
---     TABLE for the pm1004vdcMonupLineRmonCrcErrorCnt articles
--- *********************************************************

pm1004vdcMonupLineRmonCrcErrorCntTable OBJECT-TYPE
	SYNTAX  SEQUENCE OF Pm1004vdcMonupLineRmonCrcErrorCntEntry
	MAX-ACCESS not-accessible
	STATUS current
	DESCRIPTION
        "
        List of pm1004vdcMonupLineRmonCrcErrorCnt 
        Article
        "
	::= { pm1004vdcMonClientRmonCounter 209 }


pm1004vdcMonupLineRmonCrcErrorCntEntry OBJECT-TYPE
	SYNTAX Pm1004vdcMonupLineRmonCrcErrorCntEntry
	MAX-ACCESS not-accessible
	STATUS current
	DESCRIPTION
        "
        Row definition for the pm1004vdcMonupLineRmonCrcErrorCnt 
        table
        "
	INDEX   { pm1004vdcMonupLineRmonCrcErrorCntIndex }
	::= { pm1004vdcMonupLineRmonCrcErrorCntTable 1 }


Pm1004vdcMonupLineRmonCrcErrorCntEntry ::=
	SEQUENCE {
	pm1004vdcMonupLineRmonCrcErrorCntIndex
		INTEGER,
	pm1004vdcMonupLineRmonCrcErrorCntValuePortn
		Counter64,
	pm1004vdcMonupLineRmonCrcErrorCntErrorPortn
		EkiOnOff,
	pm1004vdcMonupLineRmonCrcErrorCntOverloadPortn
		EkiOnOff
	}


pm1004vdcMonupLineRmonCrcErrorCntIndex OBJECT-TYPE
	SYNTAX  INTEGER(0..128)
	MAX-ACCESS  read-only
	STATUS current
	DESCRIPTION
        "
        Index definition for the pm1004vdcMonupLineRmonCrcErrorCnt 
        table
        "
	::= { pm1004vdcMonupLineRmonCrcErrorCntEntry 1 }


pm1004vdcMonupLineRmonCrcErrorCntValuePortn OBJECT-TYPE
	SYNTAX  Counter64
	MAX-ACCESS read-only
	STATUS current
	DESCRIPTION
        "
        Line Input CRC Errors :This counter 
        is increased each time a CRC error 
        is detected on the Line port  <Help> 
         This counter gives the number
         of CRC Errors received on the
         Line port
        "
	::= { pm1004vdcMonupLineRmonCrcErrorCntEntry 2 }


pm1004vdcMonupLineRmonCrcErrorCntErrorPortn OBJECT-TYPE
	SYNTAX  EkiOnOff
	MAX-ACCESS read-only
	STATUS current
	DESCRIPTION
        "
        CRC Errors Counter Error :This 
        OID when set indicates the CRC
         Errors counter value is invalid 
        on line port
        "
	::= { pm1004vdcMonupLineRmonCrcErrorCntEntry 3 }


pm1004vdcMonupLineRmonCrcErrorCntOverloadPortn OBJECT-TYPE
	SYNTAX  EkiOnOff
	MAX-ACCESS read-only
	STATUS current
	DESCRIPTION
        "
        CRC Errors Counter Overload :This 
        OID when set indicates a CRC Errors 
        counter overload on line port
        "
	::= { pm1004vdcMonupLineRmonCrcErrorCntEntry 4 }


--- *********************************************************
---     TABLE for the pm1004vdcMonupLineRmonPacketsCnt articles
--- *********************************************************

pm1004vdcMonupLineRmonPacketsCntTable OBJECT-TYPE
	SYNTAX  SEQUENCE OF Pm1004vdcMonupLineRmonPacketsCntEntry
	MAX-ACCESS not-accessible
	STATUS current
	DESCRIPTION
        "
        List of pm1004vdcMonupLineRmonPacketsCnt 
        Article
        "
	::= { pm1004vdcMonClientRmonCounter 210 }


pm1004vdcMonupLineRmonPacketsCntEntry OBJECT-TYPE
	SYNTAX Pm1004vdcMonupLineRmonPacketsCntEntry
	MAX-ACCESS not-accessible
	STATUS current
	DESCRIPTION
        "
        Row definition for the pm1004vdcMonupLineRmonPacketsCnt 
        table
        "
	INDEX   { pm1004vdcMonupLineRmonPacketsCntIndex }
	::= { pm1004vdcMonupLineRmonPacketsCntTable 1 }


Pm1004vdcMonupLineRmonPacketsCntEntry ::=
	SEQUENCE {
	pm1004vdcMonupLineRmonPacketsCntIndex
		INTEGER,
	pm1004vdcMonupLineRmonPacketsCntValuePortn
		Counter64,
	pm1004vdcMonupLineRmonPacketsCntErrorPortn
		EkiOnOff,
	pm1004vdcMonupLineRmonPacketsCntOverloadPortn
		EkiOnOff
	}


pm1004vdcMonupLineRmonPacketsCntIndex OBJECT-TYPE
	SYNTAX  INTEGER(0..128)
	MAX-ACCESS  read-only
	STATUS current
	DESCRIPTION
        "
        Index definition for the pm1004vdcMonupLineRmonPacketsCnt 
        table
        "
	::= { pm1004vdcMonupLineRmonPacketsCntEntry 1 }


pm1004vdcMonupLineRmonPacketsCntValuePortn OBJECT-TYPE
	SYNTAX  Counter64
	MAX-ACCESS read-only
	STATUS current
	DESCRIPTION
        "
        Line Input Packets :This counter 
        is increased each time a packet 
        is received on the Line port  <Help> 
         This counter gives the number
         of packets received on the Line 
        port
        "
	::= { pm1004vdcMonupLineRmonPacketsCntEntry 2 }


pm1004vdcMonupLineRmonPacketsCntErrorPortn OBJECT-TYPE
	SYNTAX  EkiOnOff
	MAX-ACCESS read-only
	STATUS current
	DESCRIPTION
        "
        Packets Counter Error :This OID 
        when set indicates the Packets
         counter value is invalid on client 
        port
        "
	::= { pm1004vdcMonupLineRmonPacketsCntEntry 3 }


pm1004vdcMonupLineRmonPacketsCntOverloadPortn OBJECT-TYPE
	SYNTAX  EkiOnOff
	MAX-ACCESS read-only
	STATUS current
	DESCRIPTION
        "
        Packets Counter Overload :This 
        OID when set indicates a Packets 
        counter overload on line port
        "
	::= { pm1004vdcMonupLineRmonPacketsCntEntry 4 }


pm1004vdcMonCountersReset  OBJECT-TYPE
	SYNTAX EkiOnOff
	MAX-ACCESS read-write
	STATUS current
	DESCRIPTION
	"RMON Counters Reset:This OID resets and restarts all the RMON counters"
	::= { pm1004vdcMonRmon   359 }

pm1004vdcMonCountersStop  OBJECT-TYPE
	SYNTAX EkiOnOff
	MAX-ACCESS read-write
	STATUS current
	DESCRIPTION
	"RMON Counters stop:This OID stops all the RMON counters"
	::= { pm1004vdcMonRmon  360 }






--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm1004vdcMesrsynth0 OBJECT-TYPE
	  SYNTAX EkiMeasureType
	  MAX-ACCESS read-only
	  STATUS deprecated
	  DESCRIPTION
        "
        Not Used :This OID gives the unit 
        used on AUX1 measurement of XFP#1 
         (Unit = )
        "
	  ::= { pm1004vdcMesrOther 0 }



pm1004vdcMesrsynth1 OBJECT-TYPE
	  SYNTAX EkiMeasureType
	  MAX-ACCESS read-only
	  STATUS deprecated
	  DESCRIPTION
        "
        Not Used :This OID gives the unit 
        used on AUX2 measurement of XFP#1 
         (Unit = )
        "
	  ::= { pm1004vdcMesrOther 1 }



--- *********************************************************
---     TABLE for the pm1004vdcMesrtempMeas articles
--- *********************************************************

pm1004vdcMesrtempMeasTable OBJECT-TYPE
	SYNTAX  SEQUENCE OF Pm1004vdcMesrtempMeasEntry
	MAX-ACCESS not-accessible
	STATUS current
	DESCRIPTION
        "
        List of pm1004vdcMesrtempMeas
         Article
        "
	::= { pm1004vdcMesrClient 16 }


pm1004vdcMesrtempMeasEntry OBJECT-TYPE
	SYNTAX Pm1004vdcMesrtempMeasEntry
	MAX-ACCESS not-accessible
	STATUS current
	DESCRIPTION
        "
        Row definition for the pm1004vdcMesrtempMeas 
        table
        "
	INDEX   { pm1004vdcMesrtempMeasIndex }
	::= { pm1004vdcMesrtempMeasTable 1 }


Pm1004vdcMesrtempMeasEntry ::=
	SEQUENCE {
	pm1004vdcMesrtempMeasIndex
		INTEGER,
	pm1004vdcMesrtempMeasPortn
		INTEGER 
	}


pm1004vdcMesrtempMeasIndex OBJECT-TYPE
	SYNTAX  INTEGER(0..128)
	MAX-ACCESS  read-only
	STATUS current
	DESCRIPTION
        "
        Index definition for the pm1004vdcMesrtempMeas 
        table
        "
	::= { pm1004vdcMesrtempMeasEntry 1 }


pm1004vdcMesrtempMeasPortn OBJECT-TYPE
	SYNTAX  INTEGER (0..65535)
	MAX-ACCESS read-only
	STATUS current
	DESCRIPTION
        "
        Client SFP Temperature :This OID 
        gives the temperature value of
         the SFP plugged in port, read
         from the DDM (Digital Diagnostic 
        Monitoring) (Temperature = AV/256) 
        (Unit = C)  <Help>  This measure 
        gives the temperature of the client 
        transceiver
        "
	::= { pm1004vdcMesrtempMeasEntry 2 }


--- *********************************************************
---     TABLE for the pm1004vdcMesrvoltMeas articles
--- *********************************************************

pm1004vdcMesrvoltMeasTable OBJECT-TYPE
	SYNTAX  SEQUENCE OF Pm1004vdcMesrvoltMeasEntry
	MAX-ACCESS not-accessible
	STATUS current
	DESCRIPTION
        "
        List of pm1004vdcMesrvoltMeas
         Article
        "
	::= { pm1004vdcMesrClient 24 }


pm1004vdcMesrvoltMeasEntry OBJECT-TYPE
	SYNTAX Pm1004vdcMesrvoltMeasEntry
	MAX-ACCESS not-accessible
	STATUS current
	DESCRIPTION
        "
        Row definition for the pm1004vdcMesrvoltMeas 
        table
        "
	INDEX   { pm1004vdcMesrvoltMeasIndex }
	::= { pm1004vdcMesrvoltMeasTable 1 }


Pm1004vdcMesrvoltMeasEntry ::=
	SEQUENCE {
	pm1004vdcMesrvoltMeasIndex
		INTEGER,
	pm1004vdcMesrvoltMeasPortn
		INTEGER 
	}


pm1004vdcMesrvoltMeasIndex OBJECT-TYPE
	SYNTAX  INTEGER(0..128)
	MAX-ACCESS  read-only
	STATUS current
	DESCRIPTION
        "
        Index definition for the pm1004vdcMesrvoltMeas 
        table
        "
	::= { pm1004vdcMesrvoltMeasEntry 1 }


pm1004vdcMesrvoltMeasPortn OBJECT-TYPE
	SYNTAX  INTEGER (0..65535)
	MAX-ACCESS read-only
	STATUS current
	DESCRIPTION
        "
        Client SFP Power Supply :This
         OID gives the 3V3 voltage value 
        of the SFP plugged into port, read 
        from the DDM (Digital Diagnostic 
        Monitoring) (Voltage = AV/10000) 
        (Unit = V)  <Help>  This measure 
        gives the 3V3 voltage of the client 
        transceiver
        "
	::= { pm1004vdcMesrvoltMeasEntry 2 }


--- *********************************************************
---     TABLE for the pm1004vdcMesrbiasMeas articles
--- *********************************************************

pm1004vdcMesrbiasMeasTable OBJECT-TYPE
	SYNTAX  SEQUENCE OF Pm1004vdcMesrbiasMeasEntry
	MAX-ACCESS not-accessible
	STATUS current
	DESCRIPTION
        "
        List of pm1004vdcMesrbiasMeas
         Article
        "
	::= { pm1004vdcMesrClient 32 }


pm1004vdcMesrbiasMeasEntry OBJECT-TYPE
	SYNTAX Pm1004vdcMesrbiasMeasEntry
	MAX-ACCESS not-accessible
	STATUS current
	DESCRIPTION
        "
        Row definition for the pm1004vdcMesrbiasMeas 
        table
        "
	INDEX   { pm1004vdcMesrbiasMeasIndex }
	::= { pm1004vdcMesrbiasMeasTable 1 }


Pm1004vdcMesrbiasMeasEntry ::=
	SEQUENCE {
	pm1004vdcMesrbiasMeasIndex
		INTEGER,
	pm1004vdcMesrbiasMeasPortn
		INTEGER 
	}


pm1004vdcMesrbiasMeasIndex OBJECT-TYPE
	SYNTAX  INTEGER(0..128)
	MAX-ACCESS  read-only
	STATUS current
	DESCRIPTION
        "
        Index definition for the pm1004vdcMesrbiasMeas 
        table
        "
	::= { pm1004vdcMesrbiasMeasEntry 1 }


pm1004vdcMesrbiasMeasPortn OBJECT-TYPE
	SYNTAX  INTEGER (0..65535)
	MAX-ACCESS read-only
	STATUS current
	DESCRIPTION
        "
        Client SFP Laser Bias :This OID 
        gives the bias value of the SFP 
        plugged into port, read from the 
        DDM (Digital Diagnostic Monitoring) 
        (Bias = AV/500)  (Unit = mA)  <Help> 
         This measure gives the bias of 
        the client transceiver
        "
	::= { pm1004vdcMesrbiasMeasEntry 2 }


--- *********************************************************
---     TABLE for the pm1004vdcMesrtxpwrMeas articles
--- *********************************************************

pm1004vdcMesrtxpwrMeasTable OBJECT-TYPE
	SYNTAX  SEQUENCE OF Pm1004vdcMesrtxpwrMeasEntry
	MAX-ACCESS not-accessible
	STATUS current
	DESCRIPTION
        "
        List of pm1004vdcMesrtxpwrMeas 
        Article
        "
	::= { pm1004vdcMesrClient 40 }


pm1004vdcMesrtxpwrMeasEntry OBJECT-TYPE
	SYNTAX Pm1004vdcMesrtxpwrMeasEntry
	MAX-ACCESS not-accessible
	STATUS current
	DESCRIPTION
        "
        Row definition for the pm1004vdcMesrtxpwrMeas 
        table
        "
	INDEX   { pm1004vdcMesrtxpwrMeasIndex }
	::= { pm1004vdcMesrtxpwrMeasTable 1 }


Pm1004vdcMesrtxpwrMeasEntry ::=
	SEQUENCE {
	pm1004vdcMesrtxpwrMeasIndex
		INTEGER,
	pm1004vdcMesrtxpwrMeasPortn
		INTEGER 
	}


pm1004vdcMesrtxpwrMeasIndex OBJECT-TYPE
	SYNTAX  INTEGER(0..128)
	MAX-ACCESS  read-only
	STATUS current
	DESCRIPTION
        "
        Index definition for the pm1004vdcMesrtxpwrMeas 
        table
        "
	::= { pm1004vdcMesrtxpwrMeasEntry 1 }


pm1004vdcMesrtxpwrMeasPortn OBJECT-TYPE
	SYNTAX  INTEGER (0..65535)
	MAX-ACCESS read-only
	STATUS current
	DESCRIPTION
        "
        Client SFP Tx Power :This OID
         gives the transmit power value 
        of the SFP plugged into port, read 
        from the DDM (Digital Diagnostic 
        Monitoring) (Power = 10*log(AV)-40) 
        (Unit = dBm)  <Help>  This measure 
        gives the Tx optical power of the 
        client transceiver
        "
	::= { pm1004vdcMesrtxpwrMeasEntry 2 }


--- *********************************************************
---     TABLE for the pm1004vdcMesrrxpwrMeas articles
--- *********************************************************

pm1004vdcMesrrxpwrMeasTable OBJECT-TYPE
	SYNTAX  SEQUENCE OF Pm1004vdcMesrrxpwrMeasEntry
	MAX-ACCESS not-accessible
	STATUS current
	DESCRIPTION
        "
        List of pm1004vdcMesrrxpwrMeas 
        Article
        "
	::= { pm1004vdcMesrClient 48 }


pm1004vdcMesrrxpwrMeasEntry OBJECT-TYPE
	SYNTAX Pm1004vdcMesrrxpwrMeasEntry
	MAX-ACCESS not-accessible
	STATUS current
	DESCRIPTION
        "
        Row definition for the pm1004vdcMesrrxpwrMeas 
        table
        "
	INDEX   { pm1004vdcMesrrxpwrMeasIndex }
	::= { pm1004vdcMesrrxpwrMeasTable 1 }


Pm1004vdcMesrrxpwrMeasEntry ::=
	SEQUENCE {
	pm1004vdcMesrrxpwrMeasIndex
		INTEGER,
	pm1004vdcMesrrxpwrMeasPortn
		INTEGER 
	}


pm1004vdcMesrrxpwrMeasIndex OBJECT-TYPE
	SYNTAX  INTEGER(0..128)
	MAX-ACCESS  read-only
	STATUS current
	DESCRIPTION
        "
        Index definition for the pm1004vdcMesrrxpwrMeas 
        table
        "
	::= { pm1004vdcMesrrxpwrMeasEntry 1 }


pm1004vdcMesrrxpwrMeasPortn OBJECT-TYPE
	SYNTAX  INTEGER (0..65535)
	MAX-ACCESS read-only
	STATUS current
	DESCRIPTION
        "
        Client SFP Rx Power :This OID
         gives the receive power value
         of the SFP plugged into port,
         read in the DDM (Digital Diagnostic 
        Monitoring) (Power = 10*log(AV)-40) 
        (Unit = dBm)  <Help>  This measure 
        gives the Rx optical power of the 
        client transceiver
        "
	::= { pm1004vdcMesrrxpwrMeasEntry 2 }


--- *********************************************************
---     TABLE for the pm1004vdcMesrxfp1LxModTempMeas articles
--- *********************************************************

pm1004vdcMesrxfp1LxModTempMeasTable OBJECT-TYPE
	SYNTAX  SEQUENCE OF Pm1004vdcMesrxfp1LxModTempMeasEntry
	MAX-ACCESS not-accessible
	STATUS current
	DESCRIPTION
        "
        List of pm1004vdcMesrxfp1LxModTempMeas 
        Article
        "
	::= { pm1004vdcMesrLine 208 }


pm1004vdcMesrxfp1LxModTempMeasEntry OBJECT-TYPE
	SYNTAX Pm1004vdcMesrxfp1LxModTempMeasEntry
	MAX-ACCESS not-accessible
	STATUS current
	DESCRIPTION
        "
        Row definition for the pm1004vdcMesrxfp1LxModTempMeas 
        table
        "
	INDEX   { pm1004vdcMesrxfp1LxModTempMeasIndex }
	::= { pm1004vdcMesrxfp1LxModTempMeasTable 1 }


Pm1004vdcMesrxfp1LxModTempMeasEntry ::=
	SEQUENCE {
	pm1004vdcMesrxfp1LxModTempMeasIndex
		INTEGER,
	pm1004vdcMesrxfp1LxModTempMeasPortn
		INTEGER 
	}


pm1004vdcMesrxfp1LxModTempMeasIndex OBJECT-TYPE
	SYNTAX  INTEGER(0..128)
	MAX-ACCESS  read-only
	STATUS current
	DESCRIPTION
        "
        Index definition for the pm1004vdcMesrxfp1LxModTempMeas 
        table
        "
	::= { pm1004vdcMesrxfp1LxModTempMeasEntry 1 }


pm1004vdcMesrxfp1LxModTempMeasPortn OBJECT-TYPE
	SYNTAX  INTEGER (0..65535)
	MAX-ACCESS read-only
	STATUS current
	DESCRIPTION
        "
        Line Optical Module Temperature 
        :This OID gives the temperature 
        of the XFP or OTX plugged in line#n, 
        read from the DDM (Digital Diagnostic 
        Monitoring) (Temperature = AV/256) 
        (Unit = C)  <Help>  This measure 
        gives the temperature of the line 
        transceiver
        "
	::= { pm1004vdcMesrxfp1LxModTempMeasEntry 2 }


--- *********************************************************
---     TABLE for the pm1004vdcMesrxfp1Reserved articles
--- *********************************************************

pm1004vdcMesrxfp1ReservedTable OBJECT-TYPE
	SYNTAX  SEQUENCE OF Pm1004vdcMesrxfp1ReservedEntry
	MAX-ACCESS not-accessible
	STATUS deprecated
	DESCRIPTION
        "
        List of pm1004vdcMesrxfp1Reserved 
        Article
        "
	::= { pm1004vdcMesrLine 209 }


pm1004vdcMesrxfp1ReservedEntry OBJECT-TYPE
	SYNTAX Pm1004vdcMesrxfp1ReservedEntry
	MAX-ACCESS not-accessible
	STATUS deprecated
	DESCRIPTION
        "
        Row definition for the pm1004vdcMesrxfp1Reserved 
        table
        "
	INDEX   { pm1004vdcMesrxfp1ReservedIndex }
	::= { pm1004vdcMesrxfp1ReservedTable 1 }


Pm1004vdcMesrxfp1ReservedEntry ::=
	SEQUENCE {
	pm1004vdcMesrxfp1ReservedIndex
		INTEGER,
	pm1004vdcMesrxfp1ReservedPortn
		INTEGER 
	}


pm1004vdcMesrxfp1ReservedIndex OBJECT-TYPE
	SYNTAX  INTEGER(0..128)
	MAX-ACCESS  read-only
	STATUS deprecated
	DESCRIPTION
        "
        Index definition for the pm1004vdcMesrxfp1Reserved 
        table
        "
	::= { pm1004vdcMesrxfp1ReservedEntry 1 }


pm1004vdcMesrxfp1ReservedPortn OBJECT-TYPE
	SYNTAX  INTEGER (0..65535)
	MAX-ACCESS read-only
	STATUS deprecated
	DESCRIPTION
        "
        Not Used :Reserved
        "
	::= { pm1004vdcMesrxfp1ReservedEntry 2 }


--- *********************************************************
---     TABLE for the pm1004vdcMesrxfp1LoBiasCurrentMeas articles
--- *********************************************************

pm1004vdcMesrxfp1LoBiasCurrentMeasTable OBJECT-TYPE
	SYNTAX  SEQUENCE OF Pm1004vdcMesrxfp1LoBiasCurrentMeasEntry
	MAX-ACCESS not-accessible
	STATUS current
	DESCRIPTION
        "
        List of pm1004vdcMesrxfp1LoBiasCurrentMeas 
        Article
        "
	::= { pm1004vdcMesrLine 210 }


pm1004vdcMesrxfp1LoBiasCurrentMeasEntry OBJECT-TYPE
	SYNTAX Pm1004vdcMesrxfp1LoBiasCurrentMeasEntry
	MAX-ACCESS not-accessible
	STATUS current
	DESCRIPTION
        "
        Row definition for the pm1004vdcMesrxfp1LoBiasCurrentMeas 
        table
        "
	INDEX   { pm1004vdcMesrxfp1LoBiasCurrentMeasIndex }
	::= { pm1004vdcMesrxfp1LoBiasCurrentMeasTable 1 }


Pm1004vdcMesrxfp1LoBiasCurrentMeasEntry ::=
	SEQUENCE {
	pm1004vdcMesrxfp1LoBiasCurrentMeasIndex
		INTEGER,
	pm1004vdcMesrxfp1LoBiasCurrentMeasPortn
		INTEGER 
	}


pm1004vdcMesrxfp1LoBiasCurrentMeasIndex OBJECT-TYPE
	SYNTAX  INTEGER(0..128)
	MAX-ACCESS  read-only
	STATUS current
	DESCRIPTION
        "
        Index definition for the pm1004vdcMesrxfp1LoBiasCurrentMeas 
        table
        "
	::= { pm1004vdcMesrxfp1LoBiasCurrentMeasEntry 1 }


pm1004vdcMesrxfp1LoBiasCurrentMeasPortn OBJECT-TYPE
	SYNTAX  INTEGER (0..65535)
	MAX-ACCESS read-only
	STATUS current
	DESCRIPTION
        "
        Line Optical Module Laser Bias 
        :This OID gives the bias value
         of the XFP or OTX plugged in line 
        #n, read from the DDM (Digital
         Diagnostic Monitoring) (Bias = 
        AV/500) (Unit = mA)  <Help>  This 
        measure gives the bias of the line 
        transceiver
        "
	::= { pm1004vdcMesrxfp1LoBiasCurrentMeasEntry 2 }


--- *********************************************************
---     TABLE for the pm1004vdcMesrxfp1LoTxPowerMeas articles
--- *********************************************************

pm1004vdcMesrxfp1LoTxPowerMeasTable OBJECT-TYPE
	SYNTAX  SEQUENCE OF Pm1004vdcMesrxfp1LoTxPowerMeasEntry
	MAX-ACCESS not-accessible
	STATUS current
	DESCRIPTION
        "
        List of pm1004vdcMesrxfp1LoTxPowerMeas 
        Article
        "
	::= { pm1004vdcMesrLine 211 }


pm1004vdcMesrxfp1LoTxPowerMeasEntry OBJECT-TYPE
	SYNTAX Pm1004vdcMesrxfp1LoTxPowerMeasEntry
	MAX-ACCESS not-accessible
	STATUS current
	DESCRIPTION
        "
        Row definition for the pm1004vdcMesrxfp1LoTxPowerMeas 
        table
        "
	INDEX   { pm1004vdcMesrxfp1LoTxPowerMeasIndex }
	::= { pm1004vdcMesrxfp1LoTxPowerMeasTable 1 }


Pm1004vdcMesrxfp1LoTxPowerMeasEntry ::=
	SEQUENCE {
	pm1004vdcMesrxfp1LoTxPowerMeasIndex
		INTEGER,
	pm1004vdcMesrxfp1LoTxPowerMeasPortn
		INTEGER 
	}


pm1004vdcMesrxfp1LoTxPowerMeasIndex OBJECT-TYPE
	SYNTAX  INTEGER(0..128)
	MAX-ACCESS  read-only
	STATUS current
	DESCRIPTION
        "
        Index definition for the pm1004vdcMesrxfp1LoTxPowerMeas 
        table
        "
	::= { pm1004vdcMesrxfp1LoTxPowerMeasEntry 1 }


pm1004vdcMesrxfp1LoTxPowerMeasPortn OBJECT-TYPE
	SYNTAX  INTEGER (0..65535)
	MAX-ACCESS read-only
	STATUS current
	DESCRIPTION
        "
        Line Optical Module Tx Power :This 
        OID gives the transmit power value 
        of the XFP or OTX plugged in line 
        #n, read from the DDM (Digital
           Diagnostic Monitoring) (Power 
        = 10*log(AV)-40) (Unit = dBm) 
         <Help>  This measure gives the 
        Tx optical power of the line transceiver
        "
	::= { pm1004vdcMesrxfp1LoTxPowerMeasEntry 2 }


--- *********************************************************
---     TABLE for the pm1004vdcMesrxfp1LiRxPowerMeas articles
--- *********************************************************

pm1004vdcMesrxfp1LiRxPowerMeasTable OBJECT-TYPE
	SYNTAX  SEQUENCE OF Pm1004vdcMesrxfp1LiRxPowerMeasEntry
	MAX-ACCESS not-accessible
	STATUS current
	DESCRIPTION
        "
        List of pm1004vdcMesrxfp1LiRxPowerMeas 
        Article
        "
	::= { pm1004vdcMesrLine 212 }


pm1004vdcMesrxfp1LiRxPowerMeasEntry OBJECT-TYPE
	SYNTAX Pm1004vdcMesrxfp1LiRxPowerMeasEntry
	MAX-ACCESS not-accessible
	STATUS current
	DESCRIPTION
        "
        Row definition for the pm1004vdcMesrxfp1LiRxPowerMeas 
        table
        "
	INDEX   { pm1004vdcMesrxfp1LiRxPowerMeasIndex }
	::= { pm1004vdcMesrxfp1LiRxPowerMeasTable 1 }


Pm1004vdcMesrxfp1LiRxPowerMeasEntry ::=
	SEQUENCE {
	pm1004vdcMesrxfp1LiRxPowerMeasIndex
		INTEGER,
	pm1004vdcMesrxfp1LiRxPowerMeasPortn
		INTEGER 
	}


pm1004vdcMesrxfp1LiRxPowerMeasIndex OBJECT-TYPE
	SYNTAX  INTEGER(0..128)
	MAX-ACCESS  read-only
	STATUS current
	DESCRIPTION
        "
        Index definition for the pm1004vdcMesrxfp1LiRxPowerMeas 
        table
        "
	::= { pm1004vdcMesrxfp1LiRxPowerMeasEntry 1 }


pm1004vdcMesrxfp1LiRxPowerMeasPortn OBJECT-TYPE
	SYNTAX  INTEGER (0..65535)
	MAX-ACCESS read-only
	STATUS current
	DESCRIPTION
        "
        Line Optical Module Rx Power :This 
        OID gives the receive power value 
        of the XFP or OTX plugged in line 
        #n, read from the DDM (Digital
         Diagnostic Monitoring) (Power
         = 10*log(AV)-40)  (Unit = dBm) 
         <Help>  This measure gives the 
        Rx optical power of the line transceiver
        "
	::= { pm1004vdcMesrxfp1LiRxPowerMeasEntry 2 }


--- *********************************************************
---     TABLE for the pm1004vdcMesrxfp1LxAux1Meas articles
--- *********************************************************

pm1004vdcMesrxfp1LxAux1MeasTable OBJECT-TYPE
	SYNTAX  SEQUENCE OF Pm1004vdcMesrxfp1LxAux1MeasEntry
	MAX-ACCESS not-accessible
	STATUS deprecated
	DESCRIPTION
        "
        List of pm1004vdcMesrxfp1LxAux1Meas 
        Article
        "
	::= { pm1004vdcMesrLine 213 }


pm1004vdcMesrxfp1LxAux1MeasEntry OBJECT-TYPE
	SYNTAX Pm1004vdcMesrxfp1LxAux1MeasEntry
	MAX-ACCESS not-accessible
	STATUS deprecated
	DESCRIPTION
        "
        Row definition for the pm1004vdcMesrxfp1LxAux1Meas 
        table
        "
	INDEX   { pm1004vdcMesrxfp1LxAux1MeasIndex }
	::= { pm1004vdcMesrxfp1LxAux1MeasTable 1 }


Pm1004vdcMesrxfp1LxAux1MeasEntry ::=
	SEQUENCE {
	pm1004vdcMesrxfp1LxAux1MeasIndex
		INTEGER,
	pm1004vdcMesrxfp1LxAux1MeasPortn
		INTEGER 
	}


pm1004vdcMesrxfp1LxAux1MeasIndex OBJECT-TYPE
	SYNTAX  INTEGER(0..128)
	MAX-ACCESS  read-only
	STATUS deprecated
	DESCRIPTION
        "
        Index definition for the pm1004vdcMesrxfp1LxAux1Meas 
        table
        "
	::= { pm1004vdcMesrxfp1LxAux1MeasEntry 1 }


pm1004vdcMesrxfp1LxAux1MeasPortn OBJECT-TYPE
	SYNTAX  INTEGER (0..65535)
	MAX-ACCESS read-only
	STATUS deprecated
	DESCRIPTION
        "
        Not Used :This OID gives the receive 
        power value read in the DDM (Digital 
        Diagnostic Monitoring) of the XFP 
        or OTX plugged in line #n (Unit 
        = ?)
        "
	::= { pm1004vdcMesrxfp1LxAux1MeasEntry 2 }


--- *********************************************************
---     TABLE for the pm1004vdcMesrxfp1LxAux2Meas articles
--- *********************************************************

pm1004vdcMesrxfp1LxAux2MeasTable OBJECT-TYPE
	SYNTAX  SEQUENCE OF Pm1004vdcMesrxfp1LxAux2MeasEntry
	MAX-ACCESS not-accessible
	STATUS deprecated
	DESCRIPTION
        "
        List of pm1004vdcMesrxfp1LxAux2Meas 
        Article
        "
	::= { pm1004vdcMesrLine 214 }


pm1004vdcMesrxfp1LxAux2MeasEntry OBJECT-TYPE
	SYNTAX Pm1004vdcMesrxfp1LxAux2MeasEntry
	MAX-ACCESS not-accessible
	STATUS deprecated
	DESCRIPTION
        "
        Row definition for the pm1004vdcMesrxfp1LxAux2Meas 
        table
        "
	INDEX   { pm1004vdcMesrxfp1LxAux2MeasIndex }
	::= { pm1004vdcMesrxfp1LxAux2MeasTable 1 }


Pm1004vdcMesrxfp1LxAux2MeasEntry ::=
	SEQUENCE {
	pm1004vdcMesrxfp1LxAux2MeasIndex
		INTEGER,
	pm1004vdcMesrxfp1LxAux2MeasPortn
		INTEGER 
	}


pm1004vdcMesrxfp1LxAux2MeasIndex OBJECT-TYPE
	SYNTAX  INTEGER(0..128)
	MAX-ACCESS  read-only
	STATUS deprecated
	DESCRIPTION
        "
        Index definition for the pm1004vdcMesrxfp1LxAux2Meas 
        table
        "
	::= { pm1004vdcMesrxfp1LxAux2MeasEntry 1 }


pm1004vdcMesrxfp1LxAux2MeasPortn OBJECT-TYPE
	SYNTAX  INTEGER (0..65535)
	MAX-ACCESS read-only
	STATUS deprecated
	DESCRIPTION
        "
        Not Used :This OID gives the receive 
        power value read in the DDM (Digital 
        Diagnostic Monitoring) of the XFP 
        or OTX plugged in line #n (Unit 
        = ?)
        "
	::= { pm1004vdcMesrxfp1LxAux2MeasEntry 2 }


--- *********************************************************
---     TABLE for the pm1004vdcMesrotx1Aging articles
--- *********************************************************

pm1004vdcMesrotx1AgingTable OBJECT-TYPE
	SYNTAX  SEQUENCE OF Pm1004vdcMesrotx1AgingEntry
	MAX-ACCESS not-accessible
	STATUS current
	DESCRIPTION
        "
        List of pm1004vdcMesrotx1Aging 
        Article
        "
	::= { pm1004vdcMesrLine 224 }


pm1004vdcMesrotx1AgingEntry OBJECT-TYPE
	SYNTAX Pm1004vdcMesrotx1AgingEntry
	MAX-ACCESS not-accessible
	STATUS current
	DESCRIPTION
        "
        Row definition for the pm1004vdcMesrotx1Aging 
        table
        "
	INDEX   { pm1004vdcMesrotx1AgingIndex }
	::= { pm1004vdcMesrotx1AgingTable 1 }


Pm1004vdcMesrotx1AgingEntry ::=
	SEQUENCE {
	pm1004vdcMesrotx1AgingIndex
		INTEGER,
	pm1004vdcMesrotx1AgingPortn
		INTEGER 
	}


pm1004vdcMesrotx1AgingIndex OBJECT-TYPE
	SYNTAX  INTEGER(0..128)
	MAX-ACCESS  read-only
	STATUS current
	DESCRIPTION
        "
        Index definition for the pm1004vdcMesrotx1Aging 
        table
        "
	::= { pm1004vdcMesrotx1AgingEntry 1 }


pm1004vdcMesrotx1AgingPortn OBJECT-TYPE
	SYNTAX  INTEGER (0..65535)
	MAX-ACCESS read-only
	STATUS current
	DESCRIPTION
        "
        Line OTX TLH Aging :This OID gives 
        the aging of the Line OTX TLH,
         read from the DDM (Digital Diagnostic 
        Monitoring)   (Aging = AV) (Unit 
        = %)  <Help>  This measure gives 
        the aging of the Line OTX TLH
        "
	::= { pm1004vdcMesrotx1AgingEntry 2 }


--- *********************************************************
---     TABLE for the pm1004vdcMesrotx1LaserTemperature articles
--- *********************************************************

pm1004vdcMesrotx1LaserTemperatureTable OBJECT-TYPE
	SYNTAX  SEQUENCE OF Pm1004vdcMesrotx1LaserTemperatureEntry
	MAX-ACCESS not-accessible
	STATUS deprecated
	DESCRIPTION
        "
        List of pm1004vdcMesrotx1LaserTemperature 
        Article
        "
	::= { pm1004vdcMesrLine 225 }


pm1004vdcMesrotx1LaserTemperatureEntry OBJECT-TYPE
	SYNTAX Pm1004vdcMesrotx1LaserTemperatureEntry
	MAX-ACCESS not-accessible
	STATUS deprecated
	DESCRIPTION
        "
        Row definition for the pm1004vdcMesrotx1LaserTemperature 
        table
        "
	INDEX   { pm1004vdcMesrotx1LaserTemperatureIndex }
	::= { pm1004vdcMesrotx1LaserTemperatureTable 1 }


Pm1004vdcMesrotx1LaserTemperatureEntry ::=
	SEQUENCE {
	pm1004vdcMesrotx1LaserTemperatureIndex
		INTEGER,
	pm1004vdcMesrotx1LaserTemperaturePortn
		INTEGER 
	}


pm1004vdcMesrotx1LaserTemperatureIndex OBJECT-TYPE
	SYNTAX  INTEGER(0..128)
	MAX-ACCESS  read-only
	STATUS deprecated
	DESCRIPTION
        "
        Index definition for the pm1004vdcMesrotx1LaserTemperature 
        table
        "
	::= { pm1004vdcMesrotx1LaserTemperatureEntry 1 }


pm1004vdcMesrotx1LaserTemperaturePortn OBJECT-TYPE
	SYNTAX  INTEGER (0..65535)
	MAX-ACCESS read-only
	STATUS deprecated
	DESCRIPTION
        "
        Line OTX TLH Laser Temperature 
        :This OID gives the laser temperature 
        of the Line OTX TLH, read from
         the DDM (Digital Diagnostic Monitoring) 
        (Temperature = AV/256) (Unit =
         C)  <Help>  This measure gives 
        the laser temperature of the Line 
        OTX TLH
        "
	::= { pm1004vdcMesrotx1LaserTemperatureEntry 2 }


--- *********************************************************
---     TABLE for the pm1004vdcMesrotx1FreqDeviation articles
--- *********************************************************

pm1004vdcMesrotx1FreqDeviationTable OBJECT-TYPE
	SYNTAX  SEQUENCE OF Pm1004vdcMesrotx1FreqDeviationEntry
	MAX-ACCESS not-accessible
	STATUS current
	DESCRIPTION
        "
        List of pm1004vdcMesrotx1FreqDeviation 
        Article
        "
	::= { pm1004vdcMesrLine 226 }


pm1004vdcMesrotx1FreqDeviationEntry OBJECT-TYPE
	SYNTAX Pm1004vdcMesrotx1FreqDeviationEntry
	MAX-ACCESS not-accessible
	STATUS current
	DESCRIPTION
        "
        Row definition for the pm1004vdcMesrotx1FreqDeviation 
        table
        "
	INDEX   { pm1004vdcMesrotx1FreqDeviationIndex }
	::= { pm1004vdcMesrotx1FreqDeviationTable 1 }


Pm1004vdcMesrotx1FreqDeviationEntry ::=
	SEQUENCE {
	pm1004vdcMesrotx1FreqDeviationIndex
		INTEGER,
	pm1004vdcMesrotx1FreqDeviationPortn
		INTEGER 
	}


pm1004vdcMesrotx1FreqDeviationIndex OBJECT-TYPE
	SYNTAX  INTEGER(0..128)
	MAX-ACCESS  read-only
	STATUS current
	DESCRIPTION
        "
        Index definition for the pm1004vdcMesrotx1FreqDeviation 
        table
        "
	::= { pm1004vdcMesrotx1FreqDeviationEntry 1 }


pm1004vdcMesrotx1FreqDeviationPortn OBJECT-TYPE
	SYNTAX  INTEGER (0..65535)
	MAX-ACCESS read-only
	STATUS current
	DESCRIPTION
        "
        Line OTX TLH Frequency Deviation 
        :This OID gives the frequency deviation 
        of the Line OTX TLH, read from
         the DDM (Digital Diagnostic Monitoring) 
         (Deviation = (AV-32768)*100) (Unit 
        = MHz)  <Help>  This measure gives 
        the frequency deviation of the
         Line OTX TLH
        "
	::= { pm1004vdcMesrotx1FreqDeviationEntry 2 }


--- *********************************************************
---     TABLE for the pm1004vdcMesrotx1LaserWvlength articles
--- *********************************************************

pm1004vdcMesrotx1LaserWvlengthTable OBJECT-TYPE
	SYNTAX  SEQUENCE OF Pm1004vdcMesrotx1LaserWvlengthEntry
	MAX-ACCESS not-accessible
	STATUS current
	DESCRIPTION
        "
        List of pm1004vdcMesrotx1LaserWvlength 
        Article
        "
	::= { pm1004vdcMesrLine 227 }


pm1004vdcMesrotx1LaserWvlengthEntry OBJECT-TYPE
	SYNTAX Pm1004vdcMesrotx1LaserWvlengthEntry
	MAX-ACCESS not-accessible
	STATUS current
	DESCRIPTION
        "
        Row definition for the pm1004vdcMesrotx1LaserWvlength 
        table
        "
	INDEX   { pm1004vdcMesrotx1LaserWvlengthIndex }
	::= { pm1004vdcMesrotx1LaserWvlengthTable 1 }


Pm1004vdcMesrotx1LaserWvlengthEntry ::=
	SEQUENCE {
	pm1004vdcMesrotx1LaserWvlengthIndex
		INTEGER,
	pm1004vdcMesrotx1LaserWvlengthPortn
		INTEGER 
	}


pm1004vdcMesrotx1LaserWvlengthIndex OBJECT-TYPE
	SYNTAX  INTEGER(0..128)
	MAX-ACCESS  read-only
	STATUS current
	DESCRIPTION
        "
        Index definition for the pm1004vdcMesrotx1LaserWvlength 
        table
        "
	::= { pm1004vdcMesrotx1LaserWvlengthEntry 1 }


pm1004vdcMesrotx1LaserWvlengthPortn OBJECT-TYPE
	SYNTAX  INTEGER (0..65535)
	MAX-ACCESS read-only
	STATUS current
	DESCRIPTION
        "
        Line Optical Module Wavelength 
        :This OID gives the laser wavelength 
        of the Line OTX TLH, read from
         the DDM (Digital Diagnostic Monitoring) 
        (Wavelength=299792458/((193,100+(AV-32768 
        )*12,5)*10 3)) (Unit = nm)  <Help> 
         This measure gives the laser wavelength 
        of the Line OTX TLH
        "
	::= { pm1004vdcMesrotx1LaserWvlengthEntry 2 }







--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm1004vdcDwlrestartProcess OBJECT IDENTIFIER ::= { pm1004vdcDwlOther 0 }




pm1004vdcDwlColdRestartProcessed OBJECT-TYPE
	  SYNTAX EkiOnOff
	  MAX-ACCESS read-only
	  STATUS current
	  DESCRIPTION
        "
        Cold Restart :This OID indicates 
        that the module last restart was 
        a Cold RESTART
        "
	  ::= { pm1004vdcDwlrestartProcess 2 }



pm1004vdcDwlWarmRestartProcessed OBJECT-TYPE
	  SYNTAX EkiOnOff
	  MAX-ACCESS read-only
	  STATUS current
	  DESCRIPTION
        "
        Warm Restart :This OID indicates 
        that the module last restart was 
        a Warm RESTART
        "
	  ::= { pm1004vdcDwlrestartProcess 1 }



--- *****************************************************
---     LEAF for the swBanksUsed article
--- *****************************************************
pm1004vdcDwlswBanksUsed OBJECT IDENTIFIER ::= { pm1004vdcDwlOther 1 }




pm1004vdcDwlSwBank2Notempty OBJECT-TYPE
	  SYNTAX EkiOnOff
	  MAX-ACCESS read-only
	  STATUS current
	  DESCRIPTION
        "
        SW bank 2 loaded :This OID indicates 
        a software is loaded in SW bank 
        2  <Help>  This status indicates 
        if the SW bank 2 contains SW package
        "
	  ::= { pm1004vdcDwlswBanksUsed 6 }



pm1004vdcDwlSwBank1Notempty OBJECT-TYPE
	  SYNTAX EkiOnOff
	  MAX-ACCESS read-only
	  STATUS current
	  DESCRIPTION
        "
        SW bank 1 loaded :This OID indicates 
        a software is loaded in SW bank 
        1  <Help>  This status indicates 
        if the SW bank 1 contains SW package
        "
	  ::= { pm1004vdcDwlswBanksUsed 5 }



pm1004vdcDwlSwBank2Used OBJECT-TYPE
	  SYNTAX EkiOnOff
	  MAX-ACCESS read-only
	  STATUS current
	  DESCRIPTION
        "
        SW bank 2 active :This OID indicates 
        the module is working on SW bank 
        2  <Help>  This status indicates 
        if the SW bank 2 is active or standby
        "
	  ::= { pm1004vdcDwlswBanksUsed 2 }



pm1004vdcDwlSwBank1Used OBJECT-TYPE
	  SYNTAX EkiOnOff
	  MAX-ACCESS read-only
	  STATUS current
	  DESCRIPTION
        "
        SW bank 1 active :This OID indicates 
        the module is working on SW bank 
        1  <Help>  This status indicates 
        if the SW bank 1 is active or standby
        "
	  ::= { pm1004vdcDwlswBanksUsed 1 }



--- *****************************************************
---     LEAF for the gwBanksUsed article
--- *****************************************************
pm1004vdcDwlgwBanksUsed OBJECT IDENTIFIER ::= { pm1004vdcDwlOther 2 }




pm1004vdcDwlGwBank4Notempty OBJECT-TYPE
	  SYNTAX EkiOnOff
	  MAX-ACCESS read-only
	  STATUS current
	  DESCRIPTION
        "
        GW bank 4 loaded :This OID indicates 
        a gateware is loaded in GW bank 
        4
        "
	  ::= { pm1004vdcDwlgwBanksUsed 8 }



pm1004vdcDwlGwBank3Notempty OBJECT-TYPE
	  SYNTAX EkiOnOff
	  MAX-ACCESS read-only
	  STATUS current
	  DESCRIPTION
        "
        GW bank 3 loaded :This OID indicates 
        a gateware is loaded in GW bank 
        3  <Help>  This status indicates 
        if the GW bank 3 contains GW package
        "
	  ::= { pm1004vdcDwlgwBanksUsed 7 }



pm1004vdcDwlGwBank2Notempty OBJECT-TYPE
	  SYNTAX EkiOnOff
	  MAX-ACCESS read-only
	  STATUS current
	  DESCRIPTION
        "
        GW bank 2 loaded :This OID indicates 
        a gateware is loaded in GW bank 
        2
        "
	  ::= { pm1004vdcDwlgwBanksUsed 6 }



pm1004vdcDwlGwBank1Notempty OBJECT-TYPE
	  SYNTAX EkiOnOff
	  MAX-ACCESS read-only
	  STATUS current
	  DESCRIPTION
        "
        GW bank 1 loaded  :This OID indicates 
        a gateware is loaded in GW bank 
        1  <Help>  This status indicates 
        if the GW bank 1 contains GW package
        "
	  ::= { pm1004vdcDwlgwBanksUsed 5 }



pm1004vdcDwlGwBank4Used OBJECT-TYPE
	  SYNTAX EkiOnOff
	  MAX-ACCESS read-only
	  STATUS current
	  DESCRIPTION
        "
        GW bank 4 active  :This OID indicates 
        the module is working on GW bank 
        4
        "
	  ::= { pm1004vdcDwlgwBanksUsed 4 }



pm1004vdcDwlGwBank3Used OBJECT-TYPE
	  SYNTAX EkiOnOff
	  MAX-ACCESS read-only
	  STATUS current
	  DESCRIPTION
        "
        GW bank 3 active :This OID indicates 
        the module is working on GW bank 
        3  <Help>  This status indicates 
        if the GW bank 3 is active or standby
        "
	  ::= { pm1004vdcDwlgwBanksUsed 3 }



pm1004vdcDwlGwBank2Used OBJECT-TYPE
	  SYNTAX EkiOnOff
	  MAX-ACCESS read-only
	  STATUS current
	  DESCRIPTION
        "
        GW bank 2 active :This OID indicates 
        the module is working on GW bank 
        2
        "
	  ::= { pm1004vdcDwlgwBanksUsed 2 }



pm1004vdcDwlGwBank1Used OBJECT-TYPE
	  SYNTAX EkiOnOff
	  MAX-ACCESS read-only
	  STATUS current
	  DESCRIPTION
        "
        GW bank 1 active  :This OID indicates 
        the module is working on GW bank 
        1  <Help>  This status indicates 
        if the GW bank 1 is active or standby
        "
	  ::= { pm1004vdcDwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm1004vdcCfgAccessCAisCsf OBJECT IDENTIFIER ::= { pm1004vdcConfig 1 }



--- *****************************************************
---     LEAF for the table 0012
--- *****************************************************

pm1004vdcCfgClientcaiscsfTable OBJECT-TYPE
	SYNTAX  SEQUENCE OF Pm1004vdcCfgClientcaiscsfEntry
	MAX-ACCESS not-accessible
	STATUS current
	DESCRIPTION
        "
        List of  Article
        "
	::= { pm1004vdcCfgAccessCAisCsf 1 }


pm1004vdcCfgClientcaiscsfEntry OBJECT-TYPE
	SYNTAX Pm1004vdcCfgClientcaiscsfEntry
	MAX-ACCESS not-accessible
	STATUS current
	DESCRIPTION
        "
        Row definition for the accessCAisCsf 
        table
        "
	INDEX   { pm1004vdcCfgClientcaiscsfIndex }
	::= { pm1004vdcCfgClientcaiscsfTable 1 }


Pm1004vdcCfgClientcaiscsfEntry ::=
	SEQUENCE {
	pm1004vdcCfgClientcaiscsfIndex
		INTEGER,
	pm1004vdcCfgCAisModePortn
		Unsigned32,
	pm1004vdcCfgUpAccessioAlmPortn
		Unsigned32,
	pm1004vdcCfgUpMapperDeAlmPortn
		Unsigned32,
	pm1004vdcCfgDownAccessioAlmPortn
		Unsigned32,
	pm1004vdcCfgDownMapperDeAlmPortn
		Unsigned32,
	pm1004vdcCfgDownDfrmAlmPortn
		Unsigned32,
	pm1004vdcCfgDownLineSyncAlarmsPortn
		Unsigned32
	}


pm1004vdcCfgClientcaiscsfIndex OBJECT-TYPE
	SYNTAX  INTEGER(0..128)
	MAX-ACCESS  read-only
	STATUS current
	DESCRIPTION
        "
        Index definition for the clientcaiscsf 
        table
        "
	::= { pm1004vdcCfgClientcaiscsfEntry 1 }


pm1004vdcCfgCAisModePortn OBJECT-TYPE
	SYNTAX  Unsigned32 (0..65536)
	MAX-ACCESS read-write
	STATUS current
	DESCRIPTION
        "
        CAIS mode  on Client Port :This 
        register enables/disables port
          laser shutdown on CAIS insertion 
        condition
        "
	::= { pm1004vdcCfgClientcaiscsfEntry 3 }


pm1004vdcCfgUpAccessioAlmPortn OBJECT-TYPE
	SYNTAX  Unsigned32 (0..65536)
	MAX-ACCESS read-write
	STATUS current
	DESCRIPTION
        "
        CSF contributors on Client Port 
        :This register configures the contributors 
        to upstream CSF insertion on the 
        port.
        "
	::= { pm1004vdcCfgClientcaiscsfEntry 9 }


pm1004vdcCfgUpMapperDeAlmPortn OBJECT-TYPE
	SYNTAX  Unsigned32 (0..65536)
	MAX-ACCESS read-write
	STATUS current
	DESCRIPTION
        "
        CSF contributors on Client Port 
        :This register configures the contributors 
        to upstream CSF insertion on the 
        port.
        "
	::= { pm1004vdcCfgClientcaiscsfEntry 10 }


pm1004vdcCfgDownAccessioAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pm1004vdcCfgClientcaiscsfEntry 17 }


pm1004vdcCfgDownMapperDeAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pm1004vdcCfgClientcaiscsfEntry 18 }


pm1004vdcCfgDownDfrmAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pm1004vdcCfgClientcaiscsfEntry 19 }


pm1004vdcCfgDownLineSyncAlarmsPortn OBJECT-TYPE
	SYNTAX  Unsigned32 (0..65536)
	MAX-ACCESS read-write
	STATUS deprecated
	DESCRIPTION
        "
        CAIS contributors on Client Port 
        :This register configures the contributors 
        to downstream CAIS insertion on 
         port.
        "
	::= { pm1004vdcCfgClientcaiscsfEntry 20 }


--- *****************************************************
---     LEAF for the table Group startup
--- *****************************************************

pm1004vdcCfgStartup OBJECT IDENTIFIER ::= { pm1004vdcConfig 2 }



--- *****************************************************
---     LEAF for the table 2111
--- *****************************************************

pm1004vdcCfgClientStartupTable OBJECT-TYPE
	SYNTAX  SEQUENCE OF Pm1004vdcCfgClientStartupEntry
	MAX-ACCESS not-accessible
	STATUS current
	DESCRIPTION
        "
        List of  Article
        "
	::= { pm1004vdcCfgStartup 1 }


pm1004vdcCfgClientStartupEntry OBJECT-TYPE
	SYNTAX Pm1004vdcCfgClientStartupEntry
	MAX-ACCESS not-accessible
	STATUS current
	DESCRIPTION
        "
        Row definition for the startup 
        table
        "
	INDEX   { pm1004vdcCfgClientStartupIndex }
	::= { pm1004vdcCfgClientStartupTable 1 }


Pm1004vdcCfgClientStartupEntry ::=
	SEQUENCE {
	pm1004vdcCfgClientStartupIndex
		INTEGER,
	pm1004vdcCfgSystConfPortPortn
		Unsigned32,
	pm1004vdcCfgNetConfPortPortn
		Unsigned32,
	pm1004vdcCfgAdddropConfPortPortn
		Unsigned32
	}


pm1004vdcCfgClientStartupIndex OBJECT-TYPE
	SYNTAX  INTEGER(0..128)
	MAX-ACCESS  read-only
	STATUS current
	DESCRIPTION
        "
        Index definition for the clientStartup 
        table
        "
	::= { pm1004vdcCfgClientStartupEntry 1 }


pm1004vdcCfgSystConfPortPortn OBJECT-TYPE
	SYNTAX  Unsigned32 (0..65536)
	MAX-ACCESS read-write
	STATUS current
	DESCRIPTION
        "
        Default Settings on Client Port 
        :This  register configures the
         default initialisation settings 
        on the port.
        "
	::= { pm1004vdcCfgClientStartupEntry 3 }


pm1004vdcCfgNetConfPortPortn OBJECT-TYPE
	SYNTAX  Unsigned32 (0..65536)
	MAX-ACCESS read-write
	STATUS current
	DESCRIPTION
        "
        Default Protocol on Client Port 
        :This register configures the default 
        initialisation protocol on the
         port.
        "
	::= { pm1004vdcCfgClientStartupEntry 4 }


pm1004vdcCfgAdddropConfPortPortn OBJECT-TYPE
	SYNTAX  Unsigned32 (0..65536)
	MAX-ACCESS read-write
	STATUS deprecated
	DESCRIPTION
        "
        Default Add&Drop mode on Client 
        Port :This register configures
         the default Add&Drop mode on the 
        port.
        "
	::= { pm1004vdcCfgClientStartupEntry 5 }


--- *****************************************************
---     LEAF for the table 2191
--- *****************************************************

pm1004vdctablelineStartup OBJECT IDENTIFIER ::= { pm1004vdcCfgStartup 2 }



pm1004vdcCfgsystConfLine1 OBJECT-TYPE
	  SYNTAX Unsigned32 (0..65536)
	  MAX-ACCESS read-write
	  STATUS current
	  DESCRIPTION
        "
        Default Settings on Line 1 :This 
        register configures the default 
        initialisation settings on Line 
        port 1.
        "
	  ::= { pm1004vdctablelineStartup 2 }



pm1004vdcCfglineOptions1 OBJECT-TYPE
	  SYNTAX Unsigned32 (0..65536)
	  MAX-ACCESS read-write
	  STATUS current
	  DESCRIPTION
        "
        Default Options on Active Line 
        Port :This register configures
         the default options on the active 
        line port
        "
	  ::= { pm1004vdctablelineStartup 5 }



pm1004vdcCfgsystConfLine2 OBJECT-TYPE
	  SYNTAX Unsigned32 (0..65536)
	  MAX-ACCESS read-write
	  STATUS current
	  DESCRIPTION
        "
        Default Settings on Line 2 :This 
        register configures the default 
        initialisation settings on Line 
        port 2.
        "
	  ::= { pm1004vdctablelineStartup 6 }



pm1004vdcCfglineSelection OBJECT-TYPE
	  SYNTAX Unsigned32 (0..65536)
	  MAX-ACCESS read-write
	  STATUS current
	  DESCRIPTION
        "
        Default Settings of active line 
        :This  register configures the
         start up active line.
        "
	  ::= { pm1004vdctablelineStartup 7 }



pm1004vdcCfglineOptions2 OBJECT-TYPE
	  SYNTAX Unsigned32 (0..65536)
	  MAX-ACCESS read-write
	  STATUS current
	  DESCRIPTION
        "
        Default Options on Active Line 
        Port :This register configures
         the default options on the active 
        line port
        "
	  ::= { pm1004vdctablelineStartup 9 }



--- *****************************************************
---     LEAF for the table 21AB
--- *****************************************************

pm1004vdcCfgXfpTable OBJECT-TYPE
	SYNTAX  SEQUENCE OF Pm1004vdcCfgXfpEntry
	MAX-ACCESS not-accessible
	STATUS current
	DESCRIPTION
        "
        List of  Article
        "
	::= { pm1004vdcCfgStartup 3 }


pm1004vdcCfgXfpEntry OBJECT-TYPE
	SYNTAX Pm1004vdcCfgXfpEntry
	MAX-ACCESS not-accessible
	STATUS current
	DESCRIPTION
        "
        Row definition for the startup 
        table
        "
	INDEX   { pm1004vdcCfgXfpIndex }
	::= { pm1004vdcCfgXfpTable 1 }


Pm1004vdcCfgXfpEntry ::=
	SEQUENCE {
	pm1004vdcCfgXfpIndex
		INTEGER,
	pm1004vdcCfgSystConfXfpPortn
		Unsigned32,
	pm1004vdcCfgDataRateConfXfpPortn
		Unsigned32
	}


pm1004vdcCfgXfpIndex OBJECT-TYPE
	SYNTAX  INTEGER(0..128)
	MAX-ACCESS  read-only
	STATUS current
	DESCRIPTION
        "
        Index definition for the xfp table
        "
	::= { pm1004vdcCfgXfpEntry 1 }


pm1004vdcCfgSystConfXfpPortn OBJECT-TYPE
	SYNTAX  Unsigned32 (0..65536)
	MAX-ACCESS read-write
	STATUS current
	DESCRIPTION
        "
        Default settings on XFP Port :This 
        register configures the default 
        initialisation settings on XFP
         port.
        "
	::= { pm1004vdcCfgXfpEntry 3 }


pm1004vdcCfgDataRateConfXfpPortn OBJECT-TYPE
	SYNTAX  Unsigned32 (0..65536)
	MAX-ACCESS read-write
	STATUS deprecated
	DESCRIPTION
        "
        :
        "
	::= { pm1004vdcCfgXfpEntry 4 }


--- *****************************************************
---     LEAF for the table Group labels
--- *****************************************************

pm1004vdcCfgLabels OBJECT IDENTIFIER ::= { pm1004vdcConfig 3 }



--- *****************************************************
---     LEAF for the table NO_VALUE
--- *****************************************************

pm1004vdcCfgLabelclientTable OBJECT-TYPE
	SYNTAX  SEQUENCE OF Pm1004vdcCfgLabelclientEntry
	MAX-ACCESS not-accessible
	STATUS current
	DESCRIPTION
        "
        List of  Article
        "
	::= { pm1004vdcCfgLabels 1 }


pm1004vdcCfgLabelclientEntry OBJECT-TYPE
	SYNTAX Pm1004vdcCfgLabelclientEntry
	MAX-ACCESS not-accessible
	STATUS current
	DESCRIPTION
        "
        Row definition for the labels
         table
        "
	INDEX   { pm1004vdcCfgLabelclientIndex }
	::= { pm1004vdcCfgLabelclientTable 1 }


Pm1004vdcCfgLabelclientEntry ::=
	SEQUENCE {
	pm1004vdcCfgLabelclientIndex
		INTEGER,
	pm1004vdcCfgLabelclientPortn
		DisplayString
	}


pm1004vdcCfgLabelclientIndex OBJECT-TYPE
	SYNTAX  INTEGER(0..128)
	MAX-ACCESS  read-only
	STATUS current
	DESCRIPTION
        "
        Index definition for the labelclient 
        table
        "
	::= { pm1004vdcCfgLabelclientEntry 1 }


pm1004vdcCfgLabelclientPortn OBJECT-TYPE
	SYNTAX  DisplayString( SIZE(1..16))
	MAX-ACCESS read-write
	STATUS current
	DESCRIPTION
        "
        Default settings on the label
         of the Ports :These registers
         configures the default initialisation 
        settings of the labels of the ports.
        "
	::= { pm1004vdcCfgLabelclientEntry 3 }


--- *****************************************************
---     LEAF for the table NO_VALUE
--- *****************************************************

pm1004vdcCfgLabellineTable OBJECT-TYPE
	SYNTAX  SEQUENCE OF Pm1004vdcCfgLabellineEntry
	MAX-ACCESS not-accessible
	STATUS current
	DESCRIPTION
        "
        List of  Article
        "
	::= { pm1004vdcCfgLabels 2 }


pm1004vdcCfgLabellineEntry OBJECT-TYPE
	SYNTAX Pm1004vdcCfgLabellineEntry
	MAX-ACCESS not-accessible
	STATUS current
	DESCRIPTION
        "
        Row definition for the labels
         table
        "
	INDEX   { pm1004vdcCfgLabellineIndex }
	::= { pm1004vdcCfgLabellineTable 1 }


Pm1004vdcCfgLabellineEntry ::=
	SEQUENCE {
	pm1004vdcCfgLabellineIndex
		INTEGER,
	pm1004vdcCfgLabellinePortn
		DisplayString
	}


pm1004vdcCfgLabellineIndex OBJECT-TYPE
	SYNTAX  INTEGER(0..128)
	MAX-ACCESS  read-only
	STATUS current
	DESCRIPTION
        "
        Index definition for the labelline 
        table
        "
	::= { pm1004vdcCfgLabellineEntry 1 }


pm1004vdcCfgLabellinePortn OBJECT-TYPE
	SYNTAX  DisplayString( SIZE(1..16))
	MAX-ACCESS read-write
	STATUS current
	DESCRIPTION
        "
        Default settings on the label
         of the lines :These registers
         configures the default initialisation 
        settings of the labels of the lines.
        "
	::= { pm1004vdcCfgLabellineEntry 3 }


--- *****************************************************
---     LEAF for the table Group startupthresholds
--- *****************************************************

pm1004vdcCfgStartupthresholds OBJECT IDENTIFIER ::= { pm1004vdcConfig 4 }



--- *****************************************************
---     LEAF for the table 5012
--- *****************************************************

pm1004vdcCfgClientStartupThreshTable OBJECT-TYPE
	SYNTAX  SEQUENCE OF Pm1004vdcCfgClientStartupThreshEntry
	MAX-ACCESS not-accessible
	STATUS current
	DESCRIPTION
        "
        List of  Article
        "
	::= { pm1004vdcCfgStartupthresholds 1 }


pm1004vdcCfgClientStartupThreshEntry OBJECT-TYPE
	SYNTAX Pm1004vdcCfgClientStartupThreshEntry
	MAX-ACCESS not-accessible
	STATUS current
	DESCRIPTION
        "
        Row definition for the startupthresholds 
        table
        "
	INDEX   { pm1004vdcCfgClientStartupThreshIndex }
	::= { pm1004vdcCfgClientStartupThreshTable 1 }


Pm1004vdcCfgClientStartupThreshEntry ::=
	SEQUENCE {
	pm1004vdcCfgClientStartupThreshIndex
		INTEGER,
	pm1004vdcCfgClientThreshtxpowhighPortn
		Unsigned32,
	pm1004vdcCfgClientThreshtxpowlowPortn
		Unsigned32,
	pm1004vdcCfgClientThreshrxpowhighPortn
		Unsigned32,
	pm1004vdcCfgClientThreshrxpowlowPortn
		Unsigned32
	}


pm1004vdcCfgClientStartupThreshIndex OBJECT-TYPE
	SYNTAX  INTEGER(0..128)
	MAX-ACCESS  read-only
	STATUS current
	DESCRIPTION
        "
        Index definition for the clientStartupThresh 
        table
        "
	::= { pm1004vdcCfgClientStartupThreshEntry 1 }


pm1004vdcCfgClientThreshtxpowhighPortn OBJECT-TYPE
	SYNTAX  Unsigned32 (0..65536)
	MAX-ACCESS read-write
	STATUS current
	DESCRIPTION
        "
        Default Setting on Tx Power high 
        threshold :This register configures 
        the default initialisation of the 
        high threshold of the Transmit
         power on the port.
        "
	::= { pm1004vdcCfgClientStartupThreshEntry 15 }


pm1004vdcCfgClientThreshtxpowlowPortn OBJECT-TYPE
	SYNTAX  Unsigned32 (0..65536)
	MAX-ACCESS read-write
	STATUS current
	DESCRIPTION
        "
        Default Setting on Tx Power low 
        threshold :This register configures 
        the default initialisation of the 
        low threshold of the Transmit power 
        on the port.
        "
	::= { pm1004vdcCfgClientStartupThreshEntry 16 }


pm1004vdcCfgClientThreshrxpowhighPortn OBJECT-TYPE
	SYNTAX  Unsigned32 (0..65536)
	MAX-ACCESS read-write
	STATUS current
	DESCRIPTION
        "
        Default Setting on Rx Power high 
        threshold :This register configures 
        the default initialisation of the 
        high threshold of the received
         power on the port.
        "
	::= { pm1004vdcCfgClientStartupThreshEntry 19 }


pm1004vdcCfgClientThreshrxpowlowPortn OBJECT-TYPE
	SYNTAX  Unsigned32 (0..65536)
	MAX-ACCESS read-write
	STATUS current
	DESCRIPTION
        "
        Default Setting on Rx Power low 
        threshold :This register configures 
        the default initialisation of the 
        low threshold of the received power 
        on the port.
        "
	::= { pm1004vdcCfgClientStartupThreshEntry 20 }


--- *****************************************************
---     LEAF for the table 50A1
--- *****************************************************

pm1004vdcCfgLineStartupThreshTable OBJECT-TYPE
	SYNTAX  SEQUENCE OF Pm1004vdcCfgLineStartupThreshEntry
	MAX-ACCESS not-accessible
	STATUS current
	DESCRIPTION
        "
        List of  Article
        "
	::= { pm1004vdcCfgStartupthresholds 2 }


pm1004vdcCfgLineStartupThreshEntry OBJECT-TYPE
	SYNTAX Pm1004vdcCfgLineStartupThreshEntry
	MAX-ACCESS not-accessible
	STATUS current
	DESCRIPTION
        "
        Row definition for the startupthresholds 
        table
        "
	INDEX   { pm1004vdcCfgLineStartupThreshIndex }
	::= { pm1004vdcCfgLineStartupThreshTable 1 }


Pm1004vdcCfgLineStartupThreshEntry ::=
	SEQUENCE {
	pm1004vdcCfgLineStartupThreshIndex
		INTEGER,
	pm1004vdcCfgLineThreshtxpowhighPortn
		Unsigned32,
	pm1004vdcCfgLineThreshtxpowlowPortn
		Unsigned32,
	pm1004vdcCfgLineThreshrxpowhighPortn
		Unsigned32,
	pm1004vdcCfgLineThreshrxpowlowPortn
		Unsigned32
	}


pm1004vdcCfgLineStartupThreshIndex OBJECT-TYPE
	SYNTAX  INTEGER(0..128)
	MAX-ACCESS  read-only
	STATUS current
	DESCRIPTION
        "
        Index definition for the lineStartupThresh 
        table
        "
	::= { pm1004vdcCfgLineStartupThreshEntry 1 }


pm1004vdcCfgLineThreshtxpowhighPortn OBJECT-TYPE
	SYNTAX  Unsigned32 (0..65536)
	MAX-ACCESS read-write
	STATUS current
	DESCRIPTION
        "
        Default Setting on Tx Power high 
        threshold :This register configures 
        the default initialisation of the 
        high threshold of the Transmit
         power on the line.
        "
	::= { pm1004vdcCfgLineStartupThreshEntry 15 }


pm1004vdcCfgLineThreshtxpowlowPortn OBJECT-TYPE
	SYNTAX  Unsigned32 (0..65536)
	MAX-ACCESS read-write
	STATUS current
	DESCRIPTION
        "
        Default Setting on Tx Power low 
        threshold :This register configures 
        the default initialisation of the 
        low threshold of the Transmit power 
        on the line.
        "
	::= { pm1004vdcCfgLineStartupThreshEntry 16 }


pm1004vdcCfgLineThreshrxpowhighPortn OBJECT-TYPE
	SYNTAX  Unsigned32 (0..65536)
	MAX-ACCESS read-write
	STATUS current
	DESCRIPTION
        "
        Default Setting on Rx Power high 
        threshold :This register configures 
        the default initialisation of the 
        high threshold of the received
         power on the line.
        "
	::= { pm1004vdcCfgLineStartupThreshEntry 19 }


pm1004vdcCfgLineThreshrxpowlowPortn OBJECT-TYPE
	SYNTAX  Unsigned32 (0..65536)
	MAX-ACCESS read-write
	STATUS current
	DESCRIPTION
        "
        Default Setting on Rx Power low 
        threshold :This register configures 
        the default initialisation of the 
        low threshold of the received power 
        on the line.
        "
	::= { pm1004vdcCfgLineStartupThreshEntry 20 }


--- *****************************************************
---     LEAF for the table Group startuptlh
--- *****************************************************

pm1004vdcCfgStartuptlh OBJECT IDENTIFIER ::= { pm1004vdcConfig 5 }



--- *****************************************************
---     LEAF for the table 25A8
--- *****************************************************

pm1004vdcCfgOtxtlhTable OBJECT-TYPE
	SYNTAX  SEQUENCE OF Pm1004vdcCfgOtxtlhEntry
	MAX-ACCESS not-accessible
	STATUS current
	DESCRIPTION
        "
        List of  Article
        "
	::= { pm1004vdcCfgStartuptlh 1 }


pm1004vdcCfgOtxtlhEntry OBJECT-TYPE
	SYNTAX Pm1004vdcCfgOtxtlhEntry
	MAX-ACCESS not-accessible
	STATUS current
	DESCRIPTION
        "
        Row definition for the startuptlh 
        table
        "
	INDEX   { pm1004vdcCfgOtxtlhIndex }
	::= { pm1004vdcCfgOtxtlhTable 1 }


Pm1004vdcCfgOtxtlhEntry ::=
	SEQUENCE {
	pm1004vdcCfgOtxtlhIndex
		INTEGER,
	pm1004vdcCfgNuPortn
		Unsigned32,
	pm1004vdcCfgLineDitherRatePortn
		Unsigned32,
	pm1004vdcCfgLineDitherFhzPortn
		Unsigned32,
	pm1004vdcCfgLinePwrLaserPortn
		Unsigned32,
	pm1004vdcCfgLineFCurrentPortn
		Unsigned32,
	pm1004vdcCfgLineGridCurrentPortn
		Unsigned32,
	pm1004vdcCfgFPortn
		Unsigned32,
	pm1004vdcCfgReservedPortn
		Unsigned32,
	pm1004vdcCfgLinePhotodiodeModePortn
		Unsigned32,
	pm1004vdcCfgLinePhotodiodeValuePortn
		Unsigned32
	}


pm1004vdcCfgOtxtlhIndex OBJECT-TYPE
	SYNTAX  INTEGER(0..128)
	MAX-ACCESS  read-only
	STATUS current
	DESCRIPTION
        "
        Index definition for the otxtlh 
        table
        "
	::= { pm1004vdcCfgOtxtlhEntry 1 }


pm1004vdcCfgNuPortn OBJECT-TYPE
	SYNTAX  Unsigned32 (0..65536)
	MAX-ACCESS read-write
	STATUS deprecated
	DESCRIPTION
        "
        :
        "
	::= { pm1004vdcCfgOtxtlhEntry 3 }


pm1004vdcCfgLineDitherRatePortn OBJECT-TYPE
	SYNTAX  Unsigned32 (0..65536)
	MAX-ACCESS read-write
	STATUS current
	DESCRIPTION
        "
        Default Line OTX TLH FM amplitude 
        :This register configures the start-up 
        width of the frequency modulation 
        of the Line OTX TLH
        "
	::= { pm1004vdcCfgOtxtlhEntry 4 }


pm1004vdcCfgLineDitherFhzPortn OBJECT-TYPE
	SYNTAX  Unsigned32 (0..65536)
	MAX-ACCESS read-write
	STATUS current
	DESCRIPTION
        "
        Default Line OTX TLH FM frequency 
        :This register configures the start-up 
        frequency of the frequency modulation 
        of the Line OTX TLH
        "
	::= { pm1004vdcCfgOtxtlhEntry 5 }


pm1004vdcCfgLinePwrLaserPortn OBJECT-TYPE
	SYNTAX  Unsigned32 (0..65536)
	MAX-ACCESS read-write
	STATUS current
	DESCRIPTION
        "
        Defaut Line OTX TLH output Power 
        :This register configures the start-up 
        output power of the Line OTX TLH 
         (Unit = dBm)
        "
	::= { pm1004vdcCfgOtxtlhEntry 6 }


pm1004vdcCfgLineFCurrentPortn OBJECT-TYPE
	SYNTAX  Unsigned32 (0..65536)
	MAX-ACCESS read-write
	STATUS current
	DESCRIPTION
        "
        Default Line OTX TLH Channel :This 
        register configures the start-up 
        laser channel of the Line OTX TLH
        "
	::= { pm1004vdcCfgOtxtlhEntry 7 }


pm1004vdcCfgLineGridCurrentPortn OBJECT-TYPE
	SYNTAX  Unsigned32 (0..65536)
	MAX-ACCESS read-write
	STATUS current
	DESCRIPTION
        "
        Default Line OTX TLH Grid :This 
        register configures the start-up 
        laser grid of the Line OTX TLH
        "
	::= { pm1004vdcCfgOtxtlhEntry 8 }


pm1004vdcCfgFPortn OBJECT-TYPE
	SYNTAX  Unsigned32 (0..65536)
	MAX-ACCESS read-write
	STATUS current
	DESCRIPTION
        "
        Default Line OTX TLH lowest Freq 
        :This register configures the start-up 
        lowest frequency supported on the 
        Line OTX TLH
        "
	::= { pm1004vdcCfgOtxtlhEntry 9 }


pm1004vdcCfgReservedPortn OBJECT-TYPE
	SYNTAX  Unsigned32 (0..65536)
	MAX-ACCESS read-write
	STATUS deprecated
	DESCRIPTION
        "
        :
        "
	::= { pm1004vdcCfgOtxtlhEntry 10 }


pm1004vdcCfgLinePhotodiodeModePortn OBJECT-TYPE
	SYNTAX  Unsigned32 (0..65536)
	MAX-ACCESS read-write
	STATUS current
	DESCRIPTION
        "
        Default Line OTX TLH APD mode
         :This register configures the
         start-up APD mode of the Line
         OTX TLH
        "
	::= { pm1004vdcCfgOtxtlhEntry 11 }


pm1004vdcCfgLinePhotodiodeValuePortn OBJECT-TYPE
	SYNTAX  Unsigned32 (0..65536)
	MAX-ACCESS read-write
	STATUS current
	DESCRIPTION
        "
        Default Line OTX TLH APD atten. 
        :This register configures the start-up 
        APD attenuation on the Line OTX 
        TLH
        "
	::= { pm1004vdcCfgOtxtlhEntry 12 }


--- *****************************************************
---     LEAF for the table Group startupslotslineaddtx1
--- *****************************************************

pm1004vdcCfgStartupslotslineaddtx1 OBJECT IDENTIFIER ::= { pm1004vdcConfig 6 }



--- *****************************************************
---     LEAF for the table 2910
--- *****************************************************

pm1004vdcCfgSlotslineaddtx1Table OBJECT-TYPE
	SYNTAX  SEQUENCE OF Pm1004vdcCfgSlotslineaddtx1Entry
	MAX-ACCESS not-accessible
	STATUS current
	DESCRIPTION
        "
        List of  Article
        "
	::= { pm1004vdcCfgStartupslotslineaddtx1 1 }


pm1004vdcCfgSlotslineaddtx1Entry OBJECT-TYPE
	SYNTAX Pm1004vdcCfgSlotslineaddtx1Entry
	MAX-ACCESS not-accessible
	STATUS current
	DESCRIPTION
        "
        Row definition for the startupslotslineaddtx1 
        table
        "
	INDEX   { pm1004vdcCfgSlotslineaddtx1Index }
	::= { pm1004vdcCfgSlotslineaddtx1Table 1 }


Pm1004vdcCfgSlotslineaddtx1Entry ::=
	SEQUENCE {
	pm1004vdcCfgSlotslineaddtx1Index
		INTEGER,
	pm1004vdcCfgLine1Addslotb2PortPortn
		Unsigned32,
	pm1004vdcCfgLine1Addslotb1PortPortn
		Unsigned32,
	pm1004vdcCfgLine1AddprotocolPortPortn
		Unsigned32
	}


pm1004vdcCfgSlotslineaddtx1Index OBJECT-TYPE
	SYNTAX  INTEGER(0..128)
	MAX-ACCESS  read-only
	STATUS current
	DESCRIPTION
        "
        Index definition for the slotslineaddtx1 
        table
        "
	::= { pm1004vdcCfgSlotslineaddtx1Entry 1 }


pm1004vdcCfgLine1Addslotb2PortPortn OBJECT-TYPE
	SYNTAX  Unsigned32 (0..65536)
	MAX-ACCESS read-write
	STATUS current
	DESCRIPTION
        "
        Port Defaut Add Slot allocation 
        (MSB) on Line1 :This register configures 
        the start-up slots allocation on 
        the port (MSB)
        "
	::= { pm1004vdcCfgSlotslineaddtx1Entry 3 }


pm1004vdcCfgLine1Addslotb1PortPortn OBJECT-TYPE
	SYNTAX  Unsigned32 (0..65536)
	MAX-ACCESS read-write
	STATUS current
	DESCRIPTION
        "
        Port Defaut Add Slot allocation 
        (LSB) on Line1 :This register configures 
        the start-up slots allocation on 
        the port (LSB)
        "
	::= { pm1004vdcCfgSlotslineaddtx1Entry 4 }


pm1004vdcCfgLine1AddprotocolPortPortn OBJECT-TYPE
	SYNTAX  Unsigned32 (0..65536)
	MAX-ACCESS read-write
	STATUS current
	DESCRIPTION
        "
        Port Defaut Protocol on Line1
         :This register configures the
         start-up protocol on the port
        "
	::= { pm1004vdcCfgSlotslineaddtx1Entry 5 }


--- *****************************************************
---     LEAF for the table Group startupslotslineaddtx2
--- *****************************************************

pm1004vdcCfgStartupslotslineaddtx2 OBJECT IDENTIFIER ::= { pm1004vdcConfig 7 }



--- *****************************************************
---     LEAF for the table 2920
--- *****************************************************

pm1004vdcCfgSlotslineaddtx2Table OBJECT-TYPE
	SYNTAX  SEQUENCE OF Pm1004vdcCfgSlotslineaddtx2Entry
	MAX-ACCESS not-accessible
	STATUS current
	DESCRIPTION
        "
        List of  Article
        "
	::= { pm1004vdcCfgStartupslotslineaddtx2 1 }


pm1004vdcCfgSlotslineaddtx2Entry OBJECT-TYPE
	SYNTAX Pm1004vdcCfgSlotslineaddtx2Entry
	MAX-ACCESS not-accessible
	STATUS current
	DESCRIPTION
        "
        Row definition for the startupslotslineaddtx2 
        table
        "
	INDEX   { pm1004vdcCfgSlotslineaddtx2Index }
	::= { pm1004vdcCfgSlotslineaddtx2Table 1 }


Pm1004vdcCfgSlotslineaddtx2Entry ::=
	SEQUENCE {
	pm1004vdcCfgSlotslineaddtx2Index
		INTEGER,
	pm1004vdcCfgLine2Addslotb2PortPortn
		Unsigned32,
	pm1004vdcCfgLine2Addslotb1PortPortn
		Unsigned32,
	pm1004vdcCfgLine2AddprotocolPortPortn
		Unsigned32
	}


pm1004vdcCfgSlotslineaddtx2Index OBJECT-TYPE
	SYNTAX  INTEGER(0..128)
	MAX-ACCESS  read-only
	STATUS current
	DESCRIPTION
        "
        Index definition for the slotslineaddtx2 
        table
        "
	::= { pm1004vdcCfgSlotslineaddtx2Entry 1 }


pm1004vdcCfgLine2Addslotb2PortPortn OBJECT-TYPE
	SYNTAX  Unsigned32 (0..65536)
	MAX-ACCESS read-write
	STATUS current
	DESCRIPTION
        "
        Port Defaut Add Slot allocation 
        (MSB) on Line2 :This register configures 
        the start-up slots allocation on 
        the port (MSB)
        "
	::= { pm1004vdcCfgSlotslineaddtx2Entry 3 }


pm1004vdcCfgLine2Addslotb1PortPortn OBJECT-TYPE
	SYNTAX  Unsigned32 (0..65536)
	MAX-ACCESS read-write
	STATUS current
	DESCRIPTION
        "
        Port Defaut Add Slot allocation 
        (LSB) on Line2 :This register configures 
        the start-up slots allocation on 
        the port (LSB)
        "
	::= { pm1004vdcCfgSlotslineaddtx2Entry 4 }


pm1004vdcCfgLine2AddprotocolPortPortn OBJECT-TYPE
	SYNTAX  Unsigned32 (0..65536)
	MAX-ACCESS read-write
	STATUS current
	DESCRIPTION
        "
        Port Defaut Protocol on Line2
         :This register configures the
         start-up protocol on the port
        "
	::= { pm1004vdcCfgSlotslineaddtx2Entry 5 }


--- *****************************************************
---     LEAF for the table Group startupslotslinepassthroughtx1
--- *****************************************************

pm1004vdcCfgStartupslotslinepassthroughtx1 OBJECT IDENTIFIER ::= { pm1004vdcConfig 8 }



--- *****************************************************
---     LEAF for the table 2912
--- *****************************************************

pm1004vdcCfgSlotslinepassthroughtx1Table OBJECT-TYPE
	SYNTAX  SEQUENCE OF Pm1004vdcCfgSlotslinepassthroughtx1Entry
	MAX-ACCESS not-accessible
	STATUS current
	DESCRIPTION
        "
        List of  Article
        "
	::= { pm1004vdcCfgStartupslotslinepassthroughtx1 1 }


pm1004vdcCfgSlotslinepassthroughtx1Entry OBJECT-TYPE
	SYNTAX Pm1004vdcCfgSlotslinepassthroughtx1Entry
	MAX-ACCESS not-accessible
	STATUS current
	DESCRIPTION
        "
        Row definition for the startupslotslinepassthroughtx1 
        table
        "
	INDEX   { pm1004vdcCfgSlotslinepassthroughtx1Index }
	::= { pm1004vdcCfgSlotslinepassthroughtx1Table 1 }


Pm1004vdcCfgSlotslinepassthroughtx1Entry ::=
	SEQUENCE {
	pm1004vdcCfgSlotslinepassthroughtx1Index
		INTEGER,
	pm1004vdcCfgLine1Slotb2PassthroughPortn
		Unsigned32,
	pm1004vdcCfgLine1Slotb1PassthroughPortn
		Unsigned32,
	pm1004vdcCfgLine1ProtocolPassthroughPortn
		Unsigned32
	}


pm1004vdcCfgSlotslinepassthroughtx1Index OBJECT-TYPE
	SYNTAX  INTEGER(0..128)
	MAX-ACCESS  read-only
	STATUS current
	DESCRIPTION
        "
        Index definition for the slotslinepassthroughtx1 
        table
        "
	::= { pm1004vdcCfgSlotslinepassthroughtx1Entry 1 }


pm1004vdcCfgLine1Slotb2PassthroughPortn OBJECT-TYPE
	SYNTAX  Unsigned32 (0..65536)
	MAX-ACCESS read-write
	STATUS current
	DESCRIPTION
        "
        Port Defaut PassThrough  Slot
         allocation (MSB) on Line1 :This 
        register configures the start-up 
        slots allocation on the port (MSB)
        "
	::= { pm1004vdcCfgSlotslinepassthroughtx1Entry 3 }


pm1004vdcCfgLine1Slotb1PassthroughPortn OBJECT-TYPE
	SYNTAX  Unsigned32 (0..65536)
	MAX-ACCESS read-write
	STATUS current
	DESCRIPTION
        "
        Port Defaut PassThrough Slot allocation 
        (LSB) on Line1 :This register configures 
        the start-up slots allocation on 
        the port (LSB)
        "
	::= { pm1004vdcCfgSlotslinepassthroughtx1Entry 4 }


pm1004vdcCfgLine1ProtocolPassthroughPortn OBJECT-TYPE
	SYNTAX  Unsigned32 (0..65536)
	MAX-ACCESS read-write
	STATUS current
	DESCRIPTION
        "
        Port Defaut PassThrough Protocol 
        on Line1 :This register configures 
        the start-up protocol on the port
        "
	::= { pm1004vdcCfgSlotslinepassthroughtx1Entry 5 }


--- *****************************************************
---     LEAF for the table Group startupslotslinepassthroughtx2
--- *****************************************************

pm1004vdcCfgStartupslotslinepassthroughtx2 OBJECT IDENTIFIER ::= { pm1004vdcConfig 9 }



--- *****************************************************
---     LEAF for the table 2922
--- *****************************************************

pm1004vdcCfgSlotslinepassthroughtx2Table OBJECT-TYPE
	SYNTAX  SEQUENCE OF Pm1004vdcCfgSlotslinepassthroughtx2Entry
	MAX-ACCESS not-accessible
	STATUS current
	DESCRIPTION
        "
        List of  Article
        "
	::= { pm1004vdcCfgStartupslotslinepassthroughtx2 1 }


pm1004vdcCfgSlotslinepassthroughtx2Entry OBJECT-TYPE
	SYNTAX Pm1004vdcCfgSlotslinepassthroughtx2Entry
	MAX-ACCESS not-accessible
	STATUS current
	DESCRIPTION
        "
        Row definition for the startupslotslinepassthroughtx2 
        table
        "
	INDEX   { pm1004vdcCfgSlotslinepassthroughtx2Index }
	::= { pm1004vdcCfgSlotslinepassthroughtx2Table 1 }


Pm1004vdcCfgSlotslinepassthroughtx2Entry ::=
	SEQUENCE {
	pm1004vdcCfgSlotslinepassthroughtx2Index
		INTEGER,
	pm1004vdcCfgLine2Slotb2PassthroughPortn
		Unsigned32,
	pm1004vdcCfgLine2Slotb1PassthroughPortn
		Unsigned32,
	pm1004vdcCfgLine2ProtocolPassthroughPortn
		Unsigned32
	}


pm1004vdcCfgSlotslinepassthroughtx2Index OBJECT-TYPE
	SYNTAX  INTEGER(0..128)
	MAX-ACCESS  read-only
	STATUS current
	DESCRIPTION
        "
        Index definition for the slotslinepassthroughtx2 
        table
        "
	::= { pm1004vdcCfgSlotslinepassthroughtx2Entry 1 }


pm1004vdcCfgLine2Slotb2PassthroughPortn OBJECT-TYPE
	SYNTAX  Unsigned32 (0..65536)
	MAX-ACCESS read-write
	STATUS current
	DESCRIPTION
        "
        Port Defaut PassThrough  Slot
         allocation (MSB) on Line2 :This 
        register configures the start-up 
        slots allocation on the port (MSB)
        "
	::= { pm1004vdcCfgSlotslinepassthroughtx2Entry 3 }


pm1004vdcCfgLine2Slotb1PassthroughPortn OBJECT-TYPE
	SYNTAX  Unsigned32 (0..65536)
	MAX-ACCESS read-write
	STATUS current
	DESCRIPTION
        "
        Port Defaut PassThrough Slot allocation 
        (LSB) on Line2 :This register configures 
        the start-up slots allocation on 
        the port (LSB)
        "
	::= { pm1004vdcCfgSlotslinepassthroughtx2Entry 4 }


pm1004vdcCfgLine2ProtocolPassthroughPortn OBJECT-TYPE
	SYNTAX  Unsigned32 (0..65536)
	MAX-ACCESS read-write
	STATUS current
	DESCRIPTION
        "
        Port Defaut PassThrough Protocol 
        on Line2 :This register configures 
        the start-up protocol on the port
        "
	::= { pm1004vdcCfgSlotslinepassthroughtx2Entry 5 }


--- *****************************************************
---     LEAF for the table Group startupslotslinedroprx1
--- *****************************************************

pm1004vdcCfgStartupslotslinedroprx1 OBJECT IDENTIFIER ::= { pm1004vdcConfig 10 }



--- *****************************************************
---     LEAF for the table 2911
--- *****************************************************

pm1004vdcCfgSlotslinedroprx1Table OBJECT-TYPE
	SYNTAX  SEQUENCE OF Pm1004vdcCfgSlotslinedroprx1Entry
	MAX-ACCESS not-accessible
	STATUS current
	DESCRIPTION
        "
        List of  Article
        "
	::= { pm1004vdcCfgStartupslotslinedroprx1 1 }


pm1004vdcCfgSlotslinedroprx1Entry OBJECT-TYPE
	SYNTAX Pm1004vdcCfgSlotslinedroprx1Entry
	MAX-ACCESS not-accessible
	STATUS current
	DESCRIPTION
        "
        Row definition for the startupslotslinedroprx1 
        table
        "
	INDEX   { pm1004vdcCfgSlotslinedroprx1Index }
	::= { pm1004vdcCfgSlotslinedroprx1Table 1 }


Pm1004vdcCfgSlotslinedroprx1Entry ::=
	SEQUENCE {
	pm1004vdcCfgSlotslinedroprx1Index
		INTEGER,
	pm1004vdcCfgLine1Dropslotb2PortPortn
		Unsigned32,
	pm1004vdcCfgLine1Dropslotb1PortPortn
		Unsigned32,
	pm1004vdcCfgLine1DropprotocolPortPortn
		Unsigned32
	}


pm1004vdcCfgSlotslinedroprx1Index OBJECT-TYPE
	SYNTAX  INTEGER(0..128)
	MAX-ACCESS  read-only
	STATUS current
	DESCRIPTION
        "
        Index definition for the slotslinedroprx1 
        table
        "
	::= { pm1004vdcCfgSlotslinedroprx1Entry 1 }


pm1004vdcCfgLine1Dropslotb2PortPortn OBJECT-TYPE
	SYNTAX  Unsigned32 (0..65536)
	MAX-ACCESS read-write
	STATUS current
	DESCRIPTION
        "
        Port Defaut Drop Slot allocation 
        (MSB) on Line1 :This register configures 
        the start-up slots allocation on 
        the port (MSB)
        "
	::= { pm1004vdcCfgSlotslinedroprx1Entry 3 }


pm1004vdcCfgLine1Dropslotb1PortPortn OBJECT-TYPE
	SYNTAX  Unsigned32 (0..65536)
	MAX-ACCESS read-write
	STATUS current
	DESCRIPTION
        "
        Port Defaut Drop Slot allocation 
        (LSB) on Line1 :This register configures 
        the start-up slots allocation on 
        the port (LSB)
        "
	::= { pm1004vdcCfgSlotslinedroprx1Entry 4 }


pm1004vdcCfgLine1DropprotocolPortPortn OBJECT-TYPE
	SYNTAX  Unsigned32 (0..65536)
	MAX-ACCESS read-write
	STATUS current
	DESCRIPTION
        "
        Port Defaut Protocol on Line1
         :This register configures the
         start-up protocol on the port
        "
	::= { pm1004vdcCfgSlotslinedroprx1Entry 5 }


--- *****************************************************
---     LEAF for the table Group startupslotslineaddrx2
--- *****************************************************

pm1004vdcCfgStartupslotslineaddrx2 OBJECT IDENTIFIER ::= { pm1004vdcConfig 11 }



--- *****************************************************
---     LEAF for the table 2921
--- *****************************************************

pm1004vdcCfgSlotslinedroprx2Table OBJECT-TYPE
	SYNTAX  SEQUENCE OF Pm1004vdcCfgSlotslinedroprx2Entry
	MAX-ACCESS not-accessible
	STATUS current
	DESCRIPTION
        "
        List of  Article
        "
	::= { pm1004vdcCfgStartupslotslineaddrx2 1 }


pm1004vdcCfgSlotslinedroprx2Entry OBJECT-TYPE
	SYNTAX Pm1004vdcCfgSlotslinedroprx2Entry
	MAX-ACCESS not-accessible
	STATUS current
	DESCRIPTION
        "
        Row definition for the startupslotslineaddrx2 
        table
        "
	INDEX   { pm1004vdcCfgSlotslinedroprx2Index }
	::= { pm1004vdcCfgSlotslinedroprx2Table 1 }


Pm1004vdcCfgSlotslinedroprx2Entry ::=
	SEQUENCE {
	pm1004vdcCfgSlotslinedroprx2Index
		INTEGER,
	pm1004vdcCfgLine2Dropslotb2PortPortn
		Unsigned32,
	pm1004vdcCfgLine2Dropslotb1PortPortn
		Unsigned32,
	pm1004vdcCfgLine2DropprotocolPortPortn
		Unsigned32
	}


pm1004vdcCfgSlotslinedroprx2Index OBJECT-TYPE
	SYNTAX  INTEGER(0..128)
	MAX-ACCESS  read-only
	STATUS current
	DESCRIPTION
        "
        Index definition for the slotslinedroprx2 
        table
        "
	::= { pm1004vdcCfgSlotslinedroprx2Entry 1 }


pm1004vdcCfgLine2Dropslotb2PortPortn OBJECT-TYPE
	SYNTAX  Unsigned32 (0..65536)
	MAX-ACCESS read-write
	STATUS current
	DESCRIPTION
        "
        Port Defaut Drop Slot allocation 
        (MSB) on Line2 :This register configures 
        the start-up slots allocation on 
        the port (MSB)
        "
	::= { pm1004vdcCfgSlotslinedroprx2Entry 3 }


pm1004vdcCfgLine2Dropslotb1PortPortn OBJECT-TYPE
	SYNTAX  Unsigned32 (0..65536)
	MAX-ACCESS read-write
	STATUS current
	DESCRIPTION
        "
        Port Defaut Drop Slot allocation 
        (LSB) on Line2 :This register configures 
        the start-up slots allocation on 
        the port (LSB)
        "
	::= { pm1004vdcCfgSlotslinedroprx2Entry 4 }


pm1004vdcCfgLine2DropprotocolPortPortn OBJECT-TYPE
	SYNTAX  Unsigned32 (0..65536)
	MAX-ACCESS read-write
	STATUS current
	DESCRIPTION
        "
        Port Defaut Protocol on Line2
         :This register configures the
         start-up protocol on the port
        "
	::= { pm1004vdcCfgSlotslinedroprx2Entry 5 }


--- *****************************************************
---     LEAF for the table Group other
--- *****************************************************

pm1004vdcCfgOther OBJECT IDENTIFIER ::= { pm1004vdcConfig 12 }



--- *****************************************************
---     LEAF for the table 2300
--- *****************************************************

pm1004vdctablemoduleOther OBJECT IDENTIFIER ::= { pm1004vdcCfgOther 1 }



pm1004vdcCfgmode OBJECT-TYPE
	  SYNTAX Unsigned32 (0..65536)
	  MAX-ACCESS read-write
	  STATUS current
	  DESCRIPTION
        "
        Default settings on Module :This 
        register selects the startup mode 
        of the module
        "
	  ::= { pm1004vdctablemoduleOther 2 }



--- *****************************************************
---     LEAF for the table Group startuptablefive
--- *****************************************************

pm1004vdcCfgStartuptablefive OBJECT IDENTIFIER ::= { pm1004vdcConfig 13 }



--- *****************************************************
---     LEAF for the table 0005
--- *****************************************************

pm1004vdcCfgOtxtlhcapabilitiesTable OBJECT-TYPE
	SYNTAX  SEQUENCE OF Pm1004vdcCfgOtxtlhcapabilitiesEntry
	MAX-ACCESS not-accessible
	STATUS current
	DESCRIPTION
        "
        List of  Article
        "
	::= { pm1004vdcCfgStartuptablefive 1 }


pm1004vdcCfgOtxtlhcapabilitiesEntry OBJECT-TYPE
	SYNTAX Pm1004vdcCfgOtxtlhcapabilitiesEntry
	MAX-ACCESS not-accessible
	STATUS current
	DESCRIPTION
        "
        Row definition for the startuptablefive 
        table
        "
	INDEX   { pm1004vdcCfgOtxtlhcapabilitiesIndex }
	::= { pm1004vdcCfgOtxtlhcapabilitiesTable 1 }


Pm1004vdcCfgOtxtlhcapabilitiesEntry ::=
	SEQUENCE {
	pm1004vdcCfgOtxtlhcapabilitiesIndex
		INTEGER,
	pm1004vdcCfgComponentTypePortn
		Unsigned32,
	pm1004vdcCfgMiscellaneousPortn
		Unsigned32,
	pm1004vdcCfgFirstChannelPortn
		Unsigned32,
	pm1004vdcCfgLastChannelPortn
		Unsigned32,
	pm1004vdcCfgGridPortn
		Unsigned32
	}


pm1004vdcCfgOtxtlhcapabilitiesIndex OBJECT-TYPE
	SYNTAX  INTEGER(0..128)
	MAX-ACCESS  read-only
	STATUS current
	DESCRIPTION
        "
        Index definition for the otxtlhcapabilities 
        table
        "
	::= { pm1004vdcCfgOtxtlhcapabilitiesEntry 1 }


pm1004vdcCfgComponentTypePortn OBJECT-TYPE
	SYNTAX  Unsigned32 (0..65536)
	MAX-ACCESS read-only
	STATUS current
	DESCRIPTION
        "
        Component parameters :This OID 
        defines the component parameters
        "
	::= { pm1004vdcCfgOtxtlhcapabilitiesEntry 3 }


pm1004vdcCfgMiscellaneousPortn OBJECT-TYPE
	SYNTAX  Unsigned32 (0..65536)
	MAX-ACCESS read-only
	STATUS current
	DESCRIPTION
        "
        Miscellaneous default settings 
        :This OID defines the miscellaneous 
        parameters
        "
	::= { pm1004vdcCfgOtxtlhcapabilitiesEntry 4 }


pm1004vdcCfgFirstChannelPortn OBJECT-TYPE
	SYNTAX  Unsigned32 (0..65536)
	MAX-ACCESS read-only
	STATUS current
	DESCRIPTION
        "
        Number of the first channel of 
        the component :This OID defines 
        the first channel number of the 
        PM
        "
	::= { pm1004vdcCfgOtxtlhcapabilitiesEntry 5 }


pm1004vdcCfgLastChannelPortn OBJECT-TYPE
	SYNTAX  Unsigned32 (0..65536)
	MAX-ACCESS read-only
	STATUS current
	DESCRIPTION
        "
        Number of the last channel of
         the component :This OID defines 
        the last channel number of the
         PM
        "
	::= { pm1004vdcCfgOtxtlhcapabilitiesEntry 6 }


pm1004vdcCfgGridPortn OBJECT-TYPE
	SYNTAX  Unsigned32 (0..65536)
	MAX-ACCESS read-only
	STATUS current
	DESCRIPTION
        "
        Grid value of the component :This 
        OID defines the grid of the PM
        "
	::= { pm1004vdcCfgOtxtlhcapabilitiesEntry 7 }



pm1004vdcCfgWriteConfiguration  OBJECT-TYPE
	SYNTAX EkiOnOff
	MAX-ACCESS read-write
	STATUS current
	DESCRIPTION
	"Write configuration to module:This OID 
	 writes the complete configuration to the module"
	::= { pm1004vdcConfig 257 }






--- *****************************************************
---     TRAP OBJECTS
--- *****************************************************

pm1004vdctrapPortNumber OBJECT-TYPE
	SYNTAX INTEGER(1..64)
	MAX-ACCESS read-only
	STATUS current
	DESCRIPTION
	"Last port which generates a trap"
	::= { pm1004vdctraps 2 }

pm1004vdctrapLineNumber OBJECT-TYPE
	SYNTAX INTEGER(1..64)
	MAX-ACCESS read-only
	STATUS current
	DESCRIPTION
	"Last Line which generates a trap"
	::= { pm1004vdctraps 3 }

pm1004vdctrapBoardNumber OBJECT-TYPE
	SYNTAX INTEGER(1..64)
	MAX-ACCESS read-only
	STATUS current
	DESCRIPTION
	"Last module which generates a trap"
	::= { pm1004vdctraps 4 }







--- *****************************************************
---     LINE TRAPS
--- *****************************************************

pm1004vdcLineTrapNotUrgentGoesOn NOTIFICATION-TYPE
	OBJECTS {pm1004vdcAlmLineDdmWarningPortn, pm1004vdctrapLineNumber, pm1004vdctrapBoardNumber}
	STATUS current
	--&FILTNAME    "PM1004VDC Line Not Urgent ON"
	--&ACTIONS     { log, minor }
	--&MATCH       { pm1004vdcAlmLineDdmWarningPortn "on", pm1004vdctrapLineNumber "$2", pm1004vdctrapBoardNumber "$3"}
	--&MESG        "DDM Warning appears on Line Port $2 of PM1004VDC(LH) in Slot $3 ($A)"
	DESCRIPTION "Not urgent Line default is activated"
	::= { pm1004vdctraps 30 }

pm1004vdcLineTrapNotUrgentGoesOff NOTIFICATION-TYPE
	OBJECTS {pm1004vdcAlmLineDdmWarningPortn, pm1004vdctrapLineNumber, pm1004vdctrapBoardNumber}
	STATUS current
	--&FILTNAME    "PM1004VDC Line Not Urgent OFF"
	--&ACTIONS     { log, normal }
	--&CLEARS      { "PM1004VDC Line Not Urgent ON" }
	--&MATCH       { pm1004vdcAlmLineDdmWarningPortn "on", pm1004vdctrapLineNumber "$2", pm1004vdctrapBoardNumber "$3"}
	--&MESG        "DDM Warning disappears on Line Port $2 of PM1004VDC in Slot $3 ($A)"
	DESCRIPTION "Not urgent Line default disappeared"
	::= { pm1004vdctraps 31 }

pm1004vdcLineTrapUrgentGoesOn NOTIFICATION-TYPE
	OBJECTS {pm1004vdcAlmLineDdmAlmPortn, pm1004vdctrapLineNumber, pm1004vdctrapBoardNumber}
	STATUS current
	--&FILTNAME    "PM1004VDC Line Urgent ON"
	--&ACTIONS     { log, major }
	--&MATCH       { pm1004vdcAlmLineDdmAlmPortn "on", pm1004vdctrapLineNumber "$2", pm1004vdctrapBoardNumber "$3"}
	--&MESG        "DDM Alarm appears on Line Port $2 of PM1004VDC in Slot $3 ($A)"
	DESCRIPTION "Urgent Line default is activated"
	::= { pm1004vdctraps 32 }

pm1004vdcLineTrapUrgentGoesOff NOTIFICATION-TYPE
	OBJECTS {pm1004vdcAlmLineDdmAlmPortn, pm1004vdctrapLineNumber, pm1004vdctrapBoardNumber}
	STATUS current
	--&FILTNAME    "PM1004VDC Line Urgent OFF"
	--&ACTIONS     { log, normal }
	--&CLEARS      { "PM1004VDC Line Urgent ON" }
	--&MATCH       { pm1004vdcAlmLineDdmAlmPortn "on", pm1004vdctrapLineNumber "$2", pm1004vdctrapBoardNumber "$3"}
	--&MESG        "DDM Alarm disappears on Line Port $2 of PM1004VDC in Slot $3 ($A)"
	DESCRIPTION "Urgent Line default disappeared"
	::= { pm1004vdctraps 33 }

pm1004vdcLineTrapCritGoesOn NOTIFICATION-TYPE
	OBJECTS {pm1004vdcAlmLineFailPortn , pm1004vdcAlmLineHwFailPortn , pm1004vdctrapLineNumber, pm1004vdctrapBoardNumber}
	STATUS current
	--&FILTNAME    "PM1004VDC Line Fail ON"
	--&ACTIONS     { log, critical }
	--&MATCH       { pm1004vdcAlmLineFailPortn "on", pm1004vdcAlmLineHwFailPortn "*", pm1004vdctrapLineNumber "$3", pm1004vdctrapBoardNumber "$4"}
	--&MESG        "Line Port $3 Down on PM1004VDC in Slot $4 ($A)"
	
	--&FILTNAME    "PM1004VDC Line HW Fail ON (Hidden)"
	--&ACTIONS     { info }
	--&MATCH       { pm1004vdcAlmLineFailPortn "*", pm1004vdcAlmLineHwFailPortn "on", pm1004vdctrapLineNumber "$3", pm1004vdctrapBoardNumber "$4"}
	--&MESG        "Line Port $3 Down on PM1004VDC in Slot $4 ($A)"
	DESCRIPTION "Critical Line default is activated"
	::= { pm1004vdctraps 34 }

pm1004vdcLineTrapCritGoesOff NOTIFICATION-TYPE
	OBJECTS {pm1004vdcAlmLineFailPortn , pm1004vdcAlmLineHwFailPortn , pm1004vdctrapLineNumber, pm1004vdctrapBoardNumber}
	STATUS current
	--&FILTNAME    "PM1004VDC Line Fail OFF"
	--&ACTIONS     { log,  normal }
	--&CLEARS      { "PM1004VDC Line Fail ON" }
	--&MATCH       { pm1004vdcAlmLineFailPortn "on", pm1004vdcAlmLineHwFailPortn "*", pm1004vdctrapLineNumber "$3", pm1004vdctrapBoardNumber "$4"}
	--&MESG        "Line Port $3 Up on PM1004VDC in Slot $4 ($A)"

	--&FILTNAME    "PM1004VDC Line HW Fail OFF (Hidden)"
	--&ACTIONS     { info }
	--&MATCH       { pm1004vdcAlmLineFailPortn "*", pm1004vdcAlmLineHwFailPortn "on", pm1004vdctrapLineNumber "$3", pm1004vdctrapBoardNumber "$4"}
	--&MESG        "Line Port $3 Up on PM1004VDC in Slot $4 ($A)"
	DESCRIPTION "Critical Line default disappeared"
	::= { pm1004vdctraps 35 }






--- *****************************************************
---     CLIENT TRAPS
--- *****************************************************

pm1004vdcClientTrapNotUrgentGoesOn NOTIFICATION-TYPE
	OBJECTS {pm1004vdcAlmSfpDdmWarningPortn, pm1004vdctrapPortNumber, pm1004vdctrapBoardNumber}
	STATUS current
	--&FILTNAME    "PM1004VDC Client Not Urgent ON"
	--&ACTIONS     { log, minor }
	--&MATCH       { pm1004vdcAlmSfpDdmWarningPortn "on", pm1004vdctrapPortNumber "$2", pm1004vdctrapBoardNumber "$3"}
	--&MESG        "DDM Warning appears on Client Port $2 of PM1004VDC in Slot $3 ($A)"
	DESCRIPTION "Not urgent client default is activated"
	::= { pm1004vdctraps 40 }

pm1004vdcClientTrapNotUrgentGoesOff NOTIFICATION-TYPE
	OBJECTS {pm1004vdcAlmSfpDdmWarningPortn, pm1004vdctrapPortNumber, pm1004vdctrapBoardNumber}
	STATUS current
	--&FILTNAME    "PM1004VDC Client Not Urgent OFF"
	--&ACTIONS     { log, normal }
	--&CLEARS      { "PM1004VDC Client Not Urgent ON" }
	--&MATCH       { pm1004vdcAlmSfpDdmWarningPortn "on", pm1004vdctrapPortNumber "$2", pm1004vdctrapBoardNumber "$3"}
	--&MESG        "DDM Warning appears on Client Port $2 of PM1004VDC in Slot $3 ($A)"
	DESCRIPTION "Not urgent client default disappeared"
	::= { pm1004vdctraps 41 }

pm1004vdcClientTrapUrgentGoesOn NOTIFICATION-TYPE
	OBJECTS {pm1004vdcAlmSfpDdmAlmPortn, pm1004vdctrapPortNumber, pm1004vdctrapBoardNumber}
	STATUS current
	--&FILTNAME    "PM1004VDC Client Urgent ON"
	--&ACTIONS     { log, major }
	--&MATCH       { pm1004vdcAlmSfpDdmAlmPortn "on", pm1004vdctrapPortNumber "$2", pm1004vdctrapBoardNumber "$3"}
	--&MESG        "DDM Alarm appears on Client Port $2 of PM1004VDC in Slot $3 ($A)"
	DESCRIPTION "Urgent client default is activated"
	::= { pm1004vdctraps 42 }

pm1004vdcClientTrapUrgentGoesOff NOTIFICATION-TYPE
	OBJECTS {pm1004vdcAlmSfpDdmAlmPortn, pm1004vdctrapPortNumber, pm1004vdctrapBoardNumber}
	STATUS current
	--&FILTNAME    "PM1004VDC Client Urgent OFF"
	--&ACTIONS     { log, normal }
	--&CLEARS      { "PM1004VDC Client Urgent ON" }
	--&MATCH       { pm1004vdcAlmSfpDdmAlmPortn "on", pm1004vdctrapPortNumber "$2", pm1004vdctrapBoardNumber "$3"}
	--&MESG        "DDM Alarm disappears on Client Port $2 of PM1004VDC in Slot $3 ($A)"
	DESCRIPTION "Urgent client default disappeared"
	::= { pm1004vdctraps 43 }

pm1004vdcClientTrapCritGoesOn NOTIFICATION-TYPE
	OBJECTS {pm1004vdcAlmFailAccPortn, pm1004vdcAlmHwFailAccPortn, pm1004vdctrapPortNumber, pm1004vdctrapBoardNumber}
	STATUS current
	--&FILTNAME    "PM1004VDC Client Fail ON"
	--&ACTIONS     { log, critical }
	--&MATCH       { pm1004vdcAlmFailAccPortn "on", pm1004vdcAlmHwFailAccPortn "*", pm1004vdctrapPortNumber "$3", pm1004vdctrapBoardNumber "$4"}
	--&MESG        "Client Port $3 Down on PM1004VDC in Slot $4 ($A)"
	
	--&FILTNAME    "PM1004VDC Client HW Fail ON (Hidden)"
	--&ACTIONS     { info }
	--&MATCH       { pm1004vdcAlmFailAccPortn "*", pm1004vdcAlmHwFailAccPortn "on", pm1004vdctrapPortNumber "$3", pm1004vdctrapBoardNumber "$4"}
	--&MESG        "Client Port $3 Down on PM1004VDC in Slot $4 ($A)"
	DESCRIPTION "Critical client default is activated"
	::= { pm1004vdctraps 44 }

pm1004vdcClientTrapCritGoesOff NOTIFICATION-TYPE
	OBJECTS {pm1004vdcAlmFailAccPortn, pm1004vdcAlmHwFailAccPortn, pm1004vdctrapPortNumber, pm1004vdctrapBoardNumber}
	STATUS current
	--&FILTNAME    "PM1004VDC Client Fail OFF"
	--&ACTIONS     { log, normal }
	--&CLEARS      { "PM1004VDC Client Fail ON" }
	--&MATCH       { pm1004vdcAlmFailAccPortn "on", pm1004vdcAlmHwFailAccPortn "*", pm1004vdctrapPortNumber "$3", pm1004vdctrapBoardNumber "$4"}
	--&MESG        "Client Port $3 Up on PM1004VDC in Slot $4 ($A)"
	
	--&FILTNAME    "PM1004VDC Client HW Fail OFF (Hidden)"
	--&ACTIONS     { info }
	--&MATCH       { pm1004vdcAlmFailAccPortn "*", pm1004vdcAlmHwFailAccPortn "on", pm1004vdctrapPortNumber "$3", pm1004vdctrapBoardNumber "$4"}
	--&MESG        "Client Port $3 Up on PM1004VDC in Slot $4 ($A)"
	DESCRIPTION "Critical client default disappeared"
	::= { pm1004vdctraps 45 }






--- *****************************************************
---     HW TRAPS
--- *****************************************************

pm1004vdcPowerTrapUrgentGoesOn NOTIFICATION-TYPE
	OBJECTS {pm1004vdcAlmDefFuseB, pm1004vdcAlmDefFuseA , pm1004vdctrapBoardNumber}
	STATUS current
	--&FILTNAME    "PM1004VDC Fuse A Fail ON"
	--&ACTIONS     { log, major }
	--&MATCH       { pm1004vdcAlmDefFuseB "*", pm1004vdcAlmDefFuseA "on", pm1004vdctrapBoardNumber "$3"}
	--&MESG        "Power Input A Fail on PM1004VDC in Slot $3 ($A)"

	--&FILTNAME    "PM1004VDC Fuse B Fail ON"
	--&ACTIONS     { log, major }
	--&MATCH       { pm1004vdcAlmDefFuseB "on", pm1004vdcAlmDefFuseA "*", pm1004vdctrapBoardNumber "$3"}
	--&MESG        "Power Input B Fail on PM1004VDC in Slot $3 ($A)"
	DESCRIPTION "Urgent power supply default is activated"
	::= { pm1004vdctraps 50 }

pm1004vdcPowerTrapUrgentGoesOff NOTIFICATION-TYPE
	OBJECTS {pm1004vdcAlmDefFuseB, pm1004vdcAlmDefFuseA , pm1004vdctrapBoardNumber}
	STATUS current
	--&FILTNAME    "PM1004VDC Fuse A&B Fail OFF"
	--&ACTIONS     { log, normal}
	--&CLEARS      { "PM1004VDC Fuse A Fail ON", "PM1004VDC Fuse B Fail ON" }
	--&MATCH       { pm1004vdcAlmDefFuseB "on", pm1004vdcAlmDefFuseA "on", pm1004vdctrapBoardNumber "$3"}
	--&MESG        "Power Inputs A and B Present on PM1004VDC in Slot $3 ($A)"
	DESCRIPTION "Urgent power supply default disappeared"
	::= { pm1004vdctraps 51 }






END
