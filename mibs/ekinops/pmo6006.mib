-- *****************************************************************
-- EKINOPS-Pmo6006.TXT:  MIB
--
--MIB Part Number:3MI00036AAAE
--MIB Version:01
--
-- Copyright (c) 2018 by Ekinops
-- All rights reserved.
-- 
-- *****************************************************************

EKINOPS-Pmo6006-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress                
        		FROM SNMPv2-SMI
 	TEXTUAL-CONVENTION,
	DisplayString
                FROM SNMPv2-TC;

modulePmo6006 MODULE-IDENTITY
        LAST-UPDATED "201804240000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.fr"
        DESCRIPTION
          "Creation."

	REVISION "201503260000Z"
	DESCRIPTION
	  "Creation for PMO6006"

	REVISION "201503300000Z"
	DESCRIPTION
	  "Creation for PMO6006"
	REVISION "201601290000Z"
	DESCRIPTION
	  "SAPI/DAPI Acc config suppress"
	REVISION "201605200000Z"
	DESCRIPTION
	  "New AlarmType – synthesisAlarm (12)"
	REVISION "201606030000Z"
	DESCRIPTION
	  "Capabilities objects of Table 5"
	REVISION "201607220000Z"
	DESCRIPTION
	  "Protocols insertion"
	REVISION "201804240000Z"
	DESCRIPTION
	  "Tunability on Client"
        ::= { ekinops 70 }



--- *****************************************************
---     LEAF LEVEL 2
--- *****************************************************


pmo6006alarms OBJECT IDENTIFIER ::= { modulePmo6006 2 }	
pmo6006AlmOther OBJECT IDENTIFIER ::= { pmo6006alarms 1 }
pmo6006AlmOtherNurg OBJECT IDENTIFIER ::= { pmo6006AlmOther 1 }
pmo6006AlmOtherUrg OBJECT IDENTIFIER ::= { pmo6006AlmOther 2 }
pmo6006AlmOtherCrit OBJECT IDENTIFIER ::= { pmo6006AlmOther 3 }

pmo6006AlmClient OBJECT IDENTIFIER ::= { pmo6006alarms 2 }
pmo6006AlmClientNurg OBJECT IDENTIFIER ::= { pmo6006AlmClient 1 }
pmo6006AlmClientUrg OBJECT IDENTIFIER ::= { pmo6006AlmClient 2 }
pmo6006AlmClientCrit OBJECT IDENTIFIER ::= { pmo6006AlmClient 3 }
	
pmo6006AlmLine OBJECT IDENTIFIER ::= { pmo6006alarms 3 }
pmo6006AlmLineNurg OBJECT IDENTIFIER ::= { pmo6006AlmLine 1 }
pmo6006AlmLineUrg OBJECT IDENTIFIER ::= { pmo6006AlmLine 2 }
pmo6006AlmLineCrit OBJECT IDENTIFIER ::= { pmo6006AlmLine 3 }





pmo6006measures OBJECT IDENTIFIER ::= { modulePmo6006 3 }	
pmo6006MesrOther OBJECT IDENTIFIER ::= { pmo6006measures 1 }	
pmo6006MesrClient OBJECT IDENTIFIER ::= { pmo6006measures 2 }	
pmo6006MesrLine OBJECT IDENTIFIER ::= { pmo6006measures 3 }	




pmo6006counters OBJECT IDENTIFIER ::= { modulePmo6006 4 }
pmo6006CntOther OBJECT IDENTIFIER ::= { pmo6006counters 1 }
pmo6006CntClient OBJECT IDENTIFIER ::= { pmo6006counters 2 }
pmo6006CntLine OBJECT IDENTIFIER ::= { pmo6006counters 3 }


pmo6006controlsWrite OBJECT IDENTIFIER ::= { modulePmo6006 6 }
pmo6006CtrlOther OBJECT IDENTIFIER ::= { pmo6006controlsWrite 1 }
pmo6006CtrlClient OBJECT IDENTIFIER ::= { pmo6006controlsWrite 2 }
pmo6006CtrlLine OBJECT IDENTIFIER ::= { pmo6006controlsWrite 3 }

pmo6006ri OBJECT IDENTIFIER ::= { modulePmo6006 7 }
pmo6006riTable OBJECT IDENTIFIER ::= { pmo6006ri 1 }

pmo6006download OBJECT IDENTIFIER ::= { modulePmo6006 8 }
pmo6006DwlOther OBJECT IDENTIFIER ::= { pmo6006download 1 }
pmo6006DwlClient OBJECT IDENTIFIER ::= { pmo6006download 2 }
pmo6006DwlLine OBJECT IDENTIFIER ::= { pmo6006download 3 }


pmo6006Config OBJECT IDENTIFIER ::= { modulePmo6006 9 }

pmo6006traps OBJECT IDENTIFIER ::= { modulePmo6006 10 }



pmo6006Monitoring OBJECT IDENTIFIER ::= { modulePmo6006 11}

pmo6006MonOther OBJECT IDENTIFIER ::= { pmo6006Monitoring 1 }
pmo6006MonRmon OBJECT IDENTIFIER ::= { pmo6006MonOther 3 }

pmo6006MonClient OBJECT IDENTIFIER ::= { pmo6006Monitoring 2 }
pmo6006MonClientRmonCounter OBJECT IDENTIFIER ::= { pmo6006MonClient 4 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************


Pmo6006OtxGrid ::= TEXTUAL-CONVENTION
    STATUS      current
    DESCRIPTION "Different grids on client and line ports"
    SYNTAX INTEGER {
		otxgrid200(200),
		otxgrid100(100),
		otxgrid50(50)
           }


Pmo6006DccMode ::= TEXTUAL-CONVENTION
    STATUS      current
    DESCRIPTION "Mode for DCC"
    SYNTAX INTEGER {
		dccNo(0),
		dccLine1(1),
		dccLine2(2)
           }

Pmo6006LineChannel ::= TEXTUAL-CONVENTION
    STATUS      current
    DESCRIPTION "Channel selection on transceiver Line ports"
    SYNTAX INTEGER


Pmo6006Odu2SapiMode ::= TEXTUAL-CONVENTION
    STATUS      current
    DESCRIPTION "Mode for SAPI-DAPI"
    SYNTAX INTEGER {
		off(0),
		sapi(1),
		dapi(2),
		sapidapi(3)
           }

Pmo6006Otu2SapiMode ::= TEXTUAL-CONVENTION
    STATUS      current
    DESCRIPTION "Mode for SAPI-DAPI"
    SYNTAX INTEGER {
		off(0),
		sapi(1),
		dapi(2),
		sapidapi(3)
           }

Pmo6006ClientProtocol ::= TEXTUAL-CONVENTION
    STATUS      current
    DESCRIPTION "Different values on the protocol on the client ports"
    SYNTAX INTEGER {
		protocolclientvalue2(2),
		protocolclientvalue3(3),
		protocolclientvalue4(4),
		protocolclientvalue6(6),
		protocolclientvalue7(7)
           }

Pmo6006ClientChannel ::= TEXTUAL-CONVENTION
    STATUS      current
    DESCRIPTION "Channel selection on transceiver Client ports"
    SYNTAX INTEGER


--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pmo6006RinvReloadInventory OBJECT-TYPE
  SYNTAX EkiOnOff
  MAX-ACCESS read-write
  STATUS current
  DESCRIPTION
        "Reload the inventory: This OID triggers an 
         inventory reload."
  ::= { pmo6006ri 2 }

pmo6006RinvHwPlatform OBJECT-TYPE
  SYNTAX DisplayString
  MAX-ACCESS read-only
  STATUS current
  DESCRIPTION
        "HW platform description: This OID contains the 
         description of the Hardware platform."
  ::= { pmo6006ri 3 }
  
pmo6006RinvModulePlatform OBJECT-TYPE
  SYNTAX DisplayString
  MAX-ACCESS read-only
  STATUS current
  DESCRIPTION
        "Module platform description: This OID contains the 
         description of the Module."
  ::= { pmo6006ri 4 }
  
pmo6006RinvSwPlatform OBJECT-TYPE
  SYNTAX DisplayString
  MAX-ACCESS read-only
  STATUS current
  DESCRIPTION
        "SW platform description: This OID contains the 
         description of the Software platform."
  ::= { pmo6006ri 5 }
  
pmo6006RinvGwPlatform OBJECT-TYPE
  SYNTAX DisplayString
  MAX-ACCESS read-only
  STATUS current
  DESCRIPTION
        "GW platform description: This OID contains the 
         description of the Gateware platform."
  ::= { pmo6006ri 6 }


pmo6006RinvSfpTable OBJECT-TYPE
      SYNTAX  SEQUENCE OF Pmo6006RinvSfpEntry
      MAX-ACCESS  not-accessible
      STATUS  current
      DESCRIPTION
              "List of the SFPs on the selected module"
      ::= { pmo6006riTable 1 }

pmo6006RinvSfpEntry OBJECT-TYPE
        SYNTAX  Pmo6006RinvSfpEntry
        MAX-ACCESS  not-accessible
        STATUS  current
        DESCRIPTION
              "Row definition for the SFP table"
        INDEX   { pmo6006RinvSfpIndex }
        ::= { pmo6006RinvSfpTable 1 }
    


Pmo6006RinvSfpEntry::=
        SEQUENCE {
          pmo6006RinvSfpIndex 
              Integer32,
          pmo6006Rinvsfp
              DisplayString
        }


    pmo6006RinvSfpIndex OBJECT-TYPE
        SYNTAX  Integer32(1..16)
        MAX-ACCESS  read-only
        STATUS  current
        DESCRIPTION
              "Index for SFP table"
        ::= { pmo6006RinvSfpEntry 1 }


    pmo6006Rinvsfp OBJECT-TYPE
        SYNTAX  DisplayString
        MAX-ACCESS  read-only
        STATUS  current
        DESCRIPTION
              "Inventory for the SFP: This OID contains the inventory for the SFP"
        ::= { pmo6006RinvSfpEntry 2 }




pmo6006RinvLineTable OBJECT-TYPE
      SYNTAX  SEQUENCE OF Pmo6006RinvLineEntry
      MAX-ACCESS  not-accessible
      STATUS  current
      DESCRIPTION
              "List of the SFPs on the selected module"
      ::= { pmo6006riTable 2 }

pmo6006RinvLineEntry OBJECT-TYPE
        SYNTAX  Pmo6006RinvLineEntry
        MAX-ACCESS  not-accessible
        STATUS  current
        DESCRIPTION
              "Row definition for the SFP table"
        INDEX   { pmo6006RinvLineIndex }
        ::= { pmo6006RinvLineTable 1 }
    


Pmo6006RinvLineEntry::=
        SEQUENCE {
          pmo6006RinvLineIndex 
              Integer32,
          pmo6006RinvxfpLine
              DisplayString
        }


    pmo6006RinvLineIndex OBJECT-TYPE
        SYNTAX  Integer32(1..16)
        MAX-ACCESS  read-only
        STATUS  current
        DESCRIPTION
              "Index for SFP table"
        ::= { pmo6006RinvLineEntry 1 }


    pmo6006RinvxfpLine OBJECT-TYPE
        SYNTAX  DisplayString
        MAX-ACCESS  read-only
        STATUS  current
        DESCRIPTION
              "Inventory for the XFP: This OID contains the inventory for the XFP"
        ::= { pmo6006RinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pmo6006AlmsynthAlm0 OBJECT IDENTIFIER ::= { pmo6006AlmOtherCrit 0 }




pmo6006AlmDefFuseB OBJECT-TYPE
	  SYNTAX EkiOnOff
	  MAX-ACCESS read-only
	  STATUS current
	  DESCRIPTION
        "
        Fuse B Fail :This OID indicates 
        that the fuse of the power input 
        B is in fail condition <Help> Status 
        of the Fuse B <Condtype> DEF_FUSE_B 
        <Probcause> powerProblem (36) <Alarmtype> 
        equipmentAlarm (5) <Polarity> (2) 
        "
	  ::= { pmo6006AlmsynthAlm0 16 }



pmo6006AlmDefFuseA OBJECT-TYPE
	  SYNTAX EkiOnOff
	  MAX-ACCESS read-only
	  STATUS current
	  DESCRIPTION
        "
        Fuse A Fail :This OID indicates 
        that the fuse of the power input 
        A is in fail condition <Help> Status 
        of the Fuse A <Condtype> DEF_FUSE_A 
        <Probcause> powerProblem (36) <Alarmtype> 
        equipmentAlarm (5) <Polarity> (2) 
        "
	  ::= { pmo6006AlmsynthAlm0 15 }



pmo6006AlmModGlobFail OBJECT-TYPE
	  SYNTAX EkiOnOff
	  MAX-ACCESS read-only
	  STATUS current
	  DESCRIPTION
        "
        Module Failure :This OID is set 
        on detection of a failure originating 
        from the RM <Help> This alarm is 
        set on detection of a failure originating 
        from the equipment <Condtype> MOD_GLOB_FAIL 
        <Probcause> other (1) <Alarmtype> 
        synthesisAlarm (12)  <Polarity> 
        (2) 
        "
	  ::= { pmo6006AlmsynthAlm0 9 }



--- *****************************************************
---     LEAF for the synthAlm2 article
--- *****************************************************
pmo6006AlmsynthAlm2 OBJECT IDENTIFIER ::= { pmo6006AlmOtherNurg 2 }




pmo6006AlmCorrelatOff OBJECT-TYPE
	  SYNTAX EkiOnOff
	  MAX-ACCESS read-only
	  STATUS current
	  DESCRIPTION
        "
        Not Used :This OID, when set,
         indicates that alarm correlation 
        is not being performed. <Condtype> 
        CORRELAT_OFF <Probcause> informationalStatus(1000) 
        <Alarmtype> other (1) <Polarity> 
        (2) 
        "
	  ::= { pmo6006AlmsynthAlm2 4 }



pmo6006AlmConfTableLoad OBJECT-TYPE
	  SYNTAX EkiOnOff
	  MAX-ACCESS read-only
	  STATUS current
	  DESCRIPTION
        "
        PM Configuration Load :This OID 
         is at 1 during the loading of
         configuration tables in the modules 
        RAM. <Condtype> CONF_TABLE_LOAD 
        <Probcause> informationalStatus(1000) 
        <Alarmtype> other (1) <Polarity> 
        (2) 
        "
	  ::= { pmo6006AlmsynthAlm2 3 }



pmo6006AlmInvUpload OBJECT-TYPE
	  SYNTAX EkiOnOff
	  MAX-ACCESS read-only
	  STATUS current
	  DESCRIPTION
        "
        Inventory Upload :This OID is
         at 1 during the uploading of PM 
        inventory information. <Condtype> 
        INV_UPLOAD <Probcause> informationalStatus(1000) 
        <Alarmtype> other (1) <Polarity> 
        (2) 
        "
	  ::= { pmo6006AlmsynthAlm2 2 }



pmo6006AlmConfTableSave OBJECT-TYPE
	  SYNTAX EkiOnOff
	  MAX-ACCESS read-only
	  STATUS current
	  DESCRIPTION
        "
        PM Configuration Save :This OID 
        is at 1 during the saving of a
         new configuration table in the 
        module Flash memory. <Condtype> 
        CONF_TABLE_SAVE <Probcause> informationalStatus(1000) 
        <Alarmtype> other (1) <Polarity> 
        (2) 
        "
	  ::= { pmo6006AlmsynthAlm2 1 }



--- *********************************************************
---     TABLE for the pmo6006AlmsynthAlmPort articles
--- *********************************************************

pmo6006AlmsynthAlmPortTable OBJECT-TYPE
	SYNTAX  SEQUENCE OF Pmo6006AlmsynthAlmPortEntry
	MAX-ACCESS not-accessible
	STATUS current
	DESCRIPTION
        "
        List of pmo6006AlmsynthAlmPort 
        Article
        "
	::= { pmo6006AlmClientCrit 8 }


pmo6006AlmsynthAlmPortEntry OBJECT-TYPE
	SYNTAX Pmo6006AlmsynthAlmPortEntry
	MAX-ACCESS not-accessible
	STATUS current
	DESCRIPTION
        "
        Row definition for the pmo6006AlmsynthAlmPort 
        table
        "
	INDEX   { pmo6006AlmsynthAlmPortIndex }
	::= { pmo6006AlmsynthAlmPortTable 1 }


Pmo6006AlmsynthAlmPortEntry ::=
	SEQUENCE {
	pmo6006AlmsynthAlmPortIndex
		INTEGER,
	pmo6006AlmUpCsfPortn
		EkiOnOff,
	pmo6006AlmFailAccPortn
		EkiOnOff,
	pmo6006AlmSfpDdmAlmPortn
		EkiOnOff,
	pmo6006AlmSfpDdmWarningPortn
		EkiOnOff,
	pmo6006AlmDwCaisPortn
		EkiOnOff,
	pmo6006AlmClientRemoteOosPortn
		EkiOnOff,
	pmo6006AlmClientLocalOosPortn
		EkiOnOff,
	pmo6006AlmDwLsdPortn
		EkiOnOff,
	pmo6006AlmHwFailAccPortn
		EkiOnOff,
	pmo6006AlmDdmAbsentPortn
		EkiOnOff,
	pmo6006AlmSfpAbsentPortn
		EkiOnOff
	}


pmo6006AlmsynthAlmPortIndex OBJECT-TYPE
	SYNTAX  INTEGER(0..128)
	MAX-ACCESS  read-only
	STATUS current
	DESCRIPTION
        "
        Index definition for the pmo6006AlmsynthAlmPort 
        table
        "
	::= { pmo6006AlmsynthAlmPortEntry 1 }


pmo6006AlmUpCsfPortn OBJECT-TYPE
	SYNTAX  EkiOnOff
	MAX-ACCESS read-only
	STATUS current
	DESCRIPTION
        "
        Client Signal Fail Inserted :This 
        OID indicates a CSF has been inserted 
        in the upstream client port. <Help> 
        This status indicates if a Client 
        Signal Fail is currently inserted 
        on the line signal for this client 
        port <Condtype> UP_CSF_1 <Probcause> 
        informationalStatus(1000) <Alarmtype> 
        other (1) <Polarity> (2) 
        "
	::= { pmo6006AlmsynthAlmPortEntry 17 }


pmo6006AlmFailAccPortn OBJECT-TYPE
	SYNTAX  EkiOnOff
	MAX-ACCESS read-only
	STATUS current
	DESCRIPTION
        "
        Client Access Fail :This OID indicates 
        a failure on the Client port <Help> 
        This alarm indicates a failure
         on the Client port <Condtype>
         FAIL_ACC_1 <Probcause> equipmentMalfunction 
        (16) <Alarmtype> synthesisAlarm 
        (12)  <Polarity> (2) 
        "
	::= { pmo6006AlmsynthAlmPortEntry 13 }


pmo6006AlmSfpDdmAlmPortn OBJECT-TYPE
	SYNTAX  EkiOnOff
	MAX-ACCESS read-only
	STATUS current
	DESCRIPTION
        "
        Alarm On Client Trscv DDM :This 
        OID indicates an alarm is being 
        received from the Client Transceiver 
        DDM <Help> This alarm indicates 
        if a DDM Alarm has been detected 
        on the client transceiver <Condtype> 
        SFP_DDM_ALM_1 <Probcause> inputOutputDeviceError 
        (24) <Alarmtype> synthesisAlarm 
        (12)  <Polarity> (2) 
        "
	::= { pmo6006AlmsynthAlmPortEntry 11 }


pmo6006AlmSfpDdmWarningPortn OBJECT-TYPE
	SYNTAX  EkiOnOff
	MAX-ACCESS read-only
	STATUS current
	DESCRIPTION
        "
        Warning On Client Trscv DDM :This 
        OID indicates a warning is being 
        received from the Client Transceiver 
        DDM <Help> This alarm indicates 
        if a DDM Warning has been detected 
        on the client transceiver <Condtype> 
        SFP_DDM_WARNING_1 <Probcause> inputOutputDeviceError 
        (24) <Alarmtype> synthesisAlarm 
        (12)  <Polarity> (2) 
        "
	::= { pmo6006AlmsynthAlmPortEntry 10 }


pmo6006AlmDwCaisPortn OBJECT-TYPE
	SYNTAX  EkiOnOff
	MAX-ACCESS read-only
	STATUS current
	DESCRIPTION
        "
        Client AIS Inserted :This OID
         indicates a CAIS has been inserted 
        on the output client port. <Help> 
        This status indicates if a Client 
        Alarm Indication Signal is currently 
        inserted on the client interface 
        <Condtype> DW_CAIS_1 <Probcause> 
        informationalStatus(1000) <Alarmtype> 
        other (1) <Polarity> (2) 
        "
	::= { pmo6006AlmsynthAlmPortEntry 9 }


pmo6006AlmClientRemoteOosPortn OBJECT-TYPE
	SYNTAX  EkiOnOff
	MAX-ACCESS read-only
	STATUS current
	DESCRIPTION
        "
        Remote Client Port In Service
         :This OID indicates that the remote 
        Client port is In Service (1) or 
        Out of Service (2) <Help> This
         status indicates if the remote 
        client port is in service <Condtype> 
        CLIENT_REMOTE_OOS <Probcause> informationalStatus(1000) 
        <Alarmtype> other (1) <Polarity> 
        (2) 
        "
	::= { pmo6006AlmsynthAlmPortEntry 8 }


pmo6006AlmClientLocalOosPortn OBJECT-TYPE
	SYNTAX  EkiOnOff
	MAX-ACCESS read-only
	STATUS current
	DESCRIPTION
        "
        Local Client Port In Service :This 
        OID indicates that the local Client 
        port is In Service (1) or Out of 
        Service (2) <Help> This status
         indicates if the local client
         port is in service <Condtype>
         CLIENT_LOCAL_OOS <Probcause> informationalStatus(1000) 
        <Alarmtype> other (1) <Polarity> 
        (2) 
        "
	::= { pmo6006AlmsynthAlmPortEntry 7 }


pmo6006AlmDwLsdPortn OBJECT-TYPE
	SYNTAX  EkiOnOff
	MAX-ACCESS read-only
	STATUS current
	DESCRIPTION
        "
        Client SFP Laser Shutdown :This 
        OID indicates the Client transceiver 
        laser is shutdown <Help> This status 
        indicates if the client transceiver 
        laser is shutdown <Condtype> DW_LSD_1 
        <Probcause> other (1) <Alarmtype> 
        equipmentAlarm (5) <Polarity> (2) 
        "
	::= { pmo6006AlmsynthAlmPortEntry 6 }


pmo6006AlmHwFailAccPortn OBJECT-TYPE
	SYNTAX  EkiOnOff
	MAX-ACCESS read-only
	STATUS current
	DESCRIPTION
        "
        Client HW Fail :This OID indicates 
        a failure on client port, most
         probably caused by a HW issue. 
        <Help> This alarm indicates a failure 
        on client port, most probably caused 
        by a HW issue. <Condtype> HW_FAIL_ACC_1 
        <Probcause> equipmentMalfunction 
        (16) <Alarmtype> synthesisAlarm 
        (12)  <Polarity> (2) 
        "
	::= { pmo6006AlmsynthAlmPortEntry 5 }


pmo6006AlmDdmAbsentPortn OBJECT-TYPE
	SYNTAX  EkiOnOff
	MAX-ACCESS read-only
	STATUS current
	DESCRIPTION
        "
        DDM Supported On Client Trscv
         :This OID indicates that the Client 
        transceiver supports the Digital 
        Diagnostic Monitoring function
         <Help> This status indicates if 
        the client transceiver includes 
        the DDM feature <Condtype> DDM_ABSENT_1 
        <Probcause> informationalStatus(1000) 
        <Alarmtype> other (1) <Polarity> 
        (2) 
        "
	::= { pmo6006AlmsynthAlmPortEntry 3 }


pmo6006AlmSfpAbsentPortn OBJECT-TYPE
	SYNTAX  EkiOnOff
	MAX-ACCESS read-only
	STATUS current
	DESCRIPTION
        "
        Client SFP Absent :This OID indicates 
        that the Transceiver is not present 
        in the client port. <Help> This 
        alarm indicates if the client transceiver 
        is not plugged <Condtype> SFP_ABSENT_1 
        <Probcause> inputOutputDeviceError 
        (24) <Alarmtype> equipmentAlarm 
        (5) <Polarity> (2) <Event> ObjectCDINV
        "
	::= { pmo6006AlmsynthAlmPortEntry 2 }


--- *********************************************************
---     TABLE for the pmo6006AlmsynthAlmLine articles
--- *********************************************************

pmo6006AlmsynthAlmLineTable OBJECT-TYPE
	SYNTAX  SEQUENCE OF Pmo6006AlmsynthAlmLineEntry
	MAX-ACCESS not-accessible
	STATUS current
	DESCRIPTION
        "
        List of pmo6006AlmsynthAlmLine 
        Article
        "
	::= { pmo6006AlmLineCrit 24 }


pmo6006AlmsynthAlmLineEntry OBJECT-TYPE
	SYNTAX Pmo6006AlmsynthAlmLineEntry
	MAX-ACCESS not-accessible
	STATUS current
	DESCRIPTION
        "
        Row definition for the pmo6006AlmsynthAlmLine 
        table
        "
	INDEX   { pmo6006AlmsynthAlmLineIndex }
	::= { pmo6006AlmsynthAlmLineTable 1 }


Pmo6006AlmsynthAlmLineEntry ::=
	SEQUENCE {
	pmo6006AlmsynthAlmLineIndex
		INTEGER,
	pmo6006AlmLineFailPortn
		EkiOnOff,
	pmo6006AlmLineDdmAlmPortn
		EkiOnOff,
	pmo6006AlmLineDdmWarningPortn
		EkiOnOff,
	pmo6006AlmUpRdiInsPortn
		EkiOnOff,
	pmo6006AlmLineLocalOosPortn
		EkiOnOff,
	pmo6006AlmLineTxOffPortn
		EkiOnOff,
	pmo6006AlmLineHwFailPortn
		EkiOnOff,
	pmo6006AlmLineDdmAbsentPortn
		EkiOnOff,
	pmo6006AlmLineSfpAbsentPortn
		EkiOnOff
	}


pmo6006AlmsynthAlmLineIndex OBJECT-TYPE
	SYNTAX  INTEGER(0..128)
	MAX-ACCESS  read-only
	STATUS current
	DESCRIPTION
        "
        Index definition for the pmo6006AlmsynthAlmLine 
        table
        "
	::= { pmo6006AlmsynthAlmLineEntry 1 }


pmo6006AlmLineFailPortn OBJECT-TYPE
	SYNTAX  EkiOnOff
	MAX-ACCESS read-only
	STATUS current
	DESCRIPTION
        "
        Line Port Failure :This OID indicates 
        a failure on the line port <Help> 
        This alarm indicates a failure
         on the line port <Condtype> LINE_FAIL 
        <Probcause> equipmentMalfunction 
        (16) <Alarmtype> synthesisAlarm 
        (12)  <Polarity> (2) 
        "
	::= { pmo6006AlmsynthAlmLineEntry 13 }


pmo6006AlmLineDdmAlmPortn OBJECT-TYPE
	SYNTAX  EkiOnOff
	MAX-ACCESS read-only
	STATUS current
	DESCRIPTION
        "
        Alarm On Line Optical Module DDM 
        :This OID indicates an alarm is 
        present coming out of Line transceiver 
        DDM <Help> This alarm indicates 
        if a DDM Alarm has been detected 
        on the line transceiver <Condtype> 
        LINE_DDM_ALM <Probcause> inputOutputDeviceError 
        (24) <Alarmtype> synthesisAlarm 
        (12)  <Polarity> (2) 
        "
	::= { pmo6006AlmsynthAlmLineEntry 11 }


pmo6006AlmLineDdmWarningPortn OBJECT-TYPE
	SYNTAX  EkiOnOff
	MAX-ACCESS read-only
	STATUS current
	DESCRIPTION
        "
        Warning On Line Optical Module 
        DDM :This OID indicates a warning 
        is present coming out of Line transceiver 
        DDM <Help> This alarm indicates 
        if a DDM Warning has been detected 
        on the line transceiver <Condtype> 
        LINE_DDM_WARNING <Probcause> inputOutputDeviceError 
        (24) <Alarmtype> synthesisAlarm 
        (12)  <Polarity> (2) 
        "
	::= { pmo6006AlmsynthAlmLineEntry 10 }


pmo6006AlmUpRdiInsPortn OBJECT-TYPE
	SYNTAX  EkiOnOff
	MAX-ACCESS read-only
	STATUS current
	DESCRIPTION
        "
        MS-RDI/L-RDI Inserted On Line
         :This OID indicates an upstream 
        MS-RDI/L-RDI has been inserted
         in the outgoing 10 Gb/s SDH/SONET 
        signal. <Help> This status indicates 
        if a MS-RDI/L-RDI is currently
         inserted on the line interface. 
        <Condtype> UP_RDI_INS <Probcause> 
        informationalStatus(1000) <Alarmtype> 
        other (1) <Polarity> (2) 
        "
	::= { pmo6006AlmsynthAlmLineEntry 9 }


pmo6006AlmLineLocalOosPortn OBJECT-TYPE
	SYNTAX  EkiOnOff
	MAX-ACCESS read-only
	STATUS current
	DESCRIPTION
        "
        Line Port In Service :This OID 
        indicates that the Line port is 
        In Service (1) of Out or Service 
        (2) <Help> This status indicates 
        if the line port is in service
         <Condtype> LINE_LOCAL_OOS <Probcause> 
        informationalStatus(1000) <Alarmtype> 
        other (1) <Polarity> (2) 
        "
	::= { pmo6006AlmsynthAlmLineEntry 7 }


pmo6006AlmLineTxOffPortn OBJECT-TYPE
	SYNTAX  EkiOnOff
	MAX-ACCESS read-only
	STATUS current
	DESCRIPTION
        "
        Line Optical Module Laser Shutdown 
        :This OID indicates the Line transceiver 
        laser is shutdown <Help> This status 
        indicates if the Line transceiver 
        laser is shutdown <Condtype> LINE_TX_OFF 
        <Probcause> other (1) <Alarmtype> 
        equipmentAlarm (5) <Polarity> (2) 
        "
	::= { pmo6006AlmsynthAlmLineEntry 6 }


pmo6006AlmLineHwFailPortn OBJECT-TYPE
	SYNTAX  EkiOnOff
	MAX-ACCESS read-only
	STATUS current
	DESCRIPTION
        "
        Line Port HW Failure :This OID 
        indicates a failure on line port, 
        most probably caused by a HW issue 
        <Help> This alarm indicates a failure 
        on line port, most probably caused 
        by a HW issue <Condtype> LINE_HW_FAIL 
        <Probcause> equipmentMalfunction 
        (16) <Alarmtype> synthesisAlarm 
        (12)  <Polarity> (2) 
        "
	::= { pmo6006AlmsynthAlmLineEntry 5 }


pmo6006AlmLineDdmAbsentPortn OBJECT-TYPE
	SYNTAX  EkiOnOff
	MAX-ACCESS read-only
	STATUS current
	DESCRIPTION
        "
        Line Optical Module Ready :This 
        OID indicates that the optical
         interface is not operational.
         <Help> This status indicates if 
        the line transceiver has been correctly 
        initialized <Condtype> LINE_DDM_ABSENT_1 
        <Probcause> equipmentMalfunction 
        (16) <Alarmtype> other (1) <Polarity> 
        (2) 
        "
	::= { pmo6006AlmsynthAlmLineEntry 3 }


pmo6006AlmLineSfpAbsentPortn OBJECT-TYPE
	SYNTAX  EkiOnOff
	MAX-ACCESS read-only
	STATUS current
	DESCRIPTION
        "
        Line Optical Module Absent :This 
        OID indicates that the line optical 
        interface is not present. <Help> 
        This alarm indicates if the line 
        transceiver is not plugged <Condtype> 
        LINE_SFP_ABSENT_1 <Probcause> inputOutputDeviceError 
        (24) <Alarmtype> equipmentAlarm 
        (5) <Polarity> (2) <Event> ObjectCDINV
        "
	::= { pmo6006AlmsynthAlmLineEntry 2 }


--- *********************************************************
---     TABLE for the pmo6006AlmclientHostLaneFault articles
--- *********************************************************

pmo6006AlmclientHostLaneFaultTable OBJECT-TYPE
	SYNTAX  SEQUENCE OF Pmo6006AlmclientHostLaneFaultEntry
	MAX-ACCESS not-accessible
	STATUS current
	DESCRIPTION
        "
        List of pmo6006AlmclientHostLaneFault 
        Article
        "
	::= { pmo6006AlmClientUrg 88 }


pmo6006AlmclientHostLaneFaultEntry OBJECT-TYPE
	SYNTAX Pmo6006AlmclientHostLaneFaultEntry
	MAX-ACCESS not-accessible
	STATUS current
	DESCRIPTION
        "
        Row definition for the pmo6006AlmclientHostLaneFault 
        table
        "
	INDEX   { pmo6006AlmclientHostLaneFaultIndex }
	::= { pmo6006AlmclientHostLaneFaultTable 1 }


Pmo6006AlmclientHostLaneFaultEntry ::=
	SEQUENCE {
	pmo6006AlmclientHostLaneFaultIndex
		INTEGER,
	pmo6006AlmClientOdu2eDlckPortn
		EkiOnOff,
	pmo6006AlmClientOdu2eIlckPortn
		EkiOnOff,
	pmo6006AlmClientOdu2eDbdiPortn
		EkiOnOff,
	pmo6006AlmClientOdu2eIbdiPortn
		EkiOnOff,
	pmo6006AlmClientOdu2eDociPortn
		EkiOnOff,
	pmo6006AlmClientOdu2eIociPortn
		EkiOnOff,
	pmo6006AlmClientLaneTxFifoErrorPortn
		EkiOnOff,
	pmo6006AlmClientOdu2eDaisPortn
		EkiOnOff,
	pmo6006AlmClientOdu2eDtimPortn
		EkiOnOff,
	pmo6006AlmClientOdu2eIaisPortn
		EkiOnOff,
	pmo6006AlmClientCsfDetectedPortn
		EkiOnOff,
	pmo6006AlmClientOdu2eDdegPortn
		EkiOnOff,
	pmo6006AlmClientOdu2eDplmPortn
		EkiOnOff,
	pmo6006AlmClientInputLossOfSigPortn
		EkiOnOff,
	pmo6006AlmClientLossOfSyncPortn
		EkiOnOff
	}


pmo6006AlmclientHostLaneFaultIndex OBJECT-TYPE
	SYNTAX  INTEGER(0..128)
	MAX-ACCESS  read-only
	STATUS current
	DESCRIPTION
        "
        Index definition for the pmo6006AlmclientHostLaneFault 
        table
        "
	::= { pmo6006AlmclientHostLaneFaultEntry 1 }


pmo6006AlmClientOdu2eDlckPortn OBJECT-TYPE
	SYNTAX  EkiOnOff
	MAX-ACCESS read-only
	STATUS current
	DESCRIPTION
        "
        ODU2e DLCK :This OID indicates 
        that a Locked Indication has been 
        detected on client port <Help>
          This alarm indicates if a Locked 
        Indication has been detected on 
        the client port <Condtype> CLIENT_ODU2E_DLCK 
        <Probcause> equipmentMalfunction 
        (16) <Alarmtype> equipmentAlarm 
        (5) <Polarity> (2)
        "
	::= { pmo6006AlmclientHostLaneFaultEntry 17 }


pmo6006AlmClientOdu2eIlckPortn OBJECT-TYPE
	SYNTAX  EkiOnOff
	MAX-ACCESS read-only
	STATUS current
	DESCRIPTION
        "
        ODU2e ILCK :This OID indicates 
        that a Locked Indication has been 
        inserted on client port <Help>
          This alarm indicates if a Locked 
        Indication has been inserted on 
        the client port <Condtype> CLIENT_ODU2E_ILCK 
        <Probcause> informationalStatus(1000) 
        <Alarmtype> other (1) <Polarity> 
        (2) 
        "
	::= { pmo6006AlmclientHostLaneFaultEntry 16 }


pmo6006AlmClientOdu2eDbdiPortn OBJECT-TYPE
	SYNTAX  EkiOnOff
	MAX-ACCESS read-only
	STATUS current
	DESCRIPTION
        "
        ODU2e DBDI :This OID indicates 
        that a Backward Defect Indication 
        has been detected on client port<Help> 
         This alarm indicates if a Backward 
        Defect Indication has been detected 
        on the client port <Condtype> CLIENT_ODU2E_DBDI 
        <Probcause> equipmentMalfunction 
        (16) <Alarmtype> equipmentAlarm 
        (5) <Polarity> (2)
        "
	::= { pmo6006AlmclientHostLaneFaultEntry 15 }


pmo6006AlmClientOdu2eIbdiPortn OBJECT-TYPE
	SYNTAX  EkiOnOff
	MAX-ACCESS read-only
	STATUS current
	DESCRIPTION
        "
        ODU2e IBDI :This OID indicates 
        that a Backward Defect Indication 
        has been inserted on client port 
        <Help>  This alarm indicates if 
        a Backward Defect Indication has 
        been inserted on the client port 
        <Condtype> CLIENT_ODU2E_IBDI <Probcause> 
        informationalStatus(1000) <Alarmtype> 
        other (1) <Polarity> (2) 
        "
	::= { pmo6006AlmclientHostLaneFaultEntry 14 }


pmo6006AlmClientOdu2eDociPortn OBJECT-TYPE
	SYNTAX  EkiOnOff
	MAX-ACCESS read-only
	STATUS current
	DESCRIPTION
        "
        ODU2e DOCI :This OID indicates 
        that a Open Connection has been 
        detected on client port <Help>
          This alarm indicates if an Open 
        Connection Indication has been
         detected on the client port <Condtype> 
        CLIENT_ODU2E_DOCI <Probcause> equipmentMalfunction 
        (16) <Alarmtype> equipmentAlarm 
        (5) <Polarity> (2)
        "
	::= { pmo6006AlmclientHostLaneFaultEntry 13 }


pmo6006AlmClientOdu2eIociPortn OBJECT-TYPE
	SYNTAX  EkiOnOff
	MAX-ACCESS read-only
	STATUS current
	DESCRIPTION
        "
        ODU2e IOCI :This OID indicates 
        that an Open Connection has been 
        inserted on client port <Help>
          This alarm indicates if an Open 
        Connection Indication has been
         inserted on the client port <Condtype> 
        CLIENT_ODU2E_IOCI <Probcause> informationalStatus(1000) 
        <Alarmtype> other (1) <Polarity> 
        (2) 
        "
	::= { pmo6006AlmclientHostLaneFaultEntry 12 }


pmo6006AlmClientLaneTxFifoErrorPortn OBJECT-TYPE
	SYNTAX  EkiOnOff
	MAX-ACCESS read-only
	STATUS current
	DESCRIPTION
        "
        Client Tx FIFO Error :This OID 
        indicates a Tx FIFO Error on the 
        Client Trscv <Help> Alarm indicating 
        a Tx FIFO Error on the Client Trscv 
        <Condtype> CLIENT_LANE_TX_FIFO_ERROR 
        <Probcause> receiverFailure (42) 
        <Alarmtype> equipmentAlarm (5)
         <Polarity> (2)
        "
	::= { pmo6006AlmclientHostLaneFaultEntry 11 }


pmo6006AlmClientOdu2eDaisPortn OBJECT-TYPE
	SYNTAX  EkiOnOff
	MAX-ACCESS read-only
	STATUS current
	DESCRIPTION
        "
        ODU2e DAIS :This OID indicates 
        that a Alarm Indication SIgnal
         has been detected on client port<Help> 
         This alarm indicates if an Alarm 
        Indication Signal has been detected 
        on the client port <Condtype> CLIENT_ODU2E_DAIS 
        <Probcause> equipmentMalfunction 
        (16) <Alarmtype> equipmentAlarm 
        (5) <Polarity> (2)
        "
	::= { pmo6006AlmclientHostLaneFaultEntry 10 }


pmo6006AlmClientOdu2eDtimPortn OBJECT-TYPE
	SYNTAX  EkiOnOff
	MAX-ACCESS read-only
	STATUS current
	DESCRIPTION
        "
        ODU2e DTIM :This OID indicates 
        that a Trace Identifier Mismatch 
        has been detected on client port<Help> 
         This alarm indicates if an Trace 
        Identifier Mismatch has been detected 
        on the client port <Condtype> CLIENT_ODU2E_DTIM 
        <Probcause> equipmentMalfunction 
        (16) <Alarmtype> equipmentAlarm 
        (5) <Polarity> (2)
        "
	::= { pmo6006AlmclientHostLaneFaultEntry 9 }


pmo6006AlmClientOdu2eIaisPortn OBJECT-TYPE
	SYNTAX  EkiOnOff
	MAX-ACCESS read-only
	STATUS current
	DESCRIPTION
        "
        ODU2e IAIS :This OID indicates 
        that an Alarm Indication Signal 
        has been inserted on client port 
        <Help>  This alarm indicates if 
        an Alarm Indication Signal has
         been inserted on the client port 
        <Condtype> CLIENT_ODU2E_IAIS <Probcause> 
        informationalStatus(1000) <Alarmtype> 
        other (1) <Polarity> (2) 
        "
	::= { pmo6006AlmclientHostLaneFaultEntry 8 }


pmo6006AlmClientCsfDetectedPortn OBJECT-TYPE
	SYNTAX  EkiOnOff
	MAX-ACCESS read-only
	STATUS current
	DESCRIPTION
        "
        ETH DCSF :This OID indicates that 
        a CSF has been detected on client 
        port in the downstream direction 
          <Help>  This alarm indicates
         if a Client Signal Fail has been 
        detected in the incoming line frame 
        for this client port <Condtype> 
        CLIENT_CSF_DETECTED <Probcause> 
        receiveFailure (41) <Alarmtype> 
        other(1) <Polarity> (2)
        "
	::= { pmo6006AlmclientHostLaneFaultEntry 7 }


pmo6006AlmClientOdu2eDdegPortn OBJECT-TYPE
	SYNTAX  EkiOnOff
	MAX-ACCESS read-only
	STATUS current
	DESCRIPTION
        "
        ODU2e DDEG :This OID indicates 
        that a Signal Degrade has been
         detected on client port<Help>
         Alarm indicating a Signal Degrade 
        upon threshold and confirmation 
        parameters <Condtype> CLIENT_ODU2E_DDEG 
        <Probcause> equipmentMalfunction 
        (16) <Alarmtype> equipmentAlarm 
        (5) <Polarity> (2)
        "
	::= { pmo6006AlmclientHostLaneFaultEntry 6 }


pmo6006AlmClientOdu2eDplmPortn OBJECT-TYPE
	SYNTAX  EkiOnOff
	MAX-ACCESS read-only
	STATUS current
	DESCRIPTION
        "
        ODU2e DPLM :This OID indicates 
        a Payload Mismatch is detected
         on the Client port<Help> Alarm 
        indicating a Payload Mismatch <Condtype> 
        CLIENT_ODU2E_DPLM <Probcause> equipmentMalfunction 
        (16) <Alarmtype> equipmentAlarm 
        (5) <Polarity> (2)
        "
	::= { pmo6006AlmclientHostLaneFaultEntry 4 }


pmo6006AlmClientInputLossOfSigPortn OBJECT-TYPE
	SYNTAX  EkiOnOff
	MAX-ACCESS read-only
	STATUS current
	DESCRIPTION
        "
        Client Input Loss Of Signal :This 
        OID indicates a Loss of Signal
         is detected on the Client Trscv 
        <Help> Alarm indicating a Loss
         of Signal is detected on the Client 
        Trscv <Condtype> CLIENT_INPUT_LOSS_OF_SIG 
        <Probcause> receiveFailure (41) 
        <Alarmtype> physicalViolation (9) 
        <Polarity> (2) 
        "
	::= { pmo6006AlmclientHostLaneFaultEntry 3 }


pmo6006AlmClientLossOfSyncPortn OBJECT-TYPE
	SYNTAX  EkiOnOff
	MAX-ACCESS read-only
	STATUS current
	DESCRIPTION
        "
        Client Frame Alignment Loss :This 
        OID indicates the module is not 
        aligned with the incoming Client 
        signal <Help> Alarm indicating
         the module is not aligned with 
        the incoming client signal <Condtype> 
        CLIENT_LOSS_OF_SYNC <Probcause> 
        receiveFailure (41) <Alarmtype> 
        integrityViolation (7) <Polarity> 
        (2) 
        "
	::= { pmo6006AlmclientHostLaneFaultEntry 2 }


--- *********************************************************
---     TABLE for the pmo6006AlmlineNetworkLaneAlarmWarning1 articles
--- *********************************************************

pmo6006AlmlineNetworkLaneAlarmWarning1Table OBJECT-TYPE
	SYNTAX  SEQUENCE OF Pmo6006AlmlineNetworkLaneAlarmWarning1Entry
	MAX-ACCESS not-accessible
	STATUS current
	DESCRIPTION
        "
        List of pmo6006AlmlineNetworkLaneAlarmWarning1 
        Article
        "
	::= { pmo6006AlmLineUrg 104 }


pmo6006AlmlineNetworkLaneAlarmWarning1Entry OBJECT-TYPE
	SYNTAX Pmo6006AlmlineNetworkLaneAlarmWarning1Entry
	MAX-ACCESS not-accessible
	STATUS current
	DESCRIPTION
        "
        Row definition for the pmo6006AlmlineNetworkLaneAlarmWarning1 
        table
        "
	INDEX   { pmo6006AlmlineNetworkLaneAlarmWarning1Index }
	::= { pmo6006AlmlineNetworkLaneAlarmWarning1Table 1 }


Pmo6006AlmlineNetworkLaneAlarmWarning1Entry ::=
	SEQUENCE {
	pmo6006AlmlineNetworkLaneAlarmWarning1Index
		INTEGER,
	pmo6006AlmLineRxPwrHighAlaPortn
		EkiOnOff,
	pmo6006AlmLineRxPwrLowAlaPortn
		EkiOnOff,
	pmo6006AlmLineTempHighAlaPortn
		EkiOnOff,
	pmo6006AlmLineTempLowAlaPortn
		EkiOnOff,
	pmo6006AlmLineVccHighAlaPortn
		EkiOnOff,
	pmo6006AlmLineVccLowAlaPortn
		EkiOnOff,
	pmo6006AlmLineTxBiasHighAlaPortn
		EkiOnOff,
	pmo6006AlmLineTxBiasLowAlaPortn
		EkiOnOff,
	pmo6006AlmLineTxPwrHighAlaPortn
		EkiOnOff,
	pmo6006AlmLineTxPwrLowAlaPortn
		EkiOnOff
	}


pmo6006AlmlineNetworkLaneAlarmWarning1Index OBJECT-TYPE
	SYNTAX  INTEGER(0..128)
	MAX-ACCESS  read-only
	STATUS current
	DESCRIPTION
        "
        Index definition for the pmo6006AlmlineNetworkLaneAlarmWarning1 
        table
        "
	::= { pmo6006AlmlineNetworkLaneAlarmWarning1Entry 1 }


pmo6006AlmLineRxPwrHighAlaPortn OBJECT-TYPE
	SYNTAX  EkiOnOff
	MAX-ACCESS read-only
	STATUS current
	DESCRIPTION
        "
        Line Trscv Rx Power High :This 
        OID indicates that the Trscv input 
        power of port is higher than the 
        threshold value written in the
         Trscv EEPROM <Help> Alarm indicating 
        that the Trscv input power of port 
        is higher than the threshold value 
        written in the Trscv EEPROM <Condtype> 
        LINE_RX_PWR_HIGH_ALA_1 <Probcause> 
        receiveFailure (41) <Alarmtype> 
        equipmentAlarm (5) <Polarity> (2) 
        "
	::= { pmo6006AlmlineNetworkLaneAlarmWarning1Entry 17 }


pmo6006AlmLineRxPwrLowAlaPortn OBJECT-TYPE
	SYNTAX  EkiOnOff
	MAX-ACCESS read-only
	STATUS current
	DESCRIPTION
        "
        Line Trscv Rx Power Low :This
         OID indicates that the Trscv input 
        power of port is lower than the 
        threshold value written in the
         Trscv EEPROM <Help> Alarm indicating 
        that the Trscv input power of port 
        is lower than the threshold value 
        written in the Trscv EEPROM <Condtype> 
        LINE_RX_PWR_LOW_ALA_1 <Probcause> 
        receiveFailure (41) <Alarmtype> 
        equipmentAlarm (5) <Polarity> (2) 
        "
	::= { pmo6006AlmlineNetworkLaneAlarmWarning1Entry 16 }


pmo6006AlmLineTempHighAlaPortn OBJECT-TYPE
	SYNTAX  EkiOnOff
	MAX-ACCESS read-only
	STATUS current
	DESCRIPTION
        "
        Line Trscv Temp High :This OID 
        indicates that the Trscv temperature 
        of port is higher than the threshold 
        value written in the Trscv EEPROM 
        <Help> Alarm indicating that the 
        Trscv temperature of port is higher 
        than the threshold value written 
        in the Trscv EEPROM <Condtype>
         LINE_TEMP_HIGH_ALA_1 <Probcause> 
        temperatureUnacceptable (51) <Alarmtype> 
        equipmentAlarm (5) <Polarity> (2) 
        "
	::= { pmo6006AlmlineNetworkLaneAlarmWarning1Entry 9 }


pmo6006AlmLineTempLowAlaPortn OBJECT-TYPE
	SYNTAX  EkiOnOff
	MAX-ACCESS read-only
	STATUS current
	DESCRIPTION
        "
        Line Trscv Temp Low :This OID
         indicates that the Trscv temperature 
        of port is lower than the threshold 
        value written in the Trscv EEPROM 
        <Help> Alarm indicating that the 
        Trscv temperature of port is lower 
        than the threshold value written 
        in the Trscv EEPROM <Condtype>
         LINE_TEMP_LOW_ALA_1 <Probcause> 
        temperatureUnacceptable (51) <Alarmtype> 
        equipmentAlarm (5) <Polarity> (2) 
        "
	::= { pmo6006AlmlineNetworkLaneAlarmWarning1Entry 8 }


pmo6006AlmLineVccHighAlaPortn OBJECT-TYPE
	SYNTAX  EkiOnOff
	MAX-ACCESS read-only
	STATUS current
	DESCRIPTION
        "
        Line Trscv Power Supply High :This 
        OID indicates that the Trscv power 
        supply of port is higher than the 
        threshold value written in the
         Trscv EEPROM <Help> Alarm indicating 
        that the Trscv power supply of
         port is higher than the threshold 
        value written in the Trscv EEPROM 
        <Condtype> LINE_VCC_HIGH_ALA_1
         <Probcause> powerProblem (36)
         <Alarmtype> equipmentAlarm (5) 
        <Polarity> (2) 
        "
	::= { pmo6006AlmlineNetworkLaneAlarmWarning1Entry 7 }


pmo6006AlmLineVccLowAlaPortn OBJECT-TYPE
	SYNTAX  EkiOnOff
	MAX-ACCESS read-only
	STATUS current
	DESCRIPTION
        "
        Line Trscv Power Supply Low :This 
        OID indicates that the Trscv power 
        supply of port is lower than the 
        threshold value written in the
         Trscv EEPROM <Help> Alarm indicating 
        that the Trscv power supply of
         port is lower than the threshold 
        value written in the Trscv EEPROM 
        <Condtype> LINE_VCC_LOW_ALA_1 <Probcause> 
        powerProblem (36) <Alarmtype> equipmentAlarm 
        (5) <Polarity> (2) 
        "
	::= { pmo6006AlmlineNetworkLaneAlarmWarning1Entry 6 }


pmo6006AlmLineTxBiasHighAlaPortn OBJECT-TYPE
	SYNTAX  EkiOnOff
	MAX-ACCESS read-only
	STATUS current
	DESCRIPTION
        "
        Line Trscv Bias High :This OID 
        indicates that the Trscv laser
         bias current of port is higher 
        than the threshold value written 
        in the Trscv EEPROM <Help> Alarm 
        indicating that the Trscv laser 
        bias current of port is higher
         than the threshold value written 
        in the Trscv EEPROM <Condtype>
         LINE_TX_BIAS_HIGH_ALA_1 <Probcause> 
        transmitterFailure (56) <Alarmtype> 
        equipmentAlarm (5) <Polarity> (2) 
        "
	::= { pmo6006AlmlineNetworkLaneAlarmWarning1Entry 5 }


pmo6006AlmLineTxBiasLowAlaPortn OBJECT-TYPE
	SYNTAX  EkiOnOff
	MAX-ACCESS read-only
	STATUS current
	DESCRIPTION
        "
        Line Trscv Bias Low :This OID
         indicates that the Trscv laser 
        bias current of port is lower than 
        the threshold value written in
         the Trscv EEPROM <Help> Alarm
         indicating that the Trscv laser 
        bias current of port is lower than 
        the threshold value written in
         the Trscv EEPROM <Condtype> LINE_TX_BIAS_LOW_ALA_1 
        <Probcause> transmitterFailure
         (56) <Alarmtype> equipmentAlarm 
        (5) <Polarity> (2) 
        "
	::= { pmo6006AlmlineNetworkLaneAlarmWarning1Entry 4 }


pmo6006AlmLineTxPwrHighAlaPortn OBJECT-TYPE
	SYNTAX  EkiOnOff
	MAX-ACCESS read-only
	STATUS current
	DESCRIPTION
        "
        Line Trscv Tx Power High :This 
        OID indicates that the Trscv output 
        power of port is higher than the 
        threshold value written in the
         Trscv EEPROM <Help> Alarm indicating 
        that the Trscv output power of
         port is higher than the threshold 
        value written in the Trscv EEPROM 
        <Condtype> LINE_TX_PWR_HIGH_ALA_1 
        <Probcause> transmitterFailure
         (56) <Alarmtype> equipmentAlarm 
        (5) <Polarity> (2) 
        "
	::= { pmo6006AlmlineNetworkLaneAlarmWarning1Entry 3 }


pmo6006AlmLineTxPwrLowAlaPortn OBJECT-TYPE
	SYNTAX  EkiOnOff
	MAX-ACCESS read-only
	STATUS current
	DESCRIPTION
        "
        Line Trscv Tx Power Low :This
         OID indicates that the Trscv output 
        power of port is lower than the 
        threshold value written in the
         Trscv EEPROM <Help> Alarm indicating 
        that the Trscv output power of
         port is lower than the threshold 
        value written in the Trscv EEPROM 
        <Condtype> LINE_TX_PWR_LOW_ALA_1 
        <Probcause> transmitterFailure
         (56) <Alarmtype> equipmentAlarm 
        (5) <Polarity> (2) 
        "
	::= { pmo6006AlmlineNetworkLaneAlarmWarning1Entry 2 }


--- *********************************************************
---     TABLE for the pmo6006AlmlineNetworkLaneAlarmWarning2 articles
--- *********************************************************

pmo6006AlmlineNetworkLaneAlarmWarning2Table OBJECT-TYPE
	SYNTAX  SEQUENCE OF Pmo6006AlmlineNetworkLaneAlarmWarning2Entry
	MAX-ACCESS not-accessible
	STATUS current
	DESCRIPTION
        "
        List of pmo6006AlmlineNetworkLaneAlarmWarning2 
        Article
        "
	::= { pmo6006AlmLineUrg 120 }


pmo6006AlmlineNetworkLaneAlarmWarning2Entry OBJECT-TYPE
	SYNTAX Pmo6006AlmlineNetworkLaneAlarmWarning2Entry
	MAX-ACCESS not-accessible
	STATUS current
	DESCRIPTION
        "
        Row definition for the pmo6006AlmlineNetworkLaneAlarmWarning2 
        table
        "
	INDEX   { pmo6006AlmlineNetworkLaneAlarmWarning2Index }
	::= { pmo6006AlmlineNetworkLaneAlarmWarning2Table 1 }


Pmo6006AlmlineNetworkLaneAlarmWarning2Entry ::=
	SEQUENCE {
	pmo6006AlmlineNetworkLaneAlarmWarning2Index
		INTEGER,
	pmo6006AlmLineRxPwrHighWngPortn
		EkiOnOff,
	pmo6006AlmLineRxPwrLowWngPortn
		EkiOnOff,
	pmo6006AlmLineTempHighWngPortn
		EkiOnOff,
	pmo6006AlmLineTempLowWngPortn
		EkiOnOff,
	pmo6006AlmLineVccHighWngPortn
		EkiOnOff,
	pmo6006AlmLineVccLowWngPortn
		EkiOnOff,
	pmo6006AlmLineTxBiasHighWngPortn
		EkiOnOff,
	pmo6006AlmLineTxBiasLowWngPortn
		EkiOnOff,
	pmo6006AlmLineTxPwrHighWngPortn
		EkiOnOff,
	pmo6006AlmLineTxPwLowWngPortn
		EkiOnOff
	}


pmo6006AlmlineNetworkLaneAlarmWarning2Index OBJECT-TYPE
	SYNTAX  INTEGER(0..128)
	MAX-ACCESS  read-only
	STATUS current
	DESCRIPTION
        "
        Index definition for the pmo6006AlmlineNetworkLaneAlarmWarning2 
        table
        "
	::= { pmo6006AlmlineNetworkLaneAlarmWarning2Entry 1 }


pmo6006AlmLineRxPwrHighWngPortn OBJECT-TYPE
	SYNTAX  EkiOnOff
	MAX-ACCESS read-only
	STATUS current
	DESCRIPTION
        "
        Line Trscv Rx Power High Warning 
        :This OID indicates that the Trscv 
        input power is higher than the
         threshold value written in the 
        Trscv EEPROM <Help> Warning indicating 
        that the Trscv input power is higher 
        than the threshold value written 
        in the Trscv EEPROM <Condtype>
         LINE_RX_PWR_HIGH_WNG_1 <Probcause> 
        receiveFailure (41) <Alarmtype> 
        equipmentAlarm (5) <Polarity> (2) 
        "
	::= { pmo6006AlmlineNetworkLaneAlarmWarning2Entry 17 }


pmo6006AlmLineRxPwrLowWngPortn OBJECT-TYPE
	SYNTAX  EkiOnOff
	MAX-ACCESS read-only
	STATUS current
	DESCRIPTION
        "
        Line Trscv Rx Power Low Warning 
        :This OID indicates that the Trscv 
        input power is lower than the threshold 
        value written in the Trscv EEPROM 
        <Help> Warning indicating that
         the Trscv input power is lower 
        than the threshold value written 
        in the Trscv EEPROM <Condtype>
         LINE_RX_PWR_LOW_WNG_1 <Probcause> 
        receiveFailure (41) <Alarmtype> 
        equipmentAlarm (5) <Polarity> (2) 
        "
	::= { pmo6006AlmlineNetworkLaneAlarmWarning2Entry 16 }


pmo6006AlmLineTempHighWngPortn OBJECT-TYPE
	SYNTAX  EkiOnOff
	MAX-ACCESS read-only
	STATUS current
	DESCRIPTION
        "
        Line Trscv Temp High Warning :This 
        OID indicates that the Trscv temperature 
        is higher than the threshold value 
        written in the Trscv EEPROM <Help> 
        Warning indicating that the Trscv 
        temperature is higher than the
         threshold value written in the 
        Trscv EEPROM <Condtype> LINE_TEMP_HIGH_WNG_1 
        <Probcause> temperatureUnacceptable 
        (51) <Alarmtype> equipmentAlarm 
        (5) <Polarity> (2) 
        "
	::= { pmo6006AlmlineNetworkLaneAlarmWarning2Entry 9 }


pmo6006AlmLineTempLowWngPortn OBJECT-TYPE
	SYNTAX  EkiOnOff
	MAX-ACCESS read-only
	STATUS current
	DESCRIPTION
        "
        Line Trscv Temp Low Warning :This 
        OID indicates that the Trscv temperature 
        is lower than the threshold value 
        written in the Trscv EEPROM <Help> 
        Warning indicating that the Trscv 
        temperature is lower than the threshold 
        value written in the Trscv EEPROM 
        <Condtype> LINE_TEMP_LOW_WNG_1
         <Probcause> temperatureUnacceptable 
        (51) <Alarmtype> equipmentAlarm 
        (5) <Polarity> (2) 
        "
	::= { pmo6006AlmlineNetworkLaneAlarmWarning2Entry 8 }


pmo6006AlmLineVccHighWngPortn OBJECT-TYPE
	SYNTAX  EkiOnOff
	MAX-ACCESS read-only
	STATUS current
	DESCRIPTION
        "
        Line Trscv Power Supply High Warning 
        :This OID indicates that the Trscv 
        power supply is higher than the 
        threshold value written in the
         Trscv EEPROM <Help> Warning indicating 
        that the Trscv power supply is
         higher than the threshold value 
        written in the Trscv EEPROM <Condtype> 
        LINE_VCC_HIGH_WNG_1 <Probcause> 
        powerProblem (36) <Alarmtype> equipmentAlarm 
        (5) <Polarity> (2) 
        "
	::= { pmo6006AlmlineNetworkLaneAlarmWarning2Entry 7 }


pmo6006AlmLineVccLowWngPortn OBJECT-TYPE
	SYNTAX  EkiOnOff
	MAX-ACCESS read-only
	STATUS current
	DESCRIPTION
        "
        Line Trscv Power Supply Low Warning 
        :This OID indicates that the Trscv 
        power supply is lower than the
         threshold value written in the 
        Trscv EEPROM <Help> Warning indicating 
        that the Trscv power supply is
         lower than the threshold value 
        written in the Trscv EEPROM <Condtype> 
        LINE_VCC_LOW_WNG_1 <Probcause>
         powerProblem (36) <Alarmtype>
         equipmentAlarm (5) <Polarity>
         (2) 
        "
	::= { pmo6006AlmlineNetworkLaneAlarmWarning2Entry 6 }


pmo6006AlmLineTxBiasHighWngPortn OBJECT-TYPE
	SYNTAX  EkiOnOff
	MAX-ACCESS read-only
	STATUS current
	DESCRIPTION
        "
        Line Trscv Bias High Warning :This 
        OID indicates that the Trscv laser 
        bias current is higher than the 
        threshold value written in the
         Trscv EEPROM <Help> Warning indicating 
        that the Trscv laser bias current 
        is higher than the threshold value 
        written in the Trscv EEPROM <Condtype> 
        LINE_TX_BIAS_HIGH_WNG_1 <Probcause> 
        transmitterFailure (56) <Alarmtype> 
        equipmentAlarm (5) <Polarity> (2) 
        "
	::= { pmo6006AlmlineNetworkLaneAlarmWarning2Entry 5 }


pmo6006AlmLineTxBiasLowWngPortn OBJECT-TYPE
	SYNTAX  EkiOnOff
	MAX-ACCESS read-only
	STATUS current
	DESCRIPTION
        "
        Line Trscv Bias Low Warning :This 
        OID indicates that the Trscv laser 
        bias current is lower than the
         threshold value written in the 
        Trscv EEPROM <Help> Warning indicating 
        that the Trscv laser bias current 
        is lower than the threshold value 
        written in the Trscv EEPROM <Condtype> 
        LINE_TX_BIAS_LOW_WNG_1 <Probcause> 
        transmitterFailure (56) <Alarmtype> 
        equipmentAlarm (5) <Polarity> (2) 
        "
	::= { pmo6006AlmlineNetworkLaneAlarmWarning2Entry 4 }


pmo6006AlmLineTxPwrHighWngPortn OBJECT-TYPE
	SYNTAX  EkiOnOff
	MAX-ACCESS read-only
	STATUS current
	DESCRIPTION
        "
        Line Trscv Tx Power High Warning 
        :This OID indicates that the Trscv 
        output power is higher than the 
        threshold value written in the
         Trscv EEPROM <Help> Warning indicating 
        that the Trscv output power is
         higher than the threshold value 
        written in the Trscv EEPROM <Condtype> 
        LINE_TX_PWR_HIGH_WNG_1 <Probcause> 
        transmitterFailure (56) <Alarmtype> 
        equipmentAlarm (5) <Polarity> (2) 
        "
	::= { pmo6006AlmlineNetworkLaneAlarmWarning2Entry 3 }


pmo6006AlmLineTxPwLowWngPortn OBJECT-TYPE
	SYNTAX  EkiOnOff
	MAX-ACCESS read-only
	STATUS current
	DESCRIPTION
        "
        Line Trscv Tx Power Low Warning 
        :This OID indicates that the Trscv 
        output power is lower than the
         threshold value written in the 
        Trscv EEPROM <Help> Warning indicating 
        that the Trscv output power is
         lower than the threshold value 
        written in the Trscv EEPROM <Condtype> 
        LINE_TX_PW_LOW_WNG_1 <Probcause> 
        transmitterFailure (56) <Alarmtype> 
        equipmentAlarm (5) <Polarity> (2) 
        "
	::= { pmo6006AlmlineNetworkLaneAlarmWarning2Entry 2 }


--- *********************************************************
---     TABLE for the pmo6006AlmlineHostLaneFault articles
--- *********************************************************

pmo6006AlmlineHostLaneFaultTable OBJECT-TYPE
	SYNTAX  SEQUENCE OF Pmo6006AlmlineHostLaneFaultEntry
	MAX-ACCESS not-accessible
	STATUS current
	DESCRIPTION
        "
        List of pmo6006AlmlineHostLaneFault 
        Article
        "
	::= { pmo6006AlmLineUrg 152 }


pmo6006AlmlineHostLaneFaultEntry OBJECT-TYPE
	SYNTAX Pmo6006AlmlineHostLaneFaultEntry
	MAX-ACCESS not-accessible
	STATUS current
	DESCRIPTION
        "
        Row definition for the pmo6006AlmlineHostLaneFault 
        table
        "
	INDEX   { pmo6006AlmlineHostLaneFaultIndex }
	::= { pmo6006AlmlineHostLaneFaultTable 1 }


Pmo6006AlmlineHostLaneFaultEntry ::=
	SEQUENCE {
	pmo6006AlmlineHostLaneFaultIndex
		INTEGER,
	pmo6006AlmLineOtu2eDlomPortn
		EkiOnOff,
	pmo6006AlmLineOtu2eDssfPortn
		EkiOnOff,
	pmo6006AlmLineOchr2eDlosPPortn
		EkiOnOff,
	pmo6006AlmClientOtu2eDtimPortn
		EkiOnOff,
	pmo6006AlmOtu2eDdegPortn
		EkiOnOff,
	pmo6006AlmLineSmBdiDetectedPortn
		EkiOnOff,
	pmo6006AlmLineSmBdiInsertedPortn
		EkiOnOff,
	pmo6006AlmLineLossOfFramePortn
		EkiOnOff,
	pmo6006AlmLineInputLossOfSignalPortn
		EkiOnOff
	}


pmo6006AlmlineHostLaneFaultIndex OBJECT-TYPE
	SYNTAX  INTEGER(0..128)
	MAX-ACCESS  read-only
	STATUS current
	DESCRIPTION
        "
        Index definition for the pmo6006AlmlineHostLaneFault 
        table
        "
	::= { pmo6006AlmlineHostLaneFaultEntry 1 }


pmo6006AlmLineOtu2eDlomPortn OBJECT-TYPE
	SYNTAX  EkiOnOff
	MAX-ACCESS read-only
	STATUS current
	DESCRIPTION
        "
        OTU2e DLOM :This OID indicates 
        that a Loss Of Multiframe has been 
        detected on line port <Help>  This 
        alarm indicates if a Loss Of Multiframe 
        has been detected on the line port 
        <Condtype> LINE_OTU2E_DLOM <Probcause> 
        equipmentMalfunction (16) <Alarmtype> 
        equipmentAlarm (5) <Polarity> (2)
        "
	::= { pmo6006AlmlineHostLaneFaultEntry 17 }


pmo6006AlmLineOtu2eDssfPortn OBJECT-TYPE
	SYNTAX  EkiOnOff
	MAX-ACCESS read-only
	STATUS current
	DESCRIPTION
        "
        OTU2e DSSF :This OID indicates 
        that a Server Signal failure has 
        been detected on line port <Help> 
         This alarm indicates if a Server 
        Signal Failure has been detected 
        on the line port <Condtype> LINE_OTU2E_DSSF 
        <Probcause> equipmentMalfunction 
        (16) <Alarmtype> equipmentAlarm 
        (5) <Polarity> (2)
        "
	::= { pmo6006AlmlineHostLaneFaultEntry 16 }


pmo6006AlmLineOchr2eDlosPPortn OBJECT-TYPE
	SYNTAX  EkiOnOff
	MAX-ACCESS read-only
	STATUS current
	DESCRIPTION
        "
        Ochr2e - DLOS-P :This OID indicates 
        that a Transmitter failure has
         been detected on line port <Help> 
         This alarm indicates if a Transmitter 
        Failure has been detected on the 
        line port <Condtype> LINE_OCHR2E_DLOS_P 
        <Probcause> equipmentMalfunction 
        (16) <Alarmtype> equipmentAlarm 
        (5) <Polarity> (2)
        "
	::= { pmo6006AlmlineHostLaneFaultEntry 12 }


pmo6006AlmClientOtu2eDtimPortn OBJECT-TYPE
	SYNTAX  EkiOnOff
	MAX-ACCESS read-only
	STATUS current
	DESCRIPTION
        "
        OTU2e DTIM :This OID indicates 
        that a Trace Identifier Mismatch 
        has been detected on line port
         <Help>  This alarm indicates if 
        a Trace Idenifier Mismatch has
         been detected on the line port 
        <Condtype> CLIENT_OTU2E_DTIM <Probcause> 
        equipmentMalfunction (16) <Alarmtype> 
        equipmentAlarm (5) <Polarity> (2)
        "
	::= { pmo6006AlmlineHostLaneFaultEntry 9 }


pmo6006AlmOtu2eDdegPortn OBJECT-TYPE
	SYNTAX  EkiOnOff
	MAX-ACCESS read-only
	STATUS current
	DESCRIPTION
        "
        OTU2e DDEG :This OID indicates 
        that a Signal Degrade has been
         detected on line port <Help> 
         This alarm indicates if a Signal 
        Degrade has been detected upon
         threshold and confirmation parameters 
        on the line port <Condtype> OTU2E_DDEG 
        <Probcause> equipmentMalfunction 
        (16) <Alarmtype> equipmentAlarm 
        (5) <Polarity> (2)
        "
	::= { pmo6006AlmlineHostLaneFaultEntry 8 }


pmo6006AlmLineSmBdiDetectedPortn OBJECT-TYPE
	SYNTAX  EkiOnOff
	MAX-ACCESS read-only
	STATUS current
	DESCRIPTION
        "
        OTU2e DBDI :This OID indicates 
        a SM Backward Defect Indication 
        is detected on the incoming Line 
        signal<Help>  This alarm indicates 
        if a Backward Defect Indication 
        has been detected on the line port 
        <Condtype> LINE_SM_BDI_DETECTED 
        <Probcause> receiveFailure (41) 
        <Alarmtype> integrityViolation
         (7) <Polarity> (2) 
        "
	::= { pmo6006AlmlineHostLaneFaultEntry 5 }


pmo6006AlmLineSmBdiInsertedPortn OBJECT-TYPE
	SYNTAX  EkiOnOff
	MAX-ACCESS read-only
	STATUS current
	DESCRIPTION
        "
        OTU2e IBDI :This OID indicates 
        a SM Backward Defect Indication 
        is inserted on the outgoing Line 
        signal<Help>  This alarm indicates 
        if a Backward Defect Indication 
        has been inserted on the line port 
        <Condtype> LINE_SM_BDI_INSERTED 
        <Probcause> informationalStatus(1000) 
        <Alarmtype> other (1) <Polarity> 
        (2) 
        "
	::= { pmo6006AlmlineHostLaneFaultEntry 4 }


pmo6006AlmLineLossOfFramePortn OBJECT-TYPE
	SYNTAX  EkiOnOff
	MAX-ACCESS read-only
	STATUS current
	DESCRIPTION
        "
        OTU2e - DLOF :This OID indicates 
        the module is not aligned with
         the incoming Line signal<Help> 
         This alarm indicates if a Loss 
        Of Frame has been detected on the 
        line port <Condtype> LINE_LOSS_OF_FRAME 
        <Probcause> receiveFailure (41) 
        <Alarmtype> integrityViolation
         (7) <Polarity> (2) 
        "
	::= { pmo6006AlmlineHostLaneFaultEntry 3 }


pmo6006AlmLineInputLossOfSignalPortn OBJECT-TYPE
	SYNTAX  EkiOnOff
	MAX-ACCESS read-only
	STATUS current
	DESCRIPTION
        "
        OPS2e DLOS-P :This OID indicates 
        a Loss of Signal is detected on 
        the Line Trscv<Help>  This alarm 
        indicates if an Optical Path Break 
        has been detected on the line port 
        <Condtype> LINE_INPUT_LOSS_OF_SIGNAL 
        <Probcause> receiveFailure (41) 
        <Alarmtype> physicalViolation (9) 
        <Polarity> (2) 
        "
	::= { pmo6006AlmlineHostLaneFaultEntry 2 }


--- *********************************************************
---     TABLE for the pmo6006AlmclientSfpAlmDdm articles
--- *********************************************************

pmo6006AlmclientSfpAlmDdmTable OBJECT-TYPE
	SYNTAX  SEQUENCE OF Pmo6006AlmclientSfpAlmDdmEntry
	MAX-ACCESS not-accessible
	STATUS current
	DESCRIPTION
        "
        List of pmo6006AlmclientSfpAlmDdm 
        Article
        "
	::= { pmo6006AlmClientUrg 216 }


pmo6006AlmclientSfpAlmDdmEntry OBJECT-TYPE
	SYNTAX Pmo6006AlmclientSfpAlmDdmEntry
	MAX-ACCESS not-accessible
	STATUS current
	DESCRIPTION
        "
        Row definition for the pmo6006AlmclientSfpAlmDdm 
        table
        "
	INDEX   { pmo6006AlmclientSfpAlmDdmIndex }
	::= { pmo6006AlmclientSfpAlmDdmTable 1 }


Pmo6006AlmclientSfpAlmDdmEntry ::=
	SEQUENCE {
	pmo6006AlmclientSfpAlmDdmIndex
		INTEGER,
	pmo6006AlmClientRxPwrHighAlaPortn
		EkiOnOff,
	pmo6006AlmClientRxPwrLowAlaPortn
		EkiOnOff,
	pmo6006AlmClientTempHighAlaPortn
		EkiOnOff,
	pmo6006AlmClientTempLowAlaPortn
		EkiOnOff,
	pmo6006AlmClientVccHighAlaPortn
		EkiOnOff,
	pmo6006AlmClientVccLowAlaPortn
		EkiOnOff,
	pmo6006AlmClientTxBiasHighAlaPortn
		EkiOnOff,
	pmo6006AlmClientTxBiasLowAlaPortn
		EkiOnOff,
	pmo6006AlmClientTxPwrHighAlaPortn
		EkiOnOff,
	pmo6006AlmClientTxPwrLowAlaPortn
		EkiOnOff
	}


pmo6006AlmclientSfpAlmDdmIndex OBJECT-TYPE
	SYNTAX  INTEGER(0..128)
	MAX-ACCESS  read-only
	STATUS current
	DESCRIPTION
        "
        Index definition for the pmo6006AlmclientSfpAlmDdm 
        table
        "
	::= { pmo6006AlmclientSfpAlmDdmEntry 1 }


pmo6006AlmClientRxPwrHighAlaPortn OBJECT-TYPE
	SYNTAX  EkiOnOff
	MAX-ACCESS read-only
	STATUS current
	DESCRIPTION
        "
        Client Trscv Rx Power High :This 
        OID indicates that the Trscv input 
        power of port is higher than the 
        threshold value written in the
         Trscv EEPROM <Help> Alarm indicating 
        that the Trscv input power of port 
        is higher than the threshold value 
        written in the Trscv EEPROM <Condtype> 
        CLIENT_RX_PWR_HIGH_ALA_1 <Probcause> 
        receiveFailure (41) <Alarmtype> 
        equipmentAlarm (5) <Polarity> (2) 
        "
	::= { pmo6006AlmclientSfpAlmDdmEntry 17 }


pmo6006AlmClientRxPwrLowAlaPortn OBJECT-TYPE
	SYNTAX  EkiOnOff
	MAX-ACCESS read-only
	STATUS current
	DESCRIPTION
        "
        Client Trscv Rx Power Low :This 
        OID indicates that the Trscv input 
        power of port is lower than the 
        threshold value written in the
         Trscv EEPROM <Help> Alarm indicating 
        that the Trscv input power of port 
        is lower than the threshold value 
        written in the Trscv EEPROM <Condtype> 
        CLIENT_RX_PWR_LOW_ALA_1 <Probcause> 
        receiveFailure (41) <Alarmtype> 
        equipmentAlarm (5) <Polarity> (2) 
        "
	::= { pmo6006AlmclientSfpAlmDdmEntry 16 }


pmo6006AlmClientTempHighAlaPortn OBJECT-TYPE
	SYNTAX  EkiOnOff
	MAX-ACCESS read-only
	STATUS current
	DESCRIPTION
        "
        Client Trscv Temp High :This OID 
        indicates that the Trscv temperature 
        of port is higher than the threshold 
        value written in the Trscv EEPROM 
        <Help> Alarm indicating that the 
        Trscv temperature of port is higher 
        than the threshold value written 
        in the Trscv EEPROM <Condtype>
         CLIENT_TEMP_HIGH_ALA_1 <Probcause> 
        temperatureUnacceptable (51) <Alarmtype> 
        equipmentAlarm (5) <Polarity> (2) 
        "
	::= { pmo6006AlmclientSfpAlmDdmEntry 9 }


pmo6006AlmClientTempLowAlaPortn OBJECT-TYPE
	SYNTAX  EkiOnOff
	MAX-ACCESS read-only
	STATUS current
	DESCRIPTION
        "
        Client Trscv Temp Low :This OID 
        indicates that the Trscv temperature 
        of port is lower than the threshold 
        value written in the Trscv EEPROM 
        <Help> Alarm indicating that the 
        Trscv temperature of port is lower 
        than the threshold value written 
        in the Trscv EEPROM <Condtype>
         CLIENT_TEMP_LOW_ALA_1 <Probcause> 
        temperatureUnacceptable (51) <Alarmtype> 
        equipmentAlarm (5) <Polarity> (2) 
        "
	::= { pmo6006AlmclientSfpAlmDdmEntry 8 }


pmo6006AlmClientVccHighAlaPortn OBJECT-TYPE
	SYNTAX  EkiOnOff
	MAX-ACCESS read-only
	STATUS current
	DESCRIPTION
        "
        Client Trscv Power Supply High 
        :This OID indicates that the Trscv 
        power supply of port is higher
         than the threshold value written 
        in the Trscv EEPROM <Help> Alarm 
        indicating that the Trscv power 
        supply of port is higher than the 
        threshold value written in the
         Trscv EEPROM <Condtype> CLIENT_VCC_HIGH_ALA_1 
        <Probcause> powerProblem (36) <Alarmtype> 
        equipmentAlarm (5) <Polarity> (2) 
        "
	::= { pmo6006AlmclientSfpAlmDdmEntry 7 }


pmo6006AlmClientVccLowAlaPortn OBJECT-TYPE
	SYNTAX  EkiOnOff
	MAX-ACCESS read-only
	STATUS current
	DESCRIPTION
        "
        Client Trscv Power Supply Low
         :This OID indicates that the Trscv 
        power supply of port is lower than 
        the threshold value written in
         the Trscv EEPROM <Help> Alarm
         indicating that the Trscv power 
        supply of port is lower than the 
        threshold value written in the
         Trscv EEPROM <Condtype> CLIENT_VCC_LOW_ALA_1 
        <Probcause> powerProblem (36) <Alarmtype> 
        equipmentAlarm (5) <Polarity> (2) 
        "
	::= { pmo6006AlmclientSfpAlmDdmEntry 6 }


pmo6006AlmClientTxBiasHighAlaPortn OBJECT-TYPE
	SYNTAX  EkiOnOff
	MAX-ACCESS read-only
	STATUS current
	DESCRIPTION
        "
        Client Trscv Bias High :This OID 
        indicates that the Trscv laser
         bias current of port is higher 
        than the threshold value written 
        in the Trscv EEPROM <Help> Alarm 
        indicating that the Trscv laser 
        bias current of port is higher
         than the threshold value written 
        in the Trscv EEPROM <Condtype>
         CLIENT_TX_BIAS_HIGH_ALA_1 <Probcause> 
        transmitterFailure (56) <Alarmtype> 
        equipmentAlarm (5) <Polarity> (2) 
        "
	::= { pmo6006AlmclientSfpAlmDdmEntry 5 }


pmo6006AlmClientTxBiasLowAlaPortn OBJECT-TYPE
	SYNTAX  EkiOnOff
	MAX-ACCESS read-only
	STATUS current
	DESCRIPTION
        "
        Client Trscv Bias Low :This OID 
        indicates that the Trscv laser
         bias current of port is lower
         than the threshold value written 
        in the Trscv EEPROM <Help> Alarm 
        indicating that the Trscv laser 
        bias current of port is lower than 
        the threshold value written in
         the Trscv EEPROM <Condtype> CLIENT_TX_BIAS_LOW_ALA_1 
        <Probcause> transmitterFailure
         (56) <Alarmtype> equipmentAlarm 
        (5) <Polarity> (2) 
        "
	::= { pmo6006AlmclientSfpAlmDdmEntry 4 }


pmo6006AlmClientTxPwrHighAlaPortn OBJECT-TYPE
	SYNTAX  EkiOnOff
	MAX-ACCESS read-only
	STATUS current
	DESCRIPTION
        "
        Client Trscv Tx Power High :This 
        OID indicates that the Trscv output 
        power of port is higher than the 
        threshold value written in the
         Trscv EEPROM <Help> Alarm indicating 
        that the Trscv output power of
         port is higher than the threshold 
        value written in the Trscv EEPROM 
        <Condtype> CLIENT_TX_PWR_HIGH_ALA_1 
        <Probcause> transmitterFailure
         (56) <Alarmtype> equipmentAlarm 
        (5) <Polarity> (2) 
        "
	::= { pmo6006AlmclientSfpAlmDdmEntry 3 }


pmo6006AlmClientTxPwrLowAlaPortn OBJECT-TYPE
	SYNTAX  EkiOnOff
	MAX-ACCESS read-only
	STATUS current
	DESCRIPTION
        "
        Client Trscv Tx Power Low :This 
        OID indicates that the Trscv output 
        power of port is lower than the 
        threshold value written in the
         Trscv EEPROM <Help> Alarm indicating 
        that the Trscv output power of
         port is lower than the threshold 
        value written in the Trscv EEPROM 
        <Condtype> CLIENT_TX_PWR_LOW_ALA_1 
        <Probcause> transmitterFailure
         (56) <Alarmtype> equipmentAlarm 
        (5) <Polarity> (2) 
        "
	::= { pmo6006AlmclientSfpAlmDdmEntry 2 }


--- *********************************************************
---     TABLE for the pmo6006AlmclientSfpWarnDdm articles
--- *********************************************************

pmo6006AlmclientSfpWarnDdmTable OBJECT-TYPE
	SYNTAX  SEQUENCE OF Pmo6006AlmclientSfpWarnDdmEntry
	MAX-ACCESS not-accessible
	STATUS current
	DESCRIPTION
        "
        List of pmo6006AlmclientSfpWarnDdm 
        Article
        "
	::= { pmo6006AlmClientNurg 232 }


pmo6006AlmclientSfpWarnDdmEntry OBJECT-TYPE
	SYNTAX Pmo6006AlmclientSfpWarnDdmEntry
	MAX-ACCESS not-accessible
	STATUS current
	DESCRIPTION
        "
        Row definition for the pmo6006AlmclientSfpWarnDdm 
        table
        "
	INDEX   { pmo6006AlmclientSfpWarnDdmIndex }
	::= { pmo6006AlmclientSfpWarnDdmTable 1 }


Pmo6006AlmclientSfpWarnDdmEntry ::=
	SEQUENCE {
	pmo6006AlmclientSfpWarnDdmIndex
		INTEGER,
	pmo6006AlmClientRxPwrHighWngPortn
		EkiOnOff,
	pmo6006AlmClientRxPwrLowWngPortn
		EkiOnOff,
	pmo6006AlmClientTempHighWngPortn
		EkiOnOff,
	pmo6006AlmClientTempLowWngPortn
		EkiOnOff,
	pmo6006AlmClientVccHighWngPortn
		EkiOnOff,
	pmo6006AlmClientVccLowWngPortn
		EkiOnOff,
	pmo6006AlmClientTxBiasHighWngPortn
		EkiOnOff,
	pmo6006AlmClientTxBiasLowWngPortn
		EkiOnOff,
	pmo6006AlmClientTxPwrHighWngPortn
		EkiOnOff,
	pmo6006AlmClientTxPwLowWngPortn
		EkiOnOff
	}


pmo6006AlmclientSfpWarnDdmIndex OBJECT-TYPE
	SYNTAX  INTEGER(0..128)
	MAX-ACCESS  read-only
	STATUS current
	DESCRIPTION
        "
        Index definition for the pmo6006AlmclientSfpWarnDdm 
        table
        "
	::= { pmo6006AlmclientSfpWarnDdmEntry 1 }


pmo6006AlmClientRxPwrHighWngPortn OBJECT-TYPE
	SYNTAX  EkiOnOff
	MAX-ACCESS read-only
	STATUS current
	DESCRIPTION
        "
        Client Trscv Rx Power High Warning 
        :This OID indicates that the Trscv 
        input power is higher than the
         threshold value written in the 
        Trscv EEPROM <Help> Warning indicating 
        that the Trscv input power is higher 
        than the threshold value written 
        in the Trscv EEPROM <Condtype>
         CLIENT_RX_PWR_HIGH_WNG_1 <Probcause> 
        receiveFailure (41) <Alarmtype> 
        equipmentAlarm (5) <Polarity> (2) 
        "
	::= { pmo6006AlmclientSfpWarnDdmEntry 17 }


pmo6006AlmClientRxPwrLowWngPortn OBJECT-TYPE
	SYNTAX  EkiOnOff
	MAX-ACCESS read-only
	STATUS current
	DESCRIPTION
        "
        Client Trscv Rx Power Low Warning 
        :This OID indicates that the Trscv 
        input power is lower than the threshold 
        value written in the Trscv EEPROM 
        <Help> Warning indicating that
         the Trscv input power is lower 
        than the threshold value written 
        in the Trscv EEPROM <Condtype>
         CLIENT_RX_PWR_LOW_WNG_1 <Probcause> 
        receiveFailure (41) <Alarmtype> 
        equipmentAlarm (5) <Polarity> (2) 
        "
	::= { pmo6006AlmclientSfpWarnDdmEntry 16 }


pmo6006AlmClientTempHighWngPortn OBJECT-TYPE
	SYNTAX  EkiOnOff
	MAX-ACCESS read-only
	STATUS current
	DESCRIPTION
        "
        Client Trscv Temp High Warning 
        :This OID indicates that the Trscv 
        temperature is higher than the
         threshold value written in the 
        Trscv EEPROM <Help> Warning indicating 
        that the Trscv temperature is higher 
        than the threshold value written 
        in the Trscv EEPROM <Condtype>
         CLIENT_TEMP_HIGH_WNG_1 <Probcause> 
        temperatureUnacceptable (51) <Alarmtype> 
        equipmentAlarm (5) <Polarity> (2) 
        "
	::= { pmo6006AlmclientSfpWarnDdmEntry 9 }


pmo6006AlmClientTempLowWngPortn OBJECT-TYPE
	SYNTAX  EkiOnOff
	MAX-ACCESS read-only
	STATUS current
	DESCRIPTION
        "
        Client Trscv Temp Low Warning
         :This OID indicates that the Trscv 
        temperature is lower than the threshold 
        value written in the Trscv EEPROM 
        <Help> Warning indicating that
         the Trscv temperature is lower 
        than the threshold value written 
        in the Trscv EEPROM <Condtype>
         CLIENT_TEMP_LOW_WNG_1 <Probcause> 
        temperatureUnacceptable (51) <Alarmtype> 
        equipmentAlarm (5) <Polarity> (2) 
        "
	::= { pmo6006AlmclientSfpWarnDdmEntry 8 }


pmo6006AlmClientVccHighWngPortn OBJECT-TYPE
	SYNTAX  EkiOnOff
	MAX-ACCESS read-only
	STATUS current
	DESCRIPTION
        "
        Client Trscv Power Supply High 
        Warning :This OID indicates that 
        the Trscv power supply is higher 
        than the threshold value written 
        in the Trscv EEPROM <Help> Warning 
        indicating that the Trscv power 
        supply is higher than the threshold 
        value written in the Trscv EEPROM 
        <Condtype> CLIENT_VCC_HIGH_WNG_1 
        <Probcause> powerProblem (36) <Alarmtype> 
        equipmentAlarm (5) <Polarity> (2) 
        "
	::= { pmo6006AlmclientSfpWarnDdmEntry 7 }


pmo6006AlmClientVccLowWngPortn OBJECT-TYPE
	SYNTAX  EkiOnOff
	MAX-ACCESS read-only
	STATUS current
	DESCRIPTION
        "
        Client Trscv Power Supply Low
         Warning :This OID indicates that 
        the Trscv power supply is lower 
        than the threshold value written 
        in the Trscv EEPROM <Help> Warning 
        indicating that the Trscv power 
        supply is lower than the threshold 
        value written in the Trscv EEPROM 
        <Condtype> CLIENT_VCC_LOW_WNG_1 
        <Probcause> powerProblem (36) <Alarmtype> 
        equipmentAlarm (5) <Polarity> (2) 
        "
	::= { pmo6006AlmclientSfpWarnDdmEntry 6 }


pmo6006AlmClientTxBiasHighWngPortn OBJECT-TYPE
	SYNTAX  EkiOnOff
	MAX-ACCESS read-only
	STATUS current
	DESCRIPTION
        "
        Client Trscv Bias High Warning 
        :This OID indicates that the Trscv 
        laser bias current is higher than 
        the threshold value written in
         the Trscv EEPROM <Help> Warning 
        indicating that the Trscv laser 
        bias current is higher than the 
        threshold value written in the
         Trscv EEPROM <Condtype> CLIENT_TX_BIAS_HIGH_WNG_1 
        <Probcause> transmitterFailure
         (56) <Alarmtype> equipmentAlarm 
        (5) <Polarity> (2) 
        "
	::= { pmo6006AlmclientSfpWarnDdmEntry 5 }


pmo6006AlmClientTxBiasLowWngPortn OBJECT-TYPE
	SYNTAX  EkiOnOff
	MAX-ACCESS read-only
	STATUS current
	DESCRIPTION
        "
        Client Trscv Bias Low Warning
         :This OID indicates that the Trscv 
        laser bias current is lower than 
        the threshold value written in
         the Trscv EEPROM <Help> Warning 
        indicating that the Trscv laser 
        bias current is lower than the
         threshold value written in the 
        Trscv EEPROM <Condtype> CLIENT_TX_BIAS_LOW_WNG_1 
        <Probcause> transmitterFailure
         (56) <Alarmtype> equipmentAlarm 
        (5) <Polarity> (2) 
        "
	::= { pmo6006AlmclientSfpWarnDdmEntry 4 }


pmo6006AlmClientTxPwrHighWngPortn OBJECT-TYPE
	SYNTAX  EkiOnOff
	MAX-ACCESS read-only
	STATUS current
	DESCRIPTION
        "
        Client Trscv Tx Power High Warning 
        :This OID indicates that the Trscv 
        output power is higher than the 
        threshold value written in the
         Trscv EEPROM <Help> Warning indicating 
        that the Trscv output power is
         higher than the threshold value 
        written in the Trscv EEPROM <Condtype> 
        CLIENT_TX_PWR_HIGH_WNG_1 <Probcause> 
        transmitterFailure (56) <Alarmtype> 
        equipmentAlarm (5) <Polarity> (2) 
        "
	::= { pmo6006AlmclientSfpWarnDdmEntry 3 }


pmo6006AlmClientTxPwLowWngPortn OBJECT-TYPE
	SYNTAX  EkiOnOff
	MAX-ACCESS read-only
	STATUS current
	DESCRIPTION
        "
        Client Trscv Tx Power Low Warning 
        :This OID indicates that the Trscv 
        output power is lower than the
         threshold value written in the 
        Trscv EEPROM <Help> Warning indicating 
        that the Trscv output power is
         lower than the threshold value 
        written in the Trscv EEPROM <Condtype> 
        CLIENT_TX_PW_LOW_WNG_1 <Probcause> 
        transmitterFailure (56) <Alarmtype> 
        equipmentAlarm (5) <Polarity> (2) 
        "
	::= { pmo6006AlmclientSfpWarnDdmEntry 2 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pmo6006CtrlconfMgnt1 OBJECT IDENTIFIER ::= { pmo6006CtrlOther 1 }




pmo6006CtrlConf2Clear1 OBJECT-TYPE
	  SYNTAX EkiOnOff
	  MAX-ACCESS read-write
	  STATUS current
	  DESCRIPTION
        "
        Clear Configuration Tables :This 
        OID clears the configuration tables 
        from configuration2 in the flash. 
         <Help>  This control restores
         the default configuration of the 
        module
        "
	  ::= { pmo6006CtrlconfMgnt1 14 }



pmo6006CtrlConf2Flash1 OBJECT-TYPE
	  SYNTAX EkiOnOff
	  MAX-ACCESS read-write
	  STATUS current
	  DESCRIPTION
        "
        Write Configuration Tables :This 
        OID saves the current configuration 
        of the PM as configuration2 in
         the flash.  <Help>  This control 
        saves the customer configuration 
        on the module
        "
	  ::= { pmo6006CtrlconfMgnt1 10 }



pmo6006CtrlConf2Load1 OBJECT-TYPE
	  SYNTAX EkiOnOff
	  MAX-ACCESS read-write
	  STATUS current
	  DESCRIPTION
        "
        Load Configuration Tables Set
         Nb 2 :When set this OID enables 
        loading from flash configuration2 
        into the PM.
        "
	  ::= { pmo6006CtrlconfMgnt1 2 }



pmo6006CtrlConf1Load1 OBJECT-TYPE
	  SYNTAX EkiOnOff
	  MAX-ACCESS read-write
	  STATUS current
	  DESCRIPTION
        "
        Load Configuration Tables Set
         Nb 1 :When set this OID enables 
        loading from flash configuration1 
        into the PM.
        "
	  ::= { pmo6006CtrlconfMgnt1 1 }



--- *****************************************************
---     LEAF for the synth4 article
--- *****************************************************
pmo6006Ctrlsynth4 OBJECT IDENTIFIER ::= { pmo6006CtrlOther 4 }




pmo6006CtrlCorrelatOff OBJECT-TYPE
	  SYNTAX EkiOnOff
	  MAX-ACCESS read-write
	  STATUS current
	  DESCRIPTION
        "
        Disable Alarm Correlation :This 
        OID disables the alarm correlation 
        in the PM.
        "
	  ::= { pmo6006Ctrlsynth4 2 }



pmo6006CtrlCorrelatOn OBJECT-TYPE
	  SYNTAX EkiOnOff
	  MAX-ACCESS read-write
	  STATUS current
	  DESCRIPTION
        "
        Enable Alarm Correlation :This 
        OID enables the alarm correlation 
        in the PM.
        "
	  ::= { pmo6006Ctrlsynth4 1 }



--- *****************************************************
---     LEAF for the swMgnt article
--- *****************************************************
pmo6006CtrlswMgnt OBJECT IDENTIFIER ::= { pmo6006CtrlOther 5 }




pmo6006CtrlLoadSwBank2 OBJECT-TYPE
	  SYNTAX EkiOnOff
	  MAX-ACCESS read-write
	  STATUS current
	  DESCRIPTION
        "
        Set Software Nb 2 As Active :This 
        OID, when set, loads the SW from 
        bank2 into the PM. It must be followed 
        by a reset.  <Help>  This controls 
        selects the second SW bank as the 
        active bank for the next module 
        reset
        "
	  ::= { pmo6006CtrlswMgnt 6 }



pmo6006CtrlLoadSwBank1 OBJECT-TYPE
	  SYNTAX EkiOnOff
	  MAX-ACCESS read-write
	  STATUS current
	  DESCRIPTION
        "
        Set Software Nb 1 As Active :This 
        OID, when set, loads the SW from 
        bank1 into the PM. It must be followed 
        by a reset.  <Help>  This controls 
        selects the first SW bank as the 
        active bank for the next module 
        reset
        "
	  ::= { pmo6006CtrlswMgnt 5 }



pmo6006CtrlWarmReset OBJECT-TYPE
	  SYNTAX EkiOnOff
	  MAX-ACCESS read-write
	  STATUS current
	  DESCRIPTION
        "
        PM Warm Reset :This OID, when
         set, causes a warm reset of the 
        PM. This reset is not traffic affecting, 
        and the configuration of PM remains 
        unchanged.  <Help>  This control 
        initiates a warm reset of the module. 
        "
	  ::= { pmo6006CtrlswMgnt 3 }



pmo6006CtrlColdReset OBJECT-TYPE
	  SYNTAX EkiOnOff
	  MAX-ACCESS read-write
	  STATUS current
	  DESCRIPTION
        "
        PM Cold Reset :This OID, when
         set, causes a cold reset of the 
        PM. This reset is traffic affecting, 
        and the configuration of PM is
         reloaded on start-up.  <Help>
          This control initiates a cold 
        reset of the module. 
        "
	  ::= { pmo6006CtrlswMgnt 2 }



--- *****************************************************
---     LEAF for the gwMgnt article
--- *****************************************************
pmo6006CtrlgwMgnt OBJECT IDENTIFIER ::= { pmo6006CtrlOther 6 }




pmo6006CtrlLoadGwBank4 OBJECT-TYPE
	  SYNTAX EkiOnOff
	  MAX-ACCESS read-write
	  STATUS current
	  DESCRIPTION
        "
        Set Gateware Nb 4 As Active :This 
        OID, when set, loads the GW from 
        bank4 (Flash) into the PM. It is 
        followed by an automatic gateware 
        cold reset.
        "
	  ::= { pmo6006CtrlgwMgnt 8 }



pmo6006CtrlLoadGwBank3 OBJECT-TYPE
	  SYNTAX EkiOnOff
	  MAX-ACCESS read-write
	  STATUS current
	  DESCRIPTION
        "
        Set Gateware Nb 3 As Active :This 
        OID, when set, loads the GW from 
        bank3 (Flash) into the PM. It is 
        followed by an automatic gateware 
        cold reset.  <Help>  This controls 
        initiates a cold reset of the module 
        and select the third GW bank as 
        the active bank
        "
	  ::= { pmo6006CtrlgwMgnt 7 }



pmo6006CtrlLoadGwBank2 OBJECT-TYPE
	  SYNTAX EkiOnOff
	  MAX-ACCESS read-write
	  STATUS current
	  DESCRIPTION
        "
        Set Gateware Nb 2 As Active :This 
        OID, when set, loads the GW from 
        bank2 (Flash) into the PM. It is 
        followed by an automatic gateware 
        cold reset.
        "
	  ::= { pmo6006CtrlgwMgnt 6 }



pmo6006CtrlLoadGwBank1 OBJECT-TYPE
	  SYNTAX EkiOnOff
	  MAX-ACCESS read-write
	  STATUS current
	  DESCRIPTION
        "
        Set Gateware Nb 1 As Active :This 
        OID, when set, loads the GW from 
        bank1 (Flash) into the PM. It is 
        followed by an automatic gateware 
        cold reset.  <Help>  This controls 
        initiates a cold reset of the module 
        and select the first GW bank as 
        the active bank
        "
	  ::= { pmo6006CtrlgwMgnt 5 }



pmo6006CtrlCurrentGwReset OBJECT-TYPE
	  SYNTAX EkiOnOff
	  MAX-ACCESS read-write
	  STATUS current
	  DESCRIPTION
        "
        Active Gateware Reset :This OID, 
        when set, resets the active gateware. 
        It is traffic affecting.
        "
	  ::= { pmo6006CtrlgwMgnt 1 }



--- *********************************************************
---     TABLE for the pmo6006CtrlaccessLoop articles
--- *********************************************************

pmo6006CtrlaccessLoopTable OBJECT-TYPE
	SYNTAX  SEQUENCE OF Pmo6006CtrlaccessLoopEntry
	MAX-ACCESS not-accessible
	STATUS current
	DESCRIPTION
        "
        List of pmo6006CtrlaccessLoop
         Article
        "
	::= { pmo6006CtrlClient 16 }


pmo6006CtrlaccessLoopEntry OBJECT-TYPE
	SYNTAX Pmo6006CtrlaccessLoopEntry
	MAX-ACCESS not-accessible
	STATUS current
	DESCRIPTION
        "
        Row definition for the pmo6006CtrlaccessLoop 
        table
        "
	INDEX   { pmo6006CtrlaccessLoopIndex }
	::= { pmo6006CtrlaccessLoopTable 1 }


Pmo6006CtrlaccessLoopEntry ::=
	SEQUENCE {
	pmo6006CtrlaccessLoopIndex
		INTEGER,
	pmo6006CtrlaccessLoopPortn
		EkiState
	}


pmo6006CtrlaccessLoopIndex OBJECT-TYPE
	SYNTAX  INTEGER(0..128)
	MAX-ACCESS  read-only
	STATUS current
	DESCRIPTION
        "
        Index definition for the pmo6006CtrlaccessLoop 
        table
        "
	::= { pmo6006CtrlaccessLoopEntry 1 }


pmo6006CtrlaccessLoopPortn OBJECT-TYPE
	SYNTAX  EkiState
	MAX-ACCESS read-write
	STATUS current
	DESCRIPTION
        "
        Client Facility Loopback :This 
        OID, when set at '1' puts the client 
        port in loopback, looping the received 
        10 Gb/s signal on the transmit
         10 Gb/s output.  <Help> This control 
        enables the Out Loopback on the 
        client port, looping the client 
        input signal on the client output
        "
	::= { pmo6006CtrlaccessLoopEntry 2 }


--- *********************************************************
---     TABLE for the pmo6006CtrlclientLoopToLine articles
--- *********************************************************

pmo6006CtrlclientLoopToLineTable OBJECT-TYPE
	SYNTAX  SEQUENCE OF Pmo6006CtrlclientLoopToLineEntry
	MAX-ACCESS not-accessible
	STATUS current
	DESCRIPTION
        "
        List of pmo6006CtrlclientLoopToLine 
        Article
        "
	::= { pmo6006CtrlClient 17 }


pmo6006CtrlclientLoopToLineEntry OBJECT-TYPE
	SYNTAX Pmo6006CtrlclientLoopToLineEntry
	MAX-ACCESS not-accessible
	STATUS current
	DESCRIPTION
        "
        Row definition for the pmo6006CtrlclientLoopToLine 
        table
        "
	INDEX   { pmo6006CtrlclientLoopToLineIndex }
	::= { pmo6006CtrlclientLoopToLineTable 1 }


Pmo6006CtrlclientLoopToLineEntry ::=
	SEQUENCE {
	pmo6006CtrlclientLoopToLineIndex
		INTEGER,
	pmo6006CtrlclientLoopToLinePortn
		EkiState
	}


pmo6006CtrlclientLoopToLineIndex OBJECT-TYPE
	SYNTAX  INTEGER(0..128)
	MAX-ACCESS  read-only
	STATUS current
	DESCRIPTION
        "
        Index definition for the pmo6006CtrlclientLoopToLine 
        table
        "
	::= { pmo6006CtrlclientLoopToLineEntry 1 }


pmo6006CtrlclientLoopToLinePortn OBJECT-TYPE
	SYNTAX  EkiState
	MAX-ACCESS read-write
	STATUS current
	DESCRIPTION
        "
        Client Terminal Loopback :This 
        OID, when set, puts the client
         port in loop back, looping the 
        10 Gb/s output signal on the 10 
        Gb/s input.<Help> This control
         enables the In Loopback on the 
        client port, looping the client 
        output signal on the client input
        "
	::= { pmo6006CtrlclientLoopToLineEntry 2 }


--- *********************************************************
---     TABLE for the pmo6006CtrlcsfUpIns articles
--- *********************************************************

pmo6006CtrlcsfUpInsTable OBJECT-TYPE
	SYNTAX  SEQUENCE OF Pmo6006CtrlcsfUpInsEntry
	MAX-ACCESS not-accessible
	STATUS current
	DESCRIPTION
        "
        List of pmo6006CtrlcsfUpIns Article
        "
	::= { pmo6006CtrlClient 21 }


pmo6006CtrlcsfUpInsEntry OBJECT-TYPE
	SYNTAX Pmo6006CtrlcsfUpInsEntry
	MAX-ACCESS not-accessible
	STATUS current
	DESCRIPTION
        "
        Row definition for the pmo6006CtrlcsfUpIns 
        table
        "
	INDEX   { pmo6006CtrlcsfUpInsIndex }
	::= { pmo6006CtrlcsfUpInsTable 1 }


Pmo6006CtrlcsfUpInsEntry ::=
	SEQUENCE {
	pmo6006CtrlcsfUpInsIndex
		INTEGER,
	pmo6006CtrlcsfUpInsPortn
		EkiState
	}


pmo6006CtrlcsfUpInsIndex OBJECT-TYPE
	SYNTAX  INTEGER(0..128)
	MAX-ACCESS  read-only
	STATUS current
	DESCRIPTION
        "
        Index definition for the pmo6006CtrlcsfUpIns 
        table
        "
	::= { pmo6006CtrlcsfUpInsEntry 1 }


pmo6006CtrlcsfUpInsPortn OBJECT-TYPE
	SYNTAX  EkiState
	MAX-ACCESS read-write
	STATUS current
	DESCRIPTION
        "
        Client Signal Fail Insertion :This 
        OID, when set, inserts  a client 
        signal fail in the upstream client 
        Port.  <Help>  This control inserts 
        a Client Signal Fail for the client 
        port
        "
	::= { pmo6006CtrlcsfUpInsEntry 2 }


--- *********************************************************
---     TABLE for the pmo6006CtrlcaisDwIns articles
--- *********************************************************

pmo6006CtrlcaisDwInsTable OBJECT-TYPE
	SYNTAX  SEQUENCE OF Pmo6006CtrlcaisDwInsEntry
	MAX-ACCESS not-accessible
	STATUS current
	DESCRIPTION
        "
        List of pmo6006CtrlcaisDwIns Article
        "
	::= { pmo6006CtrlClient 22 }


pmo6006CtrlcaisDwInsEntry OBJECT-TYPE
	SYNTAX Pmo6006CtrlcaisDwInsEntry
	MAX-ACCESS not-accessible
	STATUS current
	DESCRIPTION
        "
        Row definition for the pmo6006CtrlcaisDwIns 
        table
        "
	INDEX   { pmo6006CtrlcaisDwInsIndex }
	::= { pmo6006CtrlcaisDwInsTable 1 }


Pmo6006CtrlcaisDwInsEntry ::=
	SEQUENCE {
	pmo6006CtrlcaisDwInsIndex
		INTEGER,
	pmo6006CtrlcaisDwInsPortn
		EkiState
	}


pmo6006CtrlcaisDwInsIndex OBJECT-TYPE
	SYNTAX  INTEGER(0..128)
	MAX-ACCESS  read-only
	STATUS current
	DESCRIPTION
        "
        Index definition for the pmo6006CtrlcaisDwIns 
        table
        "
	::= { pmo6006CtrlcaisDwInsEntry 1 }


pmo6006CtrlcaisDwInsPortn OBJECT-TYPE
	SYNTAX  EkiState
	MAX-ACCESS read-write
	STATUS current
	DESCRIPTION
        "
        Client AIS Insertion :This OID, 
        when set, inserts a client AIS
         on the downstream client Port. 
         <Help>  This control inserts a 
        Client AIS for the client port
        "
	::= { pmo6006CtrlcaisDwInsEntry 2 }


--- *********************************************************
---     TABLE for the pmo6006CtrlclientOci articles
--- *********************************************************

pmo6006CtrlclientOciTable OBJECT-TYPE
	SYNTAX  SEQUENCE OF Pmo6006CtrlclientOciEntry
	MAX-ACCESS not-accessible
	STATUS current
	DESCRIPTION
        "
        List of pmo6006CtrlclientOci Article
        "
	::= { pmo6006CtrlClient 23 }


pmo6006CtrlclientOciEntry OBJECT-TYPE
	SYNTAX Pmo6006CtrlclientOciEntry
	MAX-ACCESS not-accessible
	STATUS current
	DESCRIPTION
        "
        Row definition for the pmo6006CtrlclientOci 
        table
        "
	INDEX   { pmo6006CtrlclientOciIndex }
	::= { pmo6006CtrlclientOciTable 1 }


Pmo6006CtrlclientOciEntry ::=
	SEQUENCE {
	pmo6006CtrlclientOciIndex
		INTEGER,
	pmo6006CtrlclientOciPortn
		EkiState
	}


pmo6006CtrlclientOciIndex OBJECT-TYPE
	SYNTAX  INTEGER(0..128)
	MAX-ACCESS  read-only
	STATUS current
	DESCRIPTION
        "
        Index definition for the pmo6006CtrlclientOci 
        table
        "
	::= { pmo6006CtrlclientOciEntry 1 }


pmo6006CtrlclientOciPortn OBJECT-TYPE
	SYNTAX  EkiState
	MAX-ACCESS read-write
	STATUS current
	DESCRIPTION
        "
        ODU2e-OCI :Label  <Help>  This 
        control inserts a Client OCI
        "
	::= { pmo6006CtrlclientOciEntry 2 }


--- *********************************************************
---     TABLE for the pmo6006CtrlclientLck articles
--- *********************************************************

pmo6006CtrlclientLckTable OBJECT-TYPE
	SYNTAX  SEQUENCE OF Pmo6006CtrlclientLckEntry
	MAX-ACCESS not-accessible
	STATUS current
	DESCRIPTION
        "
        List of pmo6006CtrlclientLck Article
        "
	::= { pmo6006CtrlClient 24 }


pmo6006CtrlclientLckEntry OBJECT-TYPE
	SYNTAX Pmo6006CtrlclientLckEntry
	MAX-ACCESS not-accessible
	STATUS current
	DESCRIPTION
        "
        Row definition for the pmo6006CtrlclientLck 
        table
        "
	INDEX   { pmo6006CtrlclientLckIndex }
	::= { pmo6006CtrlclientLckTable 1 }


Pmo6006CtrlclientLckEntry ::=
	SEQUENCE {
	pmo6006CtrlclientLckIndex
		INTEGER,
	pmo6006CtrlclientLckPortn
		EkiState
	}


pmo6006CtrlclientLckIndex OBJECT-TYPE
	SYNTAX  INTEGER(0..128)
	MAX-ACCESS  read-only
	STATUS current
	DESCRIPTION
        "
        Index definition for the pmo6006CtrlclientLck 
        table
        "
	::= { pmo6006CtrlclientLckEntry 1 }


pmo6006CtrlclientLckPortn OBJECT-TYPE
	SYNTAX  EkiState
	MAX-ACCESS read-write
	STATUS current
	DESCRIPTION
        "
        ODU2e-LCK :Label  <Help>  This 
        control inserts a Client LCK
        "
	::= { pmo6006CtrlclientLckEntry 2 }


--- *********************************************************
---     TABLE for the pmo6006CtrlclientAis articles
--- *********************************************************

pmo6006CtrlclientAisTable OBJECT-TYPE
	SYNTAX  SEQUENCE OF Pmo6006CtrlclientAisEntry
	MAX-ACCESS not-accessible
	STATUS current
	DESCRIPTION
        "
        List of pmo6006CtrlclientAis Article
        "
	::= { pmo6006CtrlClient 25 }


pmo6006CtrlclientAisEntry OBJECT-TYPE
	SYNTAX Pmo6006CtrlclientAisEntry
	MAX-ACCESS not-accessible
	STATUS current
	DESCRIPTION
        "
        Row definition for the pmo6006CtrlclientAis 
        table
        "
	INDEX   { pmo6006CtrlclientAisIndex }
	::= { pmo6006CtrlclientAisTable 1 }


Pmo6006CtrlclientAisEntry ::=
	SEQUENCE {
	pmo6006CtrlclientAisIndex
		INTEGER,
	pmo6006CtrlclientAisPortn
		EkiState
	}


pmo6006CtrlclientAisIndex OBJECT-TYPE
	SYNTAX  INTEGER(0..128)
	MAX-ACCESS  read-only
	STATUS current
	DESCRIPTION
        "
        Index definition for the pmo6006CtrlclientAis 
        table
        "
	::= { pmo6006CtrlclientAisEntry 1 }


pmo6006CtrlclientAisPortn OBJECT-TYPE
	SYNTAX  EkiState
	MAX-ACCESS read-write
	STATUS current
	DESCRIPTION
        "
        ODU2e-AIS :Label  <Help>  This 
        control inserts a Client AIS 
        "
	::= { pmo6006CtrlclientAisEntry 2 }


--- *********************************************************
---     TABLE for the pmo6006CtrlclientBdi articles
--- *********************************************************

pmo6006CtrlclientBdiTable OBJECT-TYPE
	SYNTAX  SEQUENCE OF Pmo6006CtrlclientBdiEntry
	MAX-ACCESS not-accessible
	STATUS current
	DESCRIPTION
        "
        List of pmo6006CtrlclientBdi Article
        "
	::= { pmo6006CtrlClient 26 }


pmo6006CtrlclientBdiEntry OBJECT-TYPE
	SYNTAX Pmo6006CtrlclientBdiEntry
	MAX-ACCESS not-accessible
	STATUS current
	DESCRIPTION
        "
        Row definition for the pmo6006CtrlclientBdi 
        table
        "
	INDEX   { pmo6006CtrlclientBdiIndex }
	::= { pmo6006CtrlclientBdiTable 1 }


Pmo6006CtrlclientBdiEntry ::=
	SEQUENCE {
	pmo6006CtrlclientBdiIndex
		INTEGER,
	pmo6006CtrlclientBdiPortn
		EkiState
	}


pmo6006CtrlclientBdiIndex OBJECT-TYPE
	SYNTAX  INTEGER(0..128)
	MAX-ACCESS  read-only
	STATUS current
	DESCRIPTION
        "
        Index definition for the pmo6006CtrlclientBdi 
        table
        "
	::= { pmo6006CtrlclientBdiEntry 1 }


pmo6006CtrlclientBdiPortn OBJECT-TYPE
	SYNTAX  EkiState
	MAX-ACCESS read-write
	STATUS current
	DESCRIPTION
        "
        ODU2e-BDI :Label  <Help>  This 
        control inserts a Client BDI
        "
	::= { pmo6006CtrlclientBdiEntry 2 }


--- *********************************************************
---     TABLE for the pmo6006CtrlcommAccessLoop articles
--- *********************************************************

pmo6006CtrlcommAccessLoopTable OBJECT-TYPE
	SYNTAX  SEQUENCE OF Pmo6006CtrlcommAccessLoopEntry
	MAX-ACCESS not-accessible
	STATUS current
	DESCRIPTION
        "
        List of pmo6006CtrlcommAccessLoop 
        Article
        "
	::= { pmo6006CtrlLine 64 }


pmo6006CtrlcommAccessLoopEntry OBJECT-TYPE
	SYNTAX Pmo6006CtrlcommAccessLoopEntry
	MAX-ACCESS not-accessible
	STATUS current
	DESCRIPTION
        "
        Row definition for the pmo6006CtrlcommAccessLoop 
        table
        "
	INDEX   { pmo6006CtrlcommAccessLoopIndex }
	::= { pmo6006CtrlcommAccessLoopTable 1 }


Pmo6006CtrlcommAccessLoopEntry ::=
	SEQUENCE {
	pmo6006CtrlcommAccessLoopIndex
		INTEGER,
	pmo6006CtrlcommAccessLoopPortn
		EkiState
	}


pmo6006CtrlcommAccessLoopIndex OBJECT-TYPE
	SYNTAX  INTEGER(0..128)
	MAX-ACCESS  read-only
	STATUS current
	DESCRIPTION
        "
        Index definition for the pmo6006CtrlcommAccessLoop 
        table
        "
	::= { pmo6006CtrlcommAccessLoopEntry 1 }


pmo6006CtrlcommAccessLoopPortn OBJECT-TYPE
	SYNTAX  EkiState
	MAX-ACCESS read-write
	STATUS current
	DESCRIPTION
        "
        Line Terminal Loopback :This OID, 
        when set, puts the module in common 
        access loop back, looping the 10 
        Gb/s output signal on the 10 Gb/s 
        input.<Help> This control enables 
        the In Loopback on the line port, 
        looping the 100 Gb/s output signal 
        on the 100 Gb/s input
        "
	::= { pmo6006CtrlcommAccessLoopEntry 2 }


--- *********************************************************
---     TABLE for the pmo6006CtrllineLoop articles
--- *********************************************************

pmo6006CtrllineLoopTable OBJECT-TYPE
	SYNTAX  SEQUENCE OF Pmo6006CtrllineLoopEntry
	MAX-ACCESS not-accessible
	STATUS current
	DESCRIPTION
        "
        List of pmo6006CtrllineLoop Article
        "
	::= { pmo6006CtrlLine 66 }


pmo6006CtrllineLoopEntry OBJECT-TYPE
	SYNTAX Pmo6006CtrllineLoopEntry
	MAX-ACCESS not-accessible
	STATUS current
	DESCRIPTION
        "
        Row definition for the pmo6006CtrllineLoop 
        table
        "
	INDEX   { pmo6006CtrllineLoopIndex }
	::= { pmo6006CtrllineLoopTable 1 }


Pmo6006CtrllineLoopEntry ::=
	SEQUENCE {
	pmo6006CtrllineLoopIndex
		INTEGER,
	pmo6006CtrllineLoopPortn
		EkiState
	}


pmo6006CtrllineLoopIndex OBJECT-TYPE
	SYNTAX  INTEGER(0..128)
	MAX-ACCESS  read-only
	STATUS current
	DESCRIPTION
        "
        Index definition for the pmo6006CtrllineLoop 
        table
        "
	::= { pmo6006CtrllineLoopEntry 1 }


pmo6006CtrllineLoopPortn OBJECT-TYPE
	SYNTAX  EkiState
	MAX-ACCESS read-write
	STATUS current
	DESCRIPTION
        "
        Line Facility Loopback :This OID, 
        when set at '1' puts the module 
        in line loopback mode, looping
         the received 10 Gb/s signal on 
        the transmit 10 Gb/s output. The 
        Upstream part of the module is
         timed on the 10 Gb/s recovered 
        clock in that case.<Help> This
         control enables the Out Loopback 
        on the line port, looping the 100 
        Gb/s input signal on the 100 Gb/s 
        output
        "
	::= { pmo6006CtrllineLoopEntry 2 }


--- *********************************************************
---     TABLE for the pmo6006CtrlfecDisable articles
--- *********************************************************

pmo6006CtrlfecDisableTable OBJECT-TYPE
	SYNTAX  SEQUENCE OF Pmo6006CtrlfecDisableEntry
	MAX-ACCESS not-accessible
	STATUS current
	DESCRIPTION
        "
        List of pmo6006CtrlfecDisable
         Article
        "
	::= { pmo6006CtrlLine 69 }


pmo6006CtrlfecDisableEntry OBJECT-TYPE
	SYNTAX Pmo6006CtrlfecDisableEntry
	MAX-ACCESS not-accessible
	STATUS current
	DESCRIPTION
        "
        Row definition for the pmo6006CtrlfecDisable 
        table
        "
	INDEX   { pmo6006CtrlfecDisableIndex }
	::= { pmo6006CtrlfecDisableTable 1 }


Pmo6006CtrlfecDisableEntry ::=
	SEQUENCE {
	pmo6006CtrlfecDisableIndex
		INTEGER,
	pmo6006CtrlfecDisablePortn
		EkiState
	}


pmo6006CtrlfecDisableIndex OBJECT-TYPE
	SYNTAX  INTEGER(0..128)
	MAX-ACCESS  read-only
	STATUS current
	DESCRIPTION
        "
        Index definition for the pmo6006CtrlfecDisable 
        table
        "
	::= { pmo6006CtrlfecDisableEntry 1 }


pmo6006CtrlfecDisablePortn OBJECT-TYPE
	SYNTAX  EkiState
	MAX-ACCESS read-write
	STATUS current
	DESCRIPTION
        "
        Forward Error Correction Inhibition 
        :This OID, when set, inhibits the 
        Forward Error Correction feature 
        on the line input  <Help>  This 
        control enables/disables the Forward 
        Error Correction on the line interface
        "
	::= { pmo6006CtrlfecDisableEntry 2 }


--- *********************************************************
---     TABLE for the pmo6006CtrllineBdi articles
--- *********************************************************

pmo6006CtrllineBdiTable OBJECT-TYPE
	SYNTAX  SEQUENCE OF Pmo6006CtrllineBdiEntry
	MAX-ACCESS not-accessible
	STATUS current
	DESCRIPTION
        "
        List of pmo6006CtrllineBdi Article
        "
	::= { pmo6006CtrlLine 70 }


pmo6006CtrllineBdiEntry OBJECT-TYPE
	SYNTAX Pmo6006CtrllineBdiEntry
	MAX-ACCESS not-accessible
	STATUS current
	DESCRIPTION
        "
        Row definition for the pmo6006CtrllineBdi 
        table
        "
	INDEX   { pmo6006CtrllineBdiIndex }
	::= { pmo6006CtrllineBdiTable 1 }


Pmo6006CtrllineBdiEntry ::=
	SEQUENCE {
	pmo6006CtrllineBdiIndex
		INTEGER,
	pmo6006CtrllineBdiPortn
		EkiState
	}


pmo6006CtrllineBdiIndex OBJECT-TYPE
	SYNTAX  INTEGER(0..128)
	MAX-ACCESS  read-only
	STATUS current
	DESCRIPTION
        "
        Index definition for the pmo6006CtrllineBdi 
        table
        "
	::= { pmo6006CtrllineBdiEntry 1 }


pmo6006CtrllineBdiPortn OBJECT-TYPE
	SYNTAX  EkiState
	MAX-ACCESS read-write
	STATUS current
	DESCRIPTION
        "
        OTU2e-BDI :Label  <Help>  This 
        control inserts a Line BDI
        "
	::= { pmo6006CtrllineBdiEntry 2 }


--- *****************************************************
---     LEAF for the ledTest article
--- *****************************************************
pmo6006CtrlledTest OBJECT IDENTIFIER ::= { pmo6006CtrlOther 192 }




pmo6006CtrlLedOff OBJECT-TYPE
	  SYNTAX EkiOnOff
	  MAX-ACCESS read-write
	  STATUS current
	  DESCRIPTION
        "
        Leds Off :This OID switches off 
        all the Leds as a test feature. 
         <Help>  This control initiates 
        a test leds turning all the LEDs 
        to OFF
        "
	  ::= { pmo6006CtrlledTest 3 }



pmo6006CtrlRedLed OBJECT-TYPE
	  SYNTAX EkiOnOff
	  MAX-ACCESS read-write
	  STATUS current
	  DESCRIPTION
        "
        Red Leds Test :This OID switches 
        on all the red Leds as a test feature. 
         <Help>  This control initiates 
        a test leds turning all the LEDs 
        to red
        "
	  ::= { pmo6006CtrlledTest 2 }



pmo6006CtrlGreenLed OBJECT-TYPE
	  SYNTAX EkiOnOff
	  MAX-ACCESS read-write
	  STATUS current
	  DESCRIPTION
        "
        Green Leds Test :This OID switches 
        on all the green Leds as a test 
        feature.  <Help>  This control
         initiates a test leds turning
         all the LEDs to green
        "
	  ::= { pmo6006CtrlledTest 1 }








--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pmo6006CntclientRemoteBip articles
--- *********************************************************

pmo6006CntclientRemoteBipTable OBJECT-TYPE
	SYNTAX  SEQUENCE OF Pmo6006CntclientRemoteBipEntry
	MAX-ACCESS not-accessible
	STATUS current
	DESCRIPTION
        "
        List of pmo6006CntclientRemoteBip 
        Article
        "
	::= { pmo6006CntClient 64 }


pmo6006CntclientRemoteBipEntry OBJECT-TYPE
	SYNTAX Pmo6006CntclientRemoteBipEntry
	MAX-ACCESS not-accessible
	STATUS current
	DESCRIPTION
        "
        Row definition for the pmo6006CntclientRemoteBip 
        table
        "
	INDEX   { pmo6006CntclientRemoteBipIndex }
	::= { pmo6006CntclientRemoteBipTable 1 }


Pmo6006CntclientRemoteBipEntry ::=
	SEQUENCE {
	pmo6006CntclientRemoteBipIndex
		INTEGER,
	pmo6006CntclientRemoteBipValuePortn
		Counter32,
	pmo6006CntclientRemoteBipErrorPortn
		EkiOnOff,
	pmo6006CntclientRemoteBipOverloadPortn
		EkiOnOff
	}


pmo6006CntclientRemoteBipIndex OBJECT-TYPE
	SYNTAX  INTEGER(0..128)
	MAX-ACCESS  read-only
	STATUS current
	DESCRIPTION
        "
        Index definition for the pmo6006CntclientRemoteBip 
        table
        "
	::= { pmo6006CntclientRemoteBipEntry 1 }


pmo6006CntclientRemoteBipValuePortn OBJECT-TYPE
	SYNTAX  Counter32
	MAX-ACCESS read-only
	STATUS current
	DESCRIPTION
        "
        ODU2e_Sk_pF_EBC :This counter
         is increased each time a BIP8
         error is detected on the Client 
        input stream  <Help>  This counter 
        gives the number of BIP8 errors 
        on the remote client path
        "
	::= { pmo6006CntclientRemoteBipEntry 2 }


pmo6006CntclientRemoteBipErrorPortn OBJECT-TYPE
	SYNTAX  EkiOnOff
	MAX-ACCESS read-only
	STATUS current
	DESCRIPTION
        "
        Client Counter Error :This OID 
        when set indicates the BIP8 error 
        counter value is invalid on Port
        "
	::= { pmo6006CntclientRemoteBipEntry 3 }


pmo6006CntclientRemoteBipOverloadPortn OBJECT-TYPE
	SYNTAX  EkiOnOff
	MAX-ACCESS read-only
	STATUS current
	DESCRIPTION
        "
        Client Counter Overload :This
         OID when set indicates a BIP8
         error counter overload on Port
        "
	::= { pmo6006CntclientRemoteBipEntry 4 }


--- *********************************************************
---     TABLE for the pmo6006CntclientCbipCounter articles
--- *********************************************************

pmo6006CntclientCbipCounterTable OBJECT-TYPE
	SYNTAX  SEQUENCE OF Pmo6006CntclientCbipCounterEntry
	MAX-ACCESS not-accessible
	STATUS current
	DESCRIPTION
        "
        List of pmo6006CntclientCbipCounter 
        Article
        "
	::= { pmo6006CntClient 96 }


pmo6006CntclientCbipCounterEntry OBJECT-TYPE
	SYNTAX Pmo6006CntclientCbipCounterEntry
	MAX-ACCESS not-accessible
	STATUS current
	DESCRIPTION
        "
        Row definition for the pmo6006CntclientCbipCounter 
        table
        "
	INDEX   { pmo6006CntclientCbipCounterIndex }
	::= { pmo6006CntclientCbipCounterTable 1 }


Pmo6006CntclientCbipCounterEntry ::=
	SEQUENCE {
	pmo6006CntclientCbipCounterIndex
		INTEGER,
	pmo6006CntclientCbipCounterValuePortn
		Counter32,
	pmo6006CntclientCbipCounterErrorPortn
		EkiOnOff,
	pmo6006CntclientCbipCounterOverloadPortn
		EkiOnOff
	}


pmo6006CntclientCbipCounterIndex OBJECT-TYPE
	SYNTAX  INTEGER(0..128)
	MAX-ACCESS  read-only
	STATUS current
	DESCRIPTION
        "
        Index definition for the pmo6006CntclientCbipCounter 
        table
        "
	::= { pmo6006CntclientCbipCounterEntry 1 }


pmo6006CntclientCbipCounterValuePortn OBJECT-TYPE
	SYNTAX  Counter32
	MAX-ACCESS read-only
	STATUS current
	DESCRIPTION
        "
        ODU2e_Sk_pN_EBC :This counter
         is incremented each time a BI8P 
        error is detected on the Client 
        path  <Help>  This counter gives 
        the number of BIP8 errors on the 
        client path
        "
	::= { pmo6006CntclientCbipCounterEntry 2 }


pmo6006CntclientCbipCounterErrorPortn OBJECT-TYPE
	SYNTAX  EkiOnOff
	MAX-ACCESS read-only
	STATUS current
	DESCRIPTION
        "
        Client Counter Error :This OID 
        when set indicates the CBIP error 
        counter value is invalid on Port
        "
	::= { pmo6006CntclientCbipCounterEntry 3 }


pmo6006CntclientCbipCounterOverloadPortn OBJECT-TYPE
	SYNTAX  EkiOnOff
	MAX-ACCESS read-only
	STATUS current
	DESCRIPTION
        "
        Client CBIP Counter Overload :This 
        OID when set indicates a CBIP error 
        counter overload on Port
        "
	::= { pmo6006CntclientCbipCounterEntry 4 }


--- *********************************************************
---     TABLE for the pmo6006CntlocalLineSmBip8ErrorCounter articles
--- *********************************************************

pmo6006CntlocalLineSmBip8ErrorCounterTable OBJECT-TYPE
	SYNTAX  SEQUENCE OF Pmo6006CntlocalLineSmBip8ErrorCounterEntry
	MAX-ACCESS not-accessible
	STATUS current
	DESCRIPTION
        "
        List of pmo6006CntlocalLineSmBip8ErrorCounter 
        Article
        "
	::= { pmo6006CntLine 192 }


pmo6006CntlocalLineSmBip8ErrorCounterEntry OBJECT-TYPE
	SYNTAX Pmo6006CntlocalLineSmBip8ErrorCounterEntry
	MAX-ACCESS not-accessible
	STATUS current
	DESCRIPTION
        "
        Row definition for the pmo6006CntlocalLineSmBip8ErrorCounter 
        table
        "
	INDEX   { pmo6006CntlocalLineSmBip8ErrorCounterIndex }
	::= { pmo6006CntlocalLineSmBip8ErrorCounterTable 1 }


Pmo6006CntlocalLineSmBip8ErrorCounterEntry ::=
	SEQUENCE {
	pmo6006CntlocalLineSmBip8ErrorCounterIndex
		INTEGER,
	pmo6006CntlocalLineSmBip8ErrorCounterValuePortn
		Counter32,
	pmo6006CntlocalLineSmBip8ErrorCounterErrorPortn
		EkiOnOff,
	pmo6006CntlocalLineSmBip8ErrorCounterOverloadPortn
		EkiOnOff
	}


pmo6006CntlocalLineSmBip8ErrorCounterIndex OBJECT-TYPE
	SYNTAX  INTEGER(0..128)
	MAX-ACCESS  read-only
	STATUS current
	DESCRIPTION
        "
        Index definition for the pmo6006CntlocalLineSmBip8ErrorCounter 
        table
        "
	::= { pmo6006CntlocalLineSmBip8ErrorCounterEntry 1 }


pmo6006CntlocalLineSmBip8ErrorCounterValuePortn OBJECT-TYPE
	SYNTAX  Counter32
	MAX-ACCESS read-only
	STATUS current
	DESCRIPTION
        "
        OTU2e_Sk_pN_EBC :This OID gives 
        the current Bit Error Rate (residual 
        SM-BIP8 error) after FEC   <Help> 
        This counter gives the current
         Bit Error Rate (residual SM-BIP8 
        error) after FEC
        "
	::= { pmo6006CntlocalLineSmBip8ErrorCounterEntry 2 }


pmo6006CntlocalLineSmBip8ErrorCounterErrorPortn OBJECT-TYPE
	SYNTAX  EkiOnOff
	MAX-ACCESS read-only
	STATUS current
	DESCRIPTION
        "
        Line Counter Error :This OID when 
        set indicates the B1 error counter 
        value is invalid on Port
        "
	::= { pmo6006CntlocalLineSmBip8ErrorCounterEntry 3 }


pmo6006CntlocalLineSmBip8ErrorCounterOverloadPortn OBJECT-TYPE
	SYNTAX  EkiOnOff
	MAX-ACCESS read-only
	STATUS current
	DESCRIPTION
        "
        Line Counter Overload :This OID 
        when set indicates a B1 error counter 
        overload on Port
        "
	::= { pmo6006CntlocalLineSmBip8ErrorCounterEntry 4 }


--- *********************************************************
---     TABLE for the pmo6006CntlocalLineFecCorrectedErrorsCounter articles
--- *********************************************************

pmo6006CntlocalLineFecCorrectedErrorsCounterTable OBJECT-TYPE
	SYNTAX  SEQUENCE OF Pmo6006CntlocalLineFecCorrectedErrorsCounterEntry
	MAX-ACCESS not-accessible
	STATUS current
	DESCRIPTION
        "
        List of pmo6006CntlocalLineFecCorrectedErrorsCounter 
        Article
        "
	::= { pmo6006CntLine 200 }


pmo6006CntlocalLineFecCorrectedErrorsCounterEntry OBJECT-TYPE
	SYNTAX Pmo6006CntlocalLineFecCorrectedErrorsCounterEntry
	MAX-ACCESS not-accessible
	STATUS current
	DESCRIPTION
        "
        Row definition for the pmo6006CntlocalLineFecCorrectedErrorsCounter 
        table
        "
	INDEX   { pmo6006CntlocalLineFecCorrectedErrorsCounterIndex }
	::= { pmo6006CntlocalLineFecCorrectedErrorsCounterTable 1 }


Pmo6006CntlocalLineFecCorrectedErrorsCounterEntry ::=
	SEQUENCE {
	pmo6006CntlocalLineFecCorrectedErrorsCounterIndex
		INTEGER,
	pmo6006CntlocalLineFecCorrectedErrorsCounterValuePortn
		Counter32,
	pmo6006CntlocalLineFecCorrectedErrorsCounterErrorPortn
		EkiOnOff,
	pmo6006CntlocalLineFecCorrectedErrorsCounterOverloadPortn
		EkiOnOff
	}


pmo6006CntlocalLineFecCorrectedErrorsCounterIndex OBJECT-TYPE
	SYNTAX  INTEGER(0..128)
	MAX-ACCESS  read-only
	STATUS current
	DESCRIPTION
        "
        Index definition for the pmo6006CntlocalLineFecCorrectedErrorsCounter 
        table
        "
	::= { pmo6006CntlocalLineFecCorrectedErrorsCounterEntry 1 }


pmo6006CntlocalLineFecCorrectedErrorsCounterValuePortn OBJECT-TYPE
	SYNTAX  Counter32
	MAX-ACCESS read-only
	STATUS current
	DESCRIPTION
        "
        OCh/OTU2e-Sk_pFECcorrErr :This 
        OID gives the current Bit Error 
        Rate before the Hard Decision FEC 
         <Help> This counter gives the
         current Bit Error Rate before
         the Hard Decision FEC
        "
	::= { pmo6006CntlocalLineFecCorrectedErrorsCounterEntry 2 }


pmo6006CntlocalLineFecCorrectedErrorsCounterErrorPortn OBJECT-TYPE
	SYNTAX  EkiOnOff
	MAX-ACCESS read-only
	STATUS current
	DESCRIPTION
        "
        FEC Counter Error :This bit when 
        set indicates the FEC corrected 
        errors counter value is invalid 
        on Line
        "
	::= { pmo6006CntlocalLineFecCorrectedErrorsCounterEntry 3 }


pmo6006CntlocalLineFecCorrectedErrorsCounterOverloadPortn OBJECT-TYPE
	SYNTAX  EkiOnOff
	MAX-ACCESS read-only
	STATUS current
	DESCRIPTION
        "
        FEC Counter Overload :This bit 
        when set indicates a FEC corrected 
        errors counter overload on Line
        "
	::= { pmo6006CntlocalLineFecCorrectedErrorsCounterEntry 4 }


--- *********************************************************
---     TABLE for the pmo6006CntremoteLineSmBip8ErrorCounter articles
--- *********************************************************

pmo6006CntremoteLineSmBip8ErrorCounterTable OBJECT-TYPE
	SYNTAX  SEQUENCE OF Pmo6006CntremoteLineSmBip8ErrorCounterEntry
	MAX-ACCESS not-accessible
	STATUS current
	DESCRIPTION
        "
        List of pmo6006CntremoteLineSmBip8ErrorCounter 
        Article
        "
	::= { pmo6006CntLine 208 }


pmo6006CntremoteLineSmBip8ErrorCounterEntry OBJECT-TYPE
	SYNTAX Pmo6006CntremoteLineSmBip8ErrorCounterEntry
	MAX-ACCESS not-accessible
	STATUS current
	DESCRIPTION
        "
        Row definition for the pmo6006CntremoteLineSmBip8ErrorCounter 
        table
        "
	INDEX   { pmo6006CntremoteLineSmBip8ErrorCounterIndex }
	::= { pmo6006CntremoteLineSmBip8ErrorCounterTable 1 }


Pmo6006CntremoteLineSmBip8ErrorCounterEntry ::=
	SEQUENCE {
	pmo6006CntremoteLineSmBip8ErrorCounterIndex
		INTEGER,
	pmo6006CntremoteLineSmBip8ErrorCounterValuePortn
		Counter32,
	pmo6006CntremoteLineSmBip8ErrorCounterErrorPortn
		EkiOnOff,
	pmo6006CntremoteLineSmBip8ErrorCounterOverloadPortn
		EkiOnOff
	}


pmo6006CntremoteLineSmBip8ErrorCounterIndex OBJECT-TYPE
	SYNTAX  INTEGER(0..128)
	MAX-ACCESS  read-only
	STATUS current
	DESCRIPTION
        "
        Index definition for the pmo6006CntremoteLineSmBip8ErrorCounter 
        table
        "
	::= { pmo6006CntremoteLineSmBip8ErrorCounterEntry 1 }


pmo6006CntremoteLineSmBip8ErrorCounterValuePortn OBJECT-TYPE
	SYNTAX  Counter32
	MAX-ACCESS read-only
	STATUS current
	DESCRIPTION
        "
        OTU2e_Sk_pF_EBC :This OID gives 
        the current Bit Error Rate (residual 
        SM-BIP8 error) after FEC on the 
        remote side  <Help> This counter 
        gives the current Bit Error Rate 
        (residual SM-BIP8 error) after
         FEC on the remote side
        "
	::= { pmo6006CntremoteLineSmBip8ErrorCounterEntry 2 }


pmo6006CntremoteLineSmBip8ErrorCounterErrorPortn OBJECT-TYPE
	SYNTAX  EkiOnOff
	MAX-ACCESS read-only
	STATUS current
	DESCRIPTION
        "
        Remote Counter Error :
        "
	::= { pmo6006CntremoteLineSmBip8ErrorCounterEntry 3 }


pmo6006CntremoteLineSmBip8ErrorCounterOverloadPortn OBJECT-TYPE
	SYNTAX  EkiOnOff
	MAX-ACCESS read-only
	STATUS current
	DESCRIPTION
        "
        Remote Counter Overload :
        "
	::= { pmo6006CntremoteLineSmBip8ErrorCounterEntry 4 }


--- *********************************************************
---     TABLE for the pmo6006CntlineDfrmTimCnt articles
--- *********************************************************

pmo6006CntlineDfrmTimCntTable OBJECT-TYPE
	SYNTAX  SEQUENCE OF Pmo6006CntlineDfrmTimCntEntry
	MAX-ACCESS not-accessible
	STATUS current
	DESCRIPTION
        "
        List of pmo6006CntlineDfrmTimCnt 
        Article
        "
	::= { pmo6006CntLine 216 }


pmo6006CntlineDfrmTimCntEntry OBJECT-TYPE
	SYNTAX Pmo6006CntlineDfrmTimCntEntry
	MAX-ACCESS not-accessible
	STATUS current
	DESCRIPTION
        "
        Row definition for the pmo6006CntlineDfrmTimCnt 
        table
        "
	INDEX   { pmo6006CntlineDfrmTimCntIndex }
	::= { pmo6006CntlineDfrmTimCntTable 1 }


Pmo6006CntlineDfrmTimCntEntry ::=
	SEQUENCE {
	pmo6006CntlineDfrmTimCntIndex
		INTEGER,
	pmo6006CntlineDfrmTimCntValuePortn
		Counter32,
	pmo6006CntlineDfrmTimCntErrorPortn
		EkiOnOff,
	pmo6006CntlineDfrmTimCntOverloadPortn
		EkiOnOff
	}


pmo6006CntlineDfrmTimCntIndex OBJECT-TYPE
	SYNTAX  INTEGER(0..128)
	MAX-ACCESS  read-only
	STATUS current
	DESCRIPTION
        "
        Index definition for the pmo6006CntlineDfrmTimCnt 
        table
        "
	::= { pmo6006CntlineDfrmTimCntEntry 1 }


pmo6006CntlineDfrmTimCntValuePortn OBJECT-TYPE
	SYNTAX  Counter32
	MAX-ACCESS read-only
	STATUS current
	DESCRIPTION
        "
        Line Timer Counter :
        "
	::= { pmo6006CntlineDfrmTimCntEntry 2 }


pmo6006CntlineDfrmTimCntErrorPortn OBJECT-TYPE
	SYNTAX  EkiOnOff
	MAX-ACCESS read-only
	STATUS current
	DESCRIPTION
        "
        Line Counter Error :This OID when 
        set indicates the deframer timer 
        counter value is invalid on Port
        "
	::= { pmo6006CntlineDfrmTimCntEntry 3 }


pmo6006CntlineDfrmTimCntOverloadPortn OBJECT-TYPE
	SYNTAX  EkiOnOff
	MAX-ACCESS read-only
	STATUS current
	DESCRIPTION
        "
        Line Counter Overload :This OID 
        when set indicates a deframer timer 
        counter overload on Port
        "
	::= { pmo6006CntlineDfrmTimCntEntry 4 }


pmo6006CntCountersReset  OBJECT-TYPE
	SYNTAX EkiOnOff
	MAX-ACCESS read-write
	STATUS current
	DESCRIPTION
	"Counters Reset:This OID resets and restarts all the counters"
	::= { pmo6006counters  259 }

pmo6006CntCountersStop  OBJECT-TYPE
	SYNTAX EkiOnOff
	MAX-ACCESS read-write
	STATUS current
	DESCRIPTION
	"Counters stop:This OID stops all the counters"
	::= { pmo6006counters 260 }






--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pmo6006MonupRmonBytesCounterClientInput articles
--- *********************************************************

pmo6006MonupRmonBytesCounterClientInputTable OBJECT-TYPE
	SYNTAX  SEQUENCE OF Pmo6006MonupRmonBytesCounterClientInputEntry
	MAX-ACCESS not-accessible
	STATUS current
	DESCRIPTION
        "
        List of pmo6006MonupRmonBytesCounterClientInput 
        Article
        "
	::= { pmo6006MonClientRmonCounter 16 }


pmo6006MonupRmonBytesCounterClientInputEntry OBJECT-TYPE
	SYNTAX Pmo6006MonupRmonBytesCounterClientInputEntry
	MAX-ACCESS not-accessible
	STATUS current
	DESCRIPTION
        "
        Row definition for the pmo6006MonupRmonBytesCounterClientInput 
        table
        "
	INDEX   { pmo6006MonupRmonBytesCounterClientInputIndex }
	::= { pmo6006MonupRmonBytesCounterClientInputTable 1 }


Pmo6006MonupRmonBytesCounterClientInputEntry ::=
	SEQUENCE {
	pmo6006MonupRmonBytesCounterClientInputIndex
		INTEGER,
	pmo6006MonupRmonBytesCounterClientInputValuePortn
		Counter64,
	pmo6006MonupRmonBytesCounterClientInputErrorPortn
		EkiOnOff,
	pmo6006MonupRmonBytesCounterClientInputOverloadPortn
		EkiOnOff
	}


pmo6006MonupRmonBytesCounterClientInputIndex OBJECT-TYPE
	SYNTAX  INTEGER(0..128)
	MAX-ACCESS  read-only
	STATUS current
	DESCRIPTION
        "
        Index definition for the pmo6006MonupRmonBytesCounterClientInput 
        table
        "
	::= { pmo6006MonupRmonBytesCounterClientInputEntry 1 }


pmo6006MonupRmonBytesCounterClientInputValuePortn OBJECT-TYPE
	SYNTAX  Counter64
	MAX-ACCESS read-only
	STATUS current
	DESCRIPTION
        "
        Client Input Bytes :This counter 
        is increased each time a data byte 
        is received on the client port
          <Help>  This counter gives the 
        number of bytes received on the 
        client port
        "
	::= { pmo6006MonupRmonBytesCounterClientInputEntry 2 }


pmo6006MonupRmonBytesCounterClientInputErrorPortn OBJECT-TYPE
	SYNTAX  EkiOnOff
	MAX-ACCESS read-only
	STATUS current
	DESCRIPTION
        "
        Bytes Counter Error :This OID
         when set indicates the Bytes counter 
        value is invalid on client port
        "
	::= { pmo6006MonupRmonBytesCounterClientInputEntry 3 }


pmo6006MonupRmonBytesCounterClientInputOverloadPortn OBJECT-TYPE
	SYNTAX  EkiOnOff
	MAX-ACCESS read-only
	STATUS current
	DESCRIPTION
        "
        Bytes Counter Overload :This OID 
        when set indicates a Bytes counter 
        overload on client port
        "
	::= { pmo6006MonupRmonBytesCounterClientInputEntry 4 }


--- *********************************************************
---     TABLE for the pmo6006MonupRmonCrcErrorsCounterClientInput articles
--- *********************************************************

pmo6006MonupRmonCrcErrorsCounterClientInputTable OBJECT-TYPE
	SYNTAX  SEQUENCE OF Pmo6006MonupRmonCrcErrorsCounterClientInputEntry
	MAX-ACCESS not-accessible
	STATUS current
	DESCRIPTION
        "
        List of pmo6006MonupRmonCrcErrorsCounterClientInput 
        Article
        "
	::= { pmo6006MonClientRmonCounter 32 }


pmo6006MonupRmonCrcErrorsCounterClientInputEntry OBJECT-TYPE
	SYNTAX Pmo6006MonupRmonCrcErrorsCounterClientInputEntry
	MAX-ACCESS not-accessible
	STATUS current
	DESCRIPTION
        "
        Row definition for the pmo6006MonupRmonCrcErrorsCounterClientInput 
        table
        "
	INDEX   { pmo6006MonupRmonCrcErrorsCounterClientInputIndex }
	::= { pmo6006MonupRmonCrcErrorsCounterClientInputTable 1 }


Pmo6006MonupRmonCrcErrorsCounterClientInputEntry ::=
	SEQUENCE {
	pmo6006MonupRmonCrcErrorsCounterClientInputIndex
		INTEGER,
	pmo6006MonupRmonCrcErrorsCounterClientInputValuePortn
		Counter64,
	pmo6006MonupRmonCrcErrorsCounterClientInputErrorPortn
		EkiOnOff,
	pmo6006MonupRmonCrcErrorsCounterClientInputOverloadPortn
		EkiOnOff
	}


pmo6006MonupRmonCrcErrorsCounterClientInputIndex OBJECT-TYPE
	SYNTAX  INTEGER(0..128)
	MAX-ACCESS  read-only
	STATUS current
	DESCRIPTION
        "
        Index definition for the pmo6006MonupRmonCrcErrorsCounterClientInput 
        table
        "
	::= { pmo6006MonupRmonCrcErrorsCounterClientInputEntry 1 }


pmo6006MonupRmonCrcErrorsCounterClientInputValuePortn OBJECT-TYPE
	SYNTAX  Counter64
	MAX-ACCESS read-only
	STATUS current
	DESCRIPTION
        "
        Client Input CRC Errors :This
         counter is increased each time 
        a B1/FCS error is detected on the 
        client port  <Help>  This counter 
        gives the number of B1/FCS Errors 
        received on the client port
        "
	::= { pmo6006MonupRmonCrcErrorsCounterClientInputEntry 2 }


pmo6006MonupRmonCrcErrorsCounterClientInputErrorPortn OBJECT-TYPE
	SYNTAX  EkiOnOff
	MAX-ACCESS read-only
	STATUS current
	DESCRIPTION
        "
        B1/FCS Errors Counter Error :This 
        OID when set indicates the B1/FCS 
        Errors counter value is invalid 
        on client port
        "
	::= { pmo6006MonupRmonCrcErrorsCounterClientInputEntry 3 }


pmo6006MonupRmonCrcErrorsCounterClientInputOverloadPortn OBJECT-TYPE
	SYNTAX  EkiOnOff
	MAX-ACCESS read-only
	STATUS current
	DESCRIPTION
        "
        B1/FCS Errors Counter Overload 
        :This OID when set indicates a
         B1/FCS Errors counter overload 
        on client port
        "
	::= { pmo6006MonupRmonCrcErrorsCounterClientInputEntry 4 }


--- *********************************************************
---     TABLE for the pmo6006MonupRmonPacketsCounterClientInput articles
--- *********************************************************

pmo6006MonupRmonPacketsCounterClientInputTable OBJECT-TYPE
	SYNTAX  SEQUENCE OF Pmo6006MonupRmonPacketsCounterClientInputEntry
	MAX-ACCESS not-accessible
	STATUS current
	DESCRIPTION
        "
        List of pmo6006MonupRmonPacketsCounterClientInput 
        Article
        "
	::= { pmo6006MonClientRmonCounter 48 }


pmo6006MonupRmonPacketsCounterClientInputEntry OBJECT-TYPE
	SYNTAX Pmo6006MonupRmonPacketsCounterClientInputEntry
	MAX-ACCESS not-accessible
	STATUS current
	DESCRIPTION
        "
        Row definition for the pmo6006MonupRmonPacketsCounterClientInput 
        table
        "
	INDEX   { pmo6006MonupRmonPacketsCounterClientInputIndex }
	::= { pmo6006MonupRmonPacketsCounterClientInputTable 1 }


Pmo6006MonupRmonPacketsCounterClientInputEntry ::=
	SEQUENCE {
	pmo6006MonupRmonPacketsCounterClientInputIndex
		INTEGER,
	pmo6006MonupRmonPacketsCounterClientInputValuePortn
		Counter64,
	pmo6006MonupRmonPacketsCounterClientInputErrorPortn
		EkiOnOff,
	pmo6006MonupRmonPacketsCounterClientInputOverloadPortn
		EkiOnOff
	}


pmo6006MonupRmonPacketsCounterClientInputIndex OBJECT-TYPE
	SYNTAX  INTEGER(0..128)
	MAX-ACCESS  read-only
	STATUS current
	DESCRIPTION
        "
        Index definition for the pmo6006MonupRmonPacketsCounterClientInput 
        table
        "
	::= { pmo6006MonupRmonPacketsCounterClientInputEntry 1 }


pmo6006MonupRmonPacketsCounterClientInputValuePortn OBJECT-TYPE
	SYNTAX  Counter64
	MAX-ACCESS read-only
	STATUS current
	DESCRIPTION
        "
        Client Input Packets :This counter 
        is increased each time a packet 
        is received on the client port
          <Help>  This counter gives the 
        number of packets received on the 
        client port
        "
	::= { pmo6006MonupRmonPacketsCounterClientInputEntry 2 }


pmo6006MonupRmonPacketsCounterClientInputErrorPortn OBJECT-TYPE
	SYNTAX  EkiOnOff
	MAX-ACCESS read-only
	STATUS current
	DESCRIPTION
        "
        Packets Counter Error :This OID 
        when set indicates the Packets
         counter value is invalid on client 
        port
        "
	::= { pmo6006MonupRmonPacketsCounterClientInputEntry 3 }


pmo6006MonupRmonPacketsCounterClientInputOverloadPortn OBJECT-TYPE
	SYNTAX  EkiOnOff
	MAX-ACCESS read-only
	STATUS current
	DESCRIPTION
        "
        Packets Counter Overload :This 
        OID when set indicates a Packets 
        counter overload on client port
        "
	::= { pmo6006MonupRmonPacketsCounterClientInputEntry 4 }


--- *********************************************************
---     TABLE for the pmo6006MonupRmonBroadcastCounterClientInput articles
--- *********************************************************

pmo6006MonupRmonBroadcastCounterClientInputTable OBJECT-TYPE
	SYNTAX  SEQUENCE OF Pmo6006MonupRmonBroadcastCounterClientInputEntry
	MAX-ACCESS not-accessible
	STATUS current
	DESCRIPTION
        "
        List of pmo6006MonupRmonBroadcastCounterClientInput 
        Article
        "
	::= { pmo6006MonClientRmonCounter 64 }


pmo6006MonupRmonBroadcastCounterClientInputEntry OBJECT-TYPE
	SYNTAX Pmo6006MonupRmonBroadcastCounterClientInputEntry
	MAX-ACCESS not-accessible
	STATUS current
	DESCRIPTION
        "
        Row definition for the pmo6006MonupRmonBroadcastCounterClientInput 
        table
        "
	INDEX   { pmo6006MonupRmonBroadcastCounterClientInputIndex }
	::= { pmo6006MonupRmonBroadcastCounterClientInputTable 1 }


Pmo6006MonupRmonBroadcastCounterClientInputEntry ::=
	SEQUENCE {
	pmo6006MonupRmonBroadcastCounterClientInputIndex
		INTEGER,
	pmo6006MonupRmonBroadcastCounterClientInputValuePortn
		Counter64,
	pmo6006MonupRmonBroadcastCounterClientInputErrorPortn
		EkiOnOff,
	pmo6006MonupRmonBroadcastCounterClientInputOverloadPortn
		EkiOnOff
	}


pmo6006MonupRmonBroadcastCounterClientInputIndex OBJECT-TYPE
	SYNTAX  INTEGER(0..128)
	MAX-ACCESS  read-only
	STATUS current
	DESCRIPTION
        "
        Index definition for the pmo6006MonupRmonBroadcastCounterClientInput 
        table
        "
	::= { pmo6006MonupRmonBroadcastCounterClientInputEntry 1 }


pmo6006MonupRmonBroadcastCounterClientInputValuePortn OBJECT-TYPE
	SYNTAX  Counter64
	MAX-ACCESS read-only
	STATUS current
	DESCRIPTION
        "
        Client Input Broadcast Packets 
        :This counter is increased each 
        time a broadcast packet is received 
        on the client port  <Help>  This 
        counter gives the number of Broadcast 
        packets received on the client
         port
        "
	::= { pmo6006MonupRmonBroadcastCounterClientInputEntry 2 }


pmo6006MonupRmonBroadcastCounterClientInputErrorPortn OBJECT-TYPE
	SYNTAX  EkiOnOff
	MAX-ACCESS read-only
	STATUS current
	DESCRIPTION
        "
        Broadcast Counter Error :This
         OID when set indicates the Broadcast 
        counter value is invalid on client 
        port
        "
	::= { pmo6006MonupRmonBroadcastCounterClientInputEntry 3 }


pmo6006MonupRmonBroadcastCounterClientInputOverloadPortn OBJECT-TYPE
	SYNTAX  EkiOnOff
	MAX-ACCESS read-only
	STATUS current
	DESCRIPTION
        "
        Broadcast Counter Overload :This 
        OID when set indicates a Broadcast 
        counter overload on client port
        "
	::= { pmo6006MonupRmonBroadcastCounterClientInputEntry 4 }


--- *********************************************************
---     TABLE for the pmo6006MonupRmonMulticastCounterClientInput articles
--- *********************************************************

pmo6006MonupRmonMulticastCounterClientInputTable OBJECT-TYPE
	SYNTAX  SEQUENCE OF Pmo6006MonupRmonMulticastCounterClientInputEntry
	MAX-ACCESS not-accessible
	STATUS current
	DESCRIPTION
        "
        List of pmo6006MonupRmonMulticastCounterClientInput 
        Article
        "
	::= { pmo6006MonClientRmonCounter 80 }


pmo6006MonupRmonMulticastCounterClientInputEntry OBJECT-TYPE
	SYNTAX Pmo6006MonupRmonMulticastCounterClientInputEntry
	MAX-ACCESS not-accessible
	STATUS current
	DESCRIPTION
        "
        Row definition for the pmo6006MonupRmonMulticastCounterClientInput 
        table
        "
	INDEX   { pmo6006MonupRmonMulticastCounterClientInputIndex }
	::= { pmo6006MonupRmonMulticastCounterClientInputTable 1 }


Pmo6006MonupRmonMulticastCounterClientInputEntry ::=
	SEQUENCE {
	pmo6006MonupRmonMulticastCounterClientInputIndex
		INTEGER,
	pmo6006MonupRmonMulticastCounterClientInputValuePortn
		Counter64,
	pmo6006MonupRmonMulticastCounterClientInputErrorPortn
		EkiOnOff,
	pmo6006MonupRmonMulticastCounterClientInputOverloadPortn
		EkiOnOff
	}


pmo6006MonupRmonMulticastCounterClientInputIndex OBJECT-TYPE
	SYNTAX  INTEGER(0..128)
	MAX-ACCESS  read-only
	STATUS current
	DESCRIPTION
        "
        Index definition for the pmo6006MonupRmonMulticastCounterClientInput 
        table
        "
	::= { pmo6006MonupRmonMulticastCounterClientInputEntry 1 }


pmo6006MonupRmonMulticastCounterClientInputValuePortn OBJECT-TYPE
	SYNTAX  Counter64
	MAX-ACCESS read-only
	STATUS current
	DESCRIPTION
        "
        Client Input Multicast Packets 
        :This counter is increased each 
        time a Multicast packet is received 
        on the client port  <Help>  This 
        counter gives the number of Multicast 
        packets received on the client
         port
        "
	::= { pmo6006MonupRmonMulticastCounterClientInputEntry 2 }


pmo6006MonupRmonMulticastCounterClientInputErrorPortn OBJECT-TYPE
	SYNTAX  EkiOnOff
	MAX-ACCESS read-only
	STATUS current
	DESCRIPTION
        "
        Multicast Counter Error :This
         OID when set indicates the Multicast 
        counter value is invalid on client 
        port
        "
	::= { pmo6006MonupRmonMulticastCounterClientInputEntry 3 }


pmo6006MonupRmonMulticastCounterClientInputOverloadPortn OBJECT-TYPE
	SYNTAX  EkiOnOff
	MAX-ACCESS read-only
	STATUS current
	DESCRIPTION
        "
        Multicast Counter Overload :This 
        OID when set indicates a Multicast 
        counter overload on client port
        "
	::= { pmo6006MonupRmonMulticastCounterClientInputEntry 4 }


--- *********************************************************
---     TABLE for the pmo6006MonupRmonPauseFrameCounterClientInput articles
--- *********************************************************

pmo6006MonupRmonPauseFrameCounterClientInputTable OBJECT-TYPE
	SYNTAX  SEQUENCE OF Pmo6006MonupRmonPauseFrameCounterClientInputEntry
	MAX-ACCESS not-accessible
	STATUS current
	DESCRIPTION
        "
        List of pmo6006MonupRmonPauseFrameCounterClientInput 
        Article
        "
	::= { pmo6006MonClientRmonCounter 96 }


pmo6006MonupRmonPauseFrameCounterClientInputEntry OBJECT-TYPE
	SYNTAX Pmo6006MonupRmonPauseFrameCounterClientInputEntry
	MAX-ACCESS not-accessible
	STATUS current
	DESCRIPTION
        "
        Row definition for the pmo6006MonupRmonPauseFrameCounterClientInput 
        table
        "
	INDEX   { pmo6006MonupRmonPauseFrameCounterClientInputIndex }
	::= { pmo6006MonupRmonPauseFrameCounterClientInputTable 1 }


Pmo6006MonupRmonPauseFrameCounterClientInputEntry ::=
	SEQUENCE {
	pmo6006MonupRmonPauseFrameCounterClientInputIndex
		INTEGER,
	pmo6006MonupRmonPauseFrameCounterClientInputValuePortn
		Counter64,
	pmo6006MonupRmonPauseFrameCounterClientInputErrorPortn
		EkiOnOff,
	pmo6006MonupRmonPauseFrameCounterClientInputOverloadPortn
		EkiOnOff
	}


pmo6006MonupRmonPauseFrameCounterClientInputIndex OBJECT-TYPE
	SYNTAX  INTEGER(0..128)
	MAX-ACCESS  read-only
	STATUS current
	DESCRIPTION
        "
        Index definition for the pmo6006MonupRmonPauseFrameCounterClientInput 
        table
        "
	::= { pmo6006MonupRmonPauseFrameCounterClientInputEntry 1 }


pmo6006MonupRmonPauseFrameCounterClientInputValuePortn OBJECT-TYPE
	SYNTAX  Counter64
	MAX-ACCESS read-only
	STATUS current
	DESCRIPTION
        "
        Client Input Pause Frames :This 
        counter is increased each time
         a Pause frame is received on the 
        client port  <Help>  This counter 
        gives the number of Pause frames 
        received on the client port
        "
	::= { pmo6006MonupRmonPauseFrameCounterClientInputEntry 2 }


pmo6006MonupRmonPauseFrameCounterClientInputErrorPortn OBJECT-TYPE
	SYNTAX  EkiOnOff
	MAX-ACCESS read-only
	STATUS current
	DESCRIPTION
        "
        Pause Counter Error :This OID
         when set indicates the Pause counter 
        value is invalid on client port
        "
	::= { pmo6006MonupRmonPauseFrameCounterClientInputEntry 3 }


pmo6006MonupRmonPauseFrameCounterClientInputOverloadPortn OBJECT-TYPE
	SYNTAX  EkiOnOff
	MAX-ACCESS read-only
	STATUS current
	DESCRIPTION
        "
        Pause Counter Overload :This OID 
        when set indicates a Pause counter 
        overload on client port
        "
	::= { pmo6006MonupRmonPauseFrameCounterClientInputEntry 4 }


--- *********************************************************
---     TABLE for the pmo6006MondwRmonCrcErrorsCounterClientInput articles
--- *********************************************************

pmo6006MondwRmonCrcErrorsCounterClientInputTable OBJECT-TYPE
	SYNTAX  SEQUENCE OF Pmo6006MondwRmonCrcErrorsCounterClientInputEntry
	MAX-ACCESS not-accessible
	STATUS current
	DESCRIPTION
        "
        List of pmo6006MondwRmonCrcErrorsCounterClientInput 
        Article
        "
	::= { pmo6006MonClientRmonCounter 224 }


pmo6006MondwRmonCrcErrorsCounterClientInputEntry OBJECT-TYPE
	SYNTAX Pmo6006MondwRmonCrcErrorsCounterClientInputEntry
	MAX-ACCESS not-accessible
	STATUS current
	DESCRIPTION
        "
        Row definition for the pmo6006MondwRmonCrcErrorsCounterClientInput 
        table
        "
	INDEX   { pmo6006MondwRmonCrcErrorsCounterClientInputIndex }
	::= { pmo6006MondwRmonCrcErrorsCounterClientInputTable 1 }


Pmo6006MondwRmonCrcErrorsCounterClientInputEntry ::=
	SEQUENCE {
	pmo6006MondwRmonCrcErrorsCounterClientInputIndex
		INTEGER,
	pmo6006MondwRmonCrcErrorsCounterClientInputValuePortn
		Counter64,
	pmo6006MondwRmonCrcErrorsCounterClientInputErrorPortn
		EkiOnOff,
	pmo6006MondwRmonCrcErrorsCounterClientInputOverloadPortn
		EkiOnOff
	}


pmo6006MondwRmonCrcErrorsCounterClientInputIndex OBJECT-TYPE
	SYNTAX  INTEGER(0..128)
	MAX-ACCESS  read-only
	STATUS current
	DESCRIPTION
        "
        Index definition for the pmo6006MondwRmonCrcErrorsCounterClientInput 
        table
        "
	::= { pmo6006MondwRmonCrcErrorsCounterClientInputEntry 1 }


pmo6006MondwRmonCrcErrorsCounterClientInputValuePortn OBJECT-TYPE
	SYNTAX  Counter64
	MAX-ACCESS read-only
	STATUS current
	DESCRIPTION
        "
        Client Output B1/CRC Errors :This 
        counter is increased each time
         a B1/FCS error is detected on
         the output client port  <Help> 
         This counter gives the number
         of B1/CRC Errors detected on the 
        client port
        "
	::= { pmo6006MondwRmonCrcErrorsCounterClientInputEntry 2 }


pmo6006MondwRmonCrcErrorsCounterClientInputErrorPortn OBJECT-TYPE
	SYNTAX  EkiOnOff
	MAX-ACCESS read-only
	STATUS current
	DESCRIPTION
        "
        Output B1/FCS Errors Counter Error 
        :This OID when set indicates the 
        output B1/FCS Errors counter value 
        is invalid on client port
        "
	::= { pmo6006MondwRmonCrcErrorsCounterClientInputEntry 3 }


pmo6006MondwRmonCrcErrorsCounterClientInputOverloadPortn OBJECT-TYPE
	SYNTAX  EkiOnOff
	MAX-ACCESS read-only
	STATUS current
	DESCRIPTION
        "
        Output B1/FCS Errors Counter Overload 
        :This OID when set indicates an 
        output B1/FCS Errors counter overload 
        on client port
        "
	::= { pmo6006MondwRmonCrcErrorsCounterClientInputEntry 4 }


--- *********************************************************
---     TABLE for the pmo6006MondwRmonPacketsCounterClientInput articles
--- *********************************************************

pmo6006MondwRmonPacketsCounterClientInputTable OBJECT-TYPE
	SYNTAX  SEQUENCE OF Pmo6006MondwRmonPacketsCounterClientInputEntry
	MAX-ACCESS not-accessible
	STATUS current
	DESCRIPTION
        "
        List of pmo6006MondwRmonPacketsCounterClientInput 
        Article
        "
	::= { pmo6006MonClientRmonCounter 240 }


pmo6006MondwRmonPacketsCounterClientInputEntry OBJECT-TYPE
	SYNTAX Pmo6006MondwRmonPacketsCounterClientInputEntry
	MAX-ACCESS not-accessible
	STATUS current
	DESCRIPTION
        "
        Row definition for the pmo6006MondwRmonPacketsCounterClientInput 
        table
        "
	INDEX   { pmo6006MondwRmonPacketsCounterClientInputIndex }
	::= { pmo6006MondwRmonPacketsCounterClientInputTable 1 }


Pmo6006MondwRmonPacketsCounterClientInputEntry ::=
	SEQUENCE {
	pmo6006MondwRmonPacketsCounterClientInputIndex
		INTEGER,
	pmo6006MondwRmonPacketsCounterClientInputValuePortn
		Counter64,
	pmo6006MondwRmonPacketsCounterClientInputErrorPortn
		EkiOnOff,
	pmo6006MondwRmonPacketsCounterClientInputOverloadPortn
		EkiOnOff
	}


pmo6006MondwRmonPacketsCounterClientInputIndex OBJECT-TYPE
	SYNTAX  INTEGER(0..128)
	MAX-ACCESS  read-only
	STATUS current
	DESCRIPTION
        "
        Index definition for the pmo6006MondwRmonPacketsCounterClientInput 
        table
        "
	::= { pmo6006MondwRmonPacketsCounterClientInputEntry 1 }


pmo6006MondwRmonPacketsCounterClientInputValuePortn OBJECT-TYPE
	SYNTAX  Counter64
	MAX-ACCESS read-only
	STATUS current
	DESCRIPTION
        "
        Client Output Packets :This counter 
        is increased each time a packet 
        is transmitted on the client port. 
         <Help>  This counter gives the 
        number of packets detected on the 
        client port
        "
	::= { pmo6006MondwRmonPacketsCounterClientInputEntry 2 }


pmo6006MondwRmonPacketsCounterClientInputErrorPortn OBJECT-TYPE
	SYNTAX  EkiOnOff
	MAX-ACCESS read-only
	STATUS current
	DESCRIPTION
        "
        Output Packets Counter Error :This 
        OID when set indicates the output 
        Packets counter value is invalid 
        on client port
        "
	::= { pmo6006MondwRmonPacketsCounterClientInputEntry 3 }


pmo6006MondwRmonPacketsCounterClientInputOverloadPortn OBJECT-TYPE
	SYNTAX  EkiOnOff
	MAX-ACCESS read-only
	STATUS current
	DESCRIPTION
        "
        Output Packets Counter Overload 
        :This OID when set indicates an 
        output Packets counter overload 
        on client port
        "
	::= { pmo6006MondwRmonPacketsCounterClientInputEntry 4 }


pmo6006MonCountersReset  OBJECT-TYPE
	SYNTAX EkiOnOff
	MAX-ACCESS read-write
	STATUS current
	DESCRIPTION
	"RMON Counters Reset:This OID resets and restarts all the RMON counters"
	::= { pmo6006MonRmon   359 }

pmo6006MonCountersStop  OBJECT-TYPE
	SYNTAX EkiOnOff
	MAX-ACCESS read-write
	STATUS current
	DESCRIPTION
	"RMON Counters stop:This OID stops all the RMON counters"
	::= { pmo6006MonRmon  360 }






--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



--- *********************************************************
---     TABLE for the pmo6006MesrclientTemp articles
--- *********************************************************

pmo6006MesrclientTempTable OBJECT-TYPE
	SYNTAX  SEQUENCE OF Pmo6006MesrclientTempEntry
	MAX-ACCESS not-accessible
	STATUS current
	DESCRIPTION
        "
        List of pmo6006MesrclientTemp
         Article
        "
	::= { pmo6006MesrClient 16 }


pmo6006MesrclientTempEntry OBJECT-TYPE
	SYNTAX Pmo6006MesrclientTempEntry
	MAX-ACCESS not-accessible
	STATUS current
	DESCRIPTION
        "
        Row definition for the pmo6006MesrclientTemp 
        table
        "
	INDEX   { pmo6006MesrclientTempIndex }
	::= { pmo6006MesrclientTempTable 1 }


Pmo6006MesrclientTempEntry ::=
	SEQUENCE {
	pmo6006MesrclientTempIndex
		INTEGER,
	pmo6006MesrclientTempPortn
		INTEGER 
	}


pmo6006MesrclientTempIndex OBJECT-TYPE
	SYNTAX  INTEGER(0..128)
	MAX-ACCESS  read-only
	STATUS current
	DESCRIPTION
        "
        Index definition for the pmo6006MesrclientTemp 
        table
        "
	::= { pmo6006MesrclientTempEntry 1 }


pmo6006MesrclientTempPortn OBJECT-TYPE
	SYNTAX  INTEGER (0..65535)
	MAX-ACCESS read-only
	STATUS current
	DESCRIPTION
        "
        Client SFP Temperature :This OID 
        gives the Laser temperature value 
        of the Client Transceiver, read 
        from the DDM (Digital Diagnostic 
        Monitoring) (Temperature = AV/256) 
        (Unit = C) <Help> This Measure
         gives the Laser temperature value 
        of the Client Transceiver
        "
	::= { pmo6006MesrclientTempEntry 2 }


--- *********************************************************
---     TABLE for the pmo6006MesrclientTxBias articles
--- *********************************************************

pmo6006MesrclientTxBiasTable OBJECT-TYPE
	SYNTAX  SEQUENCE OF Pmo6006MesrclientTxBiasEntry
	MAX-ACCESS not-accessible
	STATUS current
	DESCRIPTION
        "
        List of pmo6006MesrclientTxBias 
        Article
        "
	::= { pmo6006MesrClient 32 }


pmo6006MesrclientTxBiasEntry OBJECT-TYPE
	SYNTAX Pmo6006MesrclientTxBiasEntry
	MAX-ACCESS not-accessible
	STATUS current
	DESCRIPTION
        "
        Row definition for the pmo6006MesrclientTxBias 
        table
        "
	INDEX   { pmo6006MesrclientTxBiasIndex }
	::= { pmo6006MesrclientTxBiasTable 1 }


Pmo6006MesrclientTxBiasEntry ::=
	SEQUENCE {
	pmo6006MesrclientTxBiasIndex
		INTEGER,
	pmo6006MesrclientTxBiasPortn
		INTEGER 
	}


pmo6006MesrclientTxBiasIndex OBJECT-TYPE
	SYNTAX  INTEGER(0..128)
	MAX-ACCESS  read-only
	STATUS current
	DESCRIPTION
        "
        Index definition for the pmo6006MesrclientTxBias 
        table
        "
	::= { pmo6006MesrclientTxBiasEntry 1 }


pmo6006MesrclientTxBiasPortn OBJECT-TYPE
	SYNTAX  INTEGER (0..65535)
	MAX-ACCESS read-only
	STATUS current
	DESCRIPTION
        "
        Client SFP Laser Bias :This OID 
        gives the Laser bias value of the 
        Client Transceiver, read from the 
        DDM (Digital Diagnostic Monitoring) 
        (Bias = AV/500) (Unit = mA) <Help> 
        This Measure gives the Laser bias 
        value of the Client Transceiver
        "
	::= { pmo6006MesrclientTxBiasEntry 2 }


--- *********************************************************
---     TABLE for the pmo6006MesrclientTxPwr articles
--- *********************************************************

pmo6006MesrclientTxPwrTable OBJECT-TYPE
	SYNTAX  SEQUENCE OF Pmo6006MesrclientTxPwrEntry
	MAX-ACCESS not-accessible
	STATUS current
	DESCRIPTION
        "
        List of pmo6006MesrclientTxPwr 
        Article
        "
	::= { pmo6006MesrClient 48 }


pmo6006MesrclientTxPwrEntry OBJECT-TYPE
	SYNTAX Pmo6006MesrclientTxPwrEntry
	MAX-ACCESS not-accessible
	STATUS current
	DESCRIPTION
        "
        Row definition for the pmo6006MesrclientTxPwr 
        table
        "
	INDEX   { pmo6006MesrclientTxPwrIndex }
	::= { pmo6006MesrclientTxPwrTable 1 }


Pmo6006MesrclientTxPwrEntry ::=
	SEQUENCE {
	pmo6006MesrclientTxPwrIndex
		INTEGER,
	pmo6006MesrclientTxPwrPortn
		INTEGER 
	}


pmo6006MesrclientTxPwrIndex OBJECT-TYPE
	SYNTAX  INTEGER(0..128)
	MAX-ACCESS  read-only
	STATUS current
	DESCRIPTION
        "
        Index definition for the pmo6006MesrclientTxPwr 
        table
        "
	::= { pmo6006MesrclientTxPwrEntry 1 }


pmo6006MesrclientTxPwrPortn OBJECT-TYPE
	SYNTAX  INTEGER (0..65535)
	MAX-ACCESS read-only
	STATUS current
	DESCRIPTION
        "
        Client SFP Tx Power :This OID
         gives the transmit power value 
        of the Client Transceiver, read 
        from the DDM (Digital Diagnostic 
        Monitoring) (Power = 10*log(AV)-40) 
        (Unit = dBm) <Help> This Measure 
        gives the transmit power value
         of the Client Transceiver
        "
	::= { pmo6006MesrclientTxPwrEntry 2 }


--- *********************************************************
---     TABLE for the pmo6006MesrclientRxPwr articles
--- *********************************************************

pmo6006MesrclientRxPwrTable OBJECT-TYPE
	SYNTAX  SEQUENCE OF Pmo6006MesrclientRxPwrEntry
	MAX-ACCESS not-accessible
	STATUS current
	DESCRIPTION
        "
        List of pmo6006MesrclientRxPwr 
        Article
        "
	::= { pmo6006MesrClient 64 }


pmo6006MesrclientRxPwrEntry OBJECT-TYPE
	SYNTAX Pmo6006MesrclientRxPwrEntry
	MAX-ACCESS not-accessible
	STATUS current
	DESCRIPTION
        "
        Row definition for the pmo6006MesrclientRxPwr 
        table
        "
	INDEX   { pmo6006MesrclientRxPwrIndex }
	::= { pmo6006MesrclientRxPwrTable 1 }


Pmo6006MesrclientRxPwrEntry ::=
	SEQUENCE {
	pmo6006MesrclientRxPwrIndex
		INTEGER,
	pmo6006MesrclientRxPwrPortn
		INTEGER 
	}


pmo6006MesrclientRxPwrIndex OBJECT-TYPE
	SYNTAX  INTEGER(0..128)
	MAX-ACCESS  read-only
	STATUS current
	DESCRIPTION
        "
        Index definition for the pmo6006MesrclientRxPwr 
        table
        "
	::= { pmo6006MesrclientRxPwrEntry 1 }


pmo6006MesrclientRxPwrPortn OBJECT-TYPE
	SYNTAX  INTEGER (0..65535)
	MAX-ACCESS read-only
	STATUS current
	DESCRIPTION
        "
        Client SFP Rx Power :This OID
         gives the receive power value
         of the Client Transceiver, read 
        in the DDM (Digital Diagnostic
         Monitoring) (Power = 10*log(AV)-40) 
        (Unit = dBm) <Help> This Measure 
        gives the receive power value of 
        the Client Transceiver
        "
	::= { pmo6006MesrclientRxPwrEntry 2 }


--- *********************************************************
---     TABLE for the pmo6006MesrlineTxPwr articles
--- *********************************************************

pmo6006MesrlineTxPwrTable OBJECT-TYPE
	SYNTAX  SEQUENCE OF Pmo6006MesrlineTxPwrEntry
	MAX-ACCESS not-accessible
	STATUS current
	DESCRIPTION
        "
        List of pmo6006MesrlineTxPwr Article
        "
	::= { pmo6006MesrLine 80 }


pmo6006MesrlineTxPwrEntry OBJECT-TYPE
	SYNTAX Pmo6006MesrlineTxPwrEntry
	MAX-ACCESS not-accessible
	STATUS current
	DESCRIPTION
        "
        Row definition for the pmo6006MesrlineTxPwr 
        table
        "
	INDEX   { pmo6006MesrlineTxPwrIndex }
	::= { pmo6006MesrlineTxPwrTable 1 }


Pmo6006MesrlineTxPwrEntry ::=
	SEQUENCE {
	pmo6006MesrlineTxPwrIndex
		INTEGER,
	pmo6006MesrlineTxPwrPortn
		INTEGER 
	}


pmo6006MesrlineTxPwrIndex OBJECT-TYPE
	SYNTAX  INTEGER(0..128)
	MAX-ACCESS  read-only
	STATUS current
	DESCRIPTION
        "
        Index definition for the pmo6006MesrlineTxPwr 
        table
        "
	::= { pmo6006MesrlineTxPwrEntry 1 }


pmo6006MesrlineTxPwrPortn OBJECT-TYPE
	SYNTAX  INTEGER (0..65535)
	MAX-ACCESS read-only
	STATUS current
	DESCRIPTION
        "
        Line Optical Module Tx Power :This 
        OID gives the Tx Laser transmit 
        power value of the Line Transceiver, 
        read in the DDM (Digital Diagnostic 
        Monitoring) (Power = 10*log(AV)-40) 
        (Unit = dBm) <Help> This Measure 
        gives the Tx Laser transmit power 
        value of the Line Transceiver
        "
	::= { pmo6006MesrlineTxPwrEntry 2 }


--- *********************************************************
---     TABLE for the pmo6006MesrlineTemp articles
--- *********************************************************

pmo6006MesrlineTempTable OBJECT-TYPE
	SYNTAX  SEQUENCE OF Pmo6006MesrlineTempEntry
	MAX-ACCESS not-accessible
	STATUS current
	DESCRIPTION
        "
        List of pmo6006MesrlineTemp Article
        "
	::= { pmo6006MesrLine 96 }


pmo6006MesrlineTempEntry OBJECT-TYPE
	SYNTAX Pmo6006MesrlineTempEntry
	MAX-ACCESS not-accessible
	STATUS current
	DESCRIPTION
        "
        Row definition for the pmo6006MesrlineTemp 
        table
        "
	INDEX   { pmo6006MesrlineTempIndex }
	::= { pmo6006MesrlineTempTable 1 }


Pmo6006MesrlineTempEntry ::=
	SEQUENCE {
	pmo6006MesrlineTempIndex
		INTEGER,
	pmo6006MesrlineTempPortn
		INTEGER 
	}


pmo6006MesrlineTempIndex OBJECT-TYPE
	SYNTAX  INTEGER(0..128)
	MAX-ACCESS  read-only
	STATUS current
	DESCRIPTION
        "
        Index definition for the pmo6006MesrlineTemp 
        table
        "
	::= { pmo6006MesrlineTempEntry 1 }


pmo6006MesrlineTempPortn OBJECT-TYPE
	SYNTAX  INTEGER (0..65535)
	MAX-ACCESS read-only
	STATUS current
	DESCRIPTION
        "
        Line Optical Module Temperature 
        :This OID gives the Tx Laser Temperature 
        value of the Line Transceiver,
         read from the DDM (Digital Diagnostic 
        Monitoring) (Temperature = AV/256) 
        (Unit = C) <Help> This Measure
         gives the Tx Laser Temperature 
        value of the Line Transceiver
        "
	::= { pmo6006MesrlineTempEntry 2 }


--- *********************************************************
---     TABLE for the pmo6006MesrlineTxBias articles
--- *********************************************************

pmo6006MesrlineTxBiasTable OBJECT-TYPE
	SYNTAX  SEQUENCE OF Pmo6006MesrlineTxBiasEntry
	MAX-ACCESS not-accessible
	STATUS current
	DESCRIPTION
        "
        List of pmo6006MesrlineTxBias
         Article
        "
	::= { pmo6006MesrLine 112 }


pmo6006MesrlineTxBiasEntry OBJECT-TYPE
	SYNTAX Pmo6006MesrlineTxBiasEntry
	MAX-ACCESS not-accessible
	STATUS current
	DESCRIPTION
        "
        Row definition for the pmo6006MesrlineTxBias 
        table
        "
	INDEX   { pmo6006MesrlineTxBiasIndex }
	::= { pmo6006MesrlineTxBiasTable 1 }


Pmo6006MesrlineTxBiasEntry ::=
	SEQUENCE {
	pmo6006MesrlineTxBiasIndex
		INTEGER,
	pmo6006MesrlineTxBiasPortn
		INTEGER 
	}


pmo6006MesrlineTxBiasIndex OBJECT-TYPE
	SYNTAX  INTEGER(0..128)
	MAX-ACCESS  read-only
	STATUS current
	DESCRIPTION
        "
        Index definition for the pmo6006MesrlineTxBias 
        table
        "
	::= { pmo6006MesrlineTxBiasEntry 1 }


pmo6006MesrlineTxBiasPortn OBJECT-TYPE
	SYNTAX  INTEGER (0..65535)
	MAX-ACCESS read-only
	STATUS current
	DESCRIPTION
        "
        Line Optical Module Laser Bias 
        :This OID gives the Tx Laser Bias 
        value of the Line Transceiver,
         read from the DDM (Digital Diagnostic 
        Monitoring) (Bias = AV/500) (Unit 
        = mA) <Help> This Measure gives 
        the Tx Laser Bias value of the
         Line Transceiver
        "
	::= { pmo6006MesrlineTxBiasEntry 2 }


--- *********************************************************
---     TABLE for the pmo6006MesrlineRxPwr articles
--- *********************************************************

pmo6006MesrlineRxPwrTable OBJECT-TYPE
	SYNTAX  SEQUENCE OF Pmo6006MesrlineRxPwrEntry
	MAX-ACCESS not-accessible
	STATUS current
	DESCRIPTION
        "
        List of pmo6006MesrlineRxPwr Article
        "
	::= { pmo6006MesrLine 128 }


pmo6006MesrlineRxPwrEntry OBJECT-TYPE
	SYNTAX Pmo6006MesrlineRxPwrEntry
	MAX-ACCESS not-accessible
	STATUS current
	DESCRIPTION
        "
        Row definition for the pmo6006MesrlineRxPwr 
        table
        "
	INDEX   { pmo6006MesrlineRxPwrIndex }
	::= { pmo6006MesrlineRxPwrTable 1 }


Pmo6006MesrlineRxPwrEntry ::=
	SEQUENCE {
	pmo6006MesrlineRxPwrIndex
		INTEGER,
	pmo6006MesrlineRxPwrPortn
		INTEGER 
	}


pmo6006MesrlineRxPwrIndex OBJECT-TYPE
	SYNTAX  INTEGER(0..128)
	MAX-ACCESS  read-only
	STATUS current
	DESCRIPTION
        "
        Index definition for the pmo6006MesrlineRxPwr 
        table
        "
	::= { pmo6006MesrlineRxPwrEntry 1 }


pmo6006MesrlineRxPwrPortn OBJECT-TYPE
	SYNTAX  INTEGER (0..65535)
	MAX-ACCESS read-only
	STATUS current
	DESCRIPTION
        "
        Line Optical Module Rx Power :This 
        OID gives the Receive power value 
        of the Line Transceiver, read in 
        the DDM (Digital Diagnostic Monitoring) 
        (Power = 10*log(AV)-40) (Unit = 
        dBm) <Help> This Measure gives
         the Receive power value of the 
        Line Transceiver
        "
	::= { pmo6006MesrlineRxPwrEntry 2 }







--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pmo6006DwlrestartProcess OBJECT IDENTIFIER ::= { pmo6006DwlOther 0 }




pmo6006DwlColdRestartProcessed OBJECT-TYPE
	  SYNTAX EkiOnOff
	  MAX-ACCESS read-only
	  STATUS current
	  DESCRIPTION
        "
        Cold Restart :This OID indicates 
        that the module last restart was 
        a Cold RESTART
        "
	  ::= { pmo6006DwlrestartProcess 2 }



pmo6006DwlWarmRestartProcessed OBJECT-TYPE
	  SYNTAX EkiOnOff
	  MAX-ACCESS read-only
	  STATUS current
	  DESCRIPTION
        "
        Warm Restart :This OID indicates 
        that the module last restart was 
        a Warm RESTART
        "
	  ::= { pmo6006DwlrestartProcess 1 }



--- *****************************************************
---     LEAF for the swBanksUsed article
--- *****************************************************
pmo6006DwlswBanksUsed OBJECT IDENTIFIER ::= { pmo6006DwlOther 1 }




pmo6006DwlSwBank2Notempty OBJECT-TYPE
	  SYNTAX EkiOnOff
	  MAX-ACCESS read-only
	  STATUS current
	  DESCRIPTION
        "
        SW bank 2 loaded :This OID indicates 
        a software is loaded in SW bank 
        2  <Help>  This status indicates 
        if the SW bank 2 contains SW package
        "
	  ::= { pmo6006DwlswBanksUsed 6 }



pmo6006DwlSwBank1Notempty OBJECT-TYPE
	  SYNTAX EkiOnOff
	  MAX-ACCESS read-only
	  STATUS current
	  DESCRIPTION
        "
        SW bank 1 loaded :This OID indicates 
        a software is loaded in SW bank 
        1  <Help>  This status indicates 
        if the SW bank 1 contains SW package
        "
	  ::= { pmo6006DwlswBanksUsed 5 }



pmo6006DwlSwBank2Used OBJECT-TYPE
	  SYNTAX EkiOnOff
	  MAX-ACCESS read-only
	  STATUS current
	  DESCRIPTION
        "
        SW bank 2 active :This OID indicates 
        the module is working on SW bank 
        2  <Help>  This status indicates 
        if the SW bank 2 is active or standby
        "
	  ::= { pmo6006DwlswBanksUsed 2 }



pmo6006DwlSwBank1Used OBJECT-TYPE
	  SYNTAX EkiOnOff
	  MAX-ACCESS read-only
	  STATUS current
	  DESCRIPTION
        "
        SW bank 1 active :This OID indicates 
        the module is working on SW bank 
        1  <Help>  This status indicates 
        if the SW bank 1 is active or standby
        "
	  ::= { pmo6006DwlswBanksUsed 1 }



--- *****************************************************
---     LEAF for the gwBanksUsed article
--- *****************************************************
pmo6006DwlgwBanksUsed OBJECT IDENTIFIER ::= { pmo6006DwlOther 2 }




pmo6006DwlGwBank4Notempty OBJECT-TYPE
	  SYNTAX EkiOnOff
	  MAX-ACCESS read-only
	  STATUS current
	  DESCRIPTION
        "
        GW bank 4 loaded :This OID indicates 
        a gateware is loaded in GW bank 
        4
        "
	  ::= { pmo6006DwlgwBanksUsed 8 }



pmo6006DwlGwBank3Notempty OBJECT-TYPE
	  SYNTAX EkiOnOff
	  MAX-ACCESS read-only
	  STATUS current
	  DESCRIPTION
        "
        GW bank 3 loaded :This OID indicates 
        a gateware is loaded in GW bank 
        3  <Help>  This status indicates 
        if the GW bank 3 contains GW package
        "
	  ::= { pmo6006DwlgwBanksUsed 7 }



pmo6006DwlGwBank2Notempty OBJECT-TYPE
	  SYNTAX EkiOnOff
	  MAX-ACCESS read-only
	  STATUS current
	  DESCRIPTION
        "
        GW bank 2 loaded :This OID indicates 
        a gateware is loaded in GW bank 
        2
        "
	  ::= { pmo6006DwlgwBanksUsed 6 }



pmo6006DwlGwBank1Notempty OBJECT-TYPE
	  SYNTAX EkiOnOff
	  MAX-ACCESS read-only
	  STATUS current
	  DESCRIPTION
        "
        GW bank 1 loaded :This OID indicates 
        a gateware is loaded in GW bank 
        1  <Help>  This status indicates 
        if the GW bank 1 contains GW package
        "
	  ::= { pmo6006DwlgwBanksUsed 5 }



pmo6006DwlGwBank4Used OBJECT-TYPE
	  SYNTAX EkiOnOff
	  MAX-ACCESS read-only
	  STATUS current
	  DESCRIPTION
        "
        GW bank 4 active :This OID indicates 
        the module is working on GW bank 
        4
        "
	  ::= { pmo6006DwlgwBanksUsed 4 }



pmo6006DwlGwBank3Used OBJECT-TYPE
	  SYNTAX EkiOnOff
	  MAX-ACCESS read-only
	  STATUS current
	  DESCRIPTION
        "
        GW bank 3 active :This OID indicates 
        the module is working on GW bank 
        3  <Help>  This status indicates 
        if the GW bank 3 is active or standby
        "
	  ::= { pmo6006DwlgwBanksUsed 3 }



pmo6006DwlGwBank2Used OBJECT-TYPE
	  SYNTAX EkiOnOff
	  MAX-ACCESS read-only
	  STATUS current
	  DESCRIPTION
        "
        GW bank 2 active :This OID indicates 
        the module is working on GW bank 
        2
        "
	  ::= { pmo6006DwlgwBanksUsed 2 }



pmo6006DwlGwBank1Used OBJECT-TYPE
	  SYNTAX EkiOnOff
	  MAX-ACCESS read-only
	  STATUS current
	  DESCRIPTION
        "
        GW bank 1 active :This OID indicates 
        the module is working on GW bank 
        1  <Help>  This status indicates 
        if the GW bank 1 is active or standby
        "
	  ::= { pmo6006DwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group startup
--- *****************************************************

pmo6006CfgStartup OBJECT IDENTIFIER ::= { pmo6006Config 1 }



--- *****************************************************
---     LEAF for the table 2110
--- *****************************************************

pmo6006CfgClientStartupTable OBJECT-TYPE
	SYNTAX  SEQUENCE OF Pmo6006CfgClientStartupEntry
	MAX-ACCESS not-accessible
	STATUS current
	DESCRIPTION
        "
        List of  Article
        "
	::= { pmo6006CfgStartup 1 }


pmo6006CfgClientStartupEntry OBJECT-TYPE
	SYNTAX Pmo6006CfgClientStartupEntry
	MAX-ACCESS not-accessible
	STATUS current
	DESCRIPTION
        "
        Row definition for the startup 
        table
        "
	INDEX   { pmo6006CfgClientStartupIndex }
	::= { pmo6006CfgClientStartupTable 1 }


Pmo6006CfgClientStartupEntry ::=
	SEQUENCE {
	pmo6006CfgClientStartupIndex
		INTEGER,
	pmo6006CfgSystConfPortPortn
		Unsigned32,
	pmo6006CfgNetConfPortPortn
		Unsigned32,
	pmo6006CfgOptionsPortPortn
		Unsigned32
	}


pmo6006CfgClientStartupIndex OBJECT-TYPE
	SYNTAX  INTEGER(0..128)
	MAX-ACCESS  read-only
	STATUS current
	DESCRIPTION
        "
        Index definition for the clientStartup 
        table
        "
	::= { pmo6006CfgClientStartupEntry 1 }


pmo6006CfgSystConfPortPortn OBJECT-TYPE
	SYNTAX  Unsigned32 (0..65536)
	MAX-ACCESS read-write
	STATUS current
	DESCRIPTION
        "
        Default Settings on Client Port 
        :This  register configures the
         default initialisation settings 
        on the port.
        "
	::= { pmo6006CfgClientStartupEntry 3 }


pmo6006CfgNetConfPortPortn OBJECT-TYPE
	SYNTAX  Unsigned32 (0..65536)
	MAX-ACCESS read-write
	STATUS current
	DESCRIPTION
        "
        Default Settings on Client Port 
        :This  register configures the
         default initialisation settings 
        on the port.
        "
	::= { pmo6006CfgClientStartupEntry 4 }


pmo6006CfgOptionsPortPortn OBJECT-TYPE
	SYNTAX  Unsigned32 (0..65536)
	MAX-ACCESS read-write
	STATUS current
	DESCRIPTION
        "
        Default Options on Client Port 
        :This register configures the default 
        options on the port.
        "
	::= { pmo6006CfgClientStartupEntry 14 }


--- *****************************************************
---     LEAF for the table 2190
--- *****************************************************

pmo6006CfgLinexr1StartupTable OBJECT-TYPE
	SYNTAX  SEQUENCE OF Pmo6006CfgLinexr1StartupEntry
	MAX-ACCESS not-accessible
	STATUS current
	DESCRIPTION
        "
        List of  Article
        "
	::= { pmo6006CfgStartup 2 }


pmo6006CfgLinexr1StartupEntry OBJECT-TYPE
	SYNTAX Pmo6006CfgLinexr1StartupEntry
	MAX-ACCESS not-accessible
	STATUS current
	DESCRIPTION
        "
        Row definition for the startup 
        table
        "
	INDEX   { pmo6006CfgLinexr1StartupIndex }
	::= { pmo6006CfgLinexr1StartupTable 1 }


Pmo6006CfgLinexr1StartupEntry ::=
	SEQUENCE {
	pmo6006CfgLinexr1StartupIndex
		INTEGER,
	pmo6006CfgSystConfLinePortn
		Unsigned32,
	pmo6006CfgOptionsLinePortn
		Unsigned32
	}


pmo6006CfgLinexr1StartupIndex OBJECT-TYPE
	SYNTAX  INTEGER(0..128)
	MAX-ACCESS  read-only
	STATUS current
	DESCRIPTION
        "
        Index definition for the linexr1Startup 
        table
        "
	::= { pmo6006CfgLinexr1StartupEntry 1 }


pmo6006CfgSystConfLinePortn OBJECT-TYPE
	SYNTAX  Unsigned32 (0..65536)
	MAX-ACCESS read-write
	STATUS current
	DESCRIPTION
        "
        Default Settings on Line :This 
        register configures the default 
        initialisation settings on Line
        "
	::= { pmo6006CfgLinexr1StartupEntry 3 }


pmo6006CfgOptionsLinePortn OBJECT-TYPE
	SYNTAX  Unsigned32 (0..65536)
	MAX-ACCESS read-write
	STATUS current
	DESCRIPTION
        "
        Default Options on Line :This
         register configures the default 
        options on the line
        "
	::= { pmo6006CfgLinexr1StartupEntry 14 }


--- *****************************************************
---     LEAF for the table 2710
--- *****************************************************

pmo6006CfgOtxtlhTable OBJECT-TYPE
	SYNTAX  SEQUENCE OF Pmo6006CfgOtxtlhEntry
	MAX-ACCESS not-accessible
	STATUS current
	DESCRIPTION
        "
        List of  Article
        "
	::= { pmo6006CfgStartup 3 }


pmo6006CfgOtxtlhEntry OBJECT-TYPE
	SYNTAX Pmo6006CfgOtxtlhEntry
	MAX-ACCESS not-accessible
	STATUS current
	DESCRIPTION
        "
        Row definition for the startup 
        table
        "
	INDEX   { pmo6006CfgOtxtlhIndex }
	::= { pmo6006CfgOtxtlhTable 1 }


Pmo6006CfgOtxtlhEntry ::=
	SEQUENCE {
	pmo6006CfgOtxtlhIndex
		INTEGER,
	pmo6006CfgLineControlsPortn
		Unsigned32,
	pmo6006CfgLinePwrLaserPortn
		Unsigned32,
	pmo6006CfgLineFCurrentPortn
		Unsigned32,
	pmo6006CfgLineGridCurrentPortn
		Unsigned32,
	pmo6006CfgLineFoPortn
		Unsigned32
	}


pmo6006CfgOtxtlhIndex OBJECT-TYPE
	SYNTAX  INTEGER(0..128)
	MAX-ACCESS  read-only
	STATUS current
	DESCRIPTION
        "
        Index definition for the otxtlh 
        table
        "
	::= { pmo6006CfgOtxtlhEntry 1 }


pmo6006CfgLineControlsPortn OBJECT-TYPE
	SYNTAX  Unsigned32 (0..65536)
	MAX-ACCESS read-write
	STATUS deprecated
	DESCRIPTION
        "
        Default Line settings :This register 
        configures the start-up settings 
        on the ports
        "
	::= { pmo6006CfgOtxtlhEntry 3 }


pmo6006CfgLinePwrLaserPortn OBJECT-TYPE
	SYNTAX  Unsigned32 (0..65536)
	MAX-ACCESS read-write
	STATUS current
	DESCRIPTION
        "
        Default Line output Power :This 
        register configures the start-up 
        output power of the client transceiver 
         (Unit = dBm)
        "
	::= { pmo6006CfgOtxtlhEntry 6 }


pmo6006CfgLineFCurrentPortn OBJECT-TYPE
	SYNTAX  Unsigned32 (0..65536)
	MAX-ACCESS read-write
	STATUS current
	DESCRIPTION
        "
        Default Line transceiver Channel 
        :This register configures the start-up 
        laser channel of the client  transceiver
        "
	::= { pmo6006CfgOtxtlhEntry 7 }


pmo6006CfgLineGridCurrentPortn OBJECT-TYPE
	SYNTAX  Unsigned32 (0..65536)
	MAX-ACCESS read-write
	STATUS current
	DESCRIPTION
        "
        Default Line transceiver Grid
         :This register configures the
         start-up laser grid of the client 
        transceiver
        "
	::= { pmo6006CfgOtxtlhEntry 8 }


pmo6006CfgLineFoPortn OBJECT-TYPE
	SYNTAX  Unsigned32 (0..65536)
	MAX-ACCESS read-write
	STATUS current
	DESCRIPTION
        "
        Default Line first Frequency :This 
        register configures the start-up 
        first frequency of the client transceiver
        "
	::= { pmo6006CfgOtxtlhEntry 9 }


--- *****************************************************
---     LEAF for the table 2610
--- *****************************************************

pmo6006CfgClientOtxtlhTable OBJECT-TYPE
	SYNTAX  SEQUENCE OF Pmo6006CfgClientOtxtlhEntry
	MAX-ACCESS not-accessible
	STATUS current
	DESCRIPTION
        "
        List of  Article
        "
	::= { pmo6006CfgStartup 4 }


pmo6006CfgClientOtxtlhEntry OBJECT-TYPE
	SYNTAX Pmo6006CfgClientOtxtlhEntry
	MAX-ACCESS not-accessible
	STATUS current
	DESCRIPTION
        "
        Row definition for the startup 
        table
        "
	INDEX   { pmo6006CfgClientOtxtlhIndex }
	::= { pmo6006CfgClientOtxtlhTable 1 }


Pmo6006CfgClientOtxtlhEntry ::=
	SEQUENCE {
	pmo6006CfgClientOtxtlhIndex
		INTEGER,
	pmo6006CfgControlsPortn
		Unsigned32,
	pmo6006CfgClientPwrLaserPortn
		Unsigned32,
	pmo6006CfgClientFCurrentPortn
		Unsigned32,
	pmo6006CfgClientGridCurrentPortn
		Unsigned32,
	pmo6006CfgClientFoPortn
		Unsigned32
	}


pmo6006CfgClientOtxtlhIndex OBJECT-TYPE
	SYNTAX  INTEGER(0..128)
	MAX-ACCESS  read-only
	STATUS current
	DESCRIPTION
        "
        Index definition for the clientOtxtlh 
        table
        "
	::= { pmo6006CfgClientOtxtlhEntry 1 }


pmo6006CfgControlsPortn OBJECT-TYPE
	SYNTAX  Unsigned32 (0..65536)
	MAX-ACCESS read-write
	STATUS deprecated
	DESCRIPTION
        "
        Defaut Client settings :This register 
        configures the start-up settings 
        on the ports
        "
	::= { pmo6006CfgClientOtxtlhEntry 3 }


pmo6006CfgClientPwrLaserPortn OBJECT-TYPE
	SYNTAX  Unsigned32 (0..65536)
	MAX-ACCESS read-write
	STATUS current
	DESCRIPTION
        "
        Defaut Client output Power :This 
        register configures the start-up 
        output power of the client transceiver 
         (Unit = dBm)
        "
	::= { pmo6006CfgClientOtxtlhEntry 6 }


pmo6006CfgClientFCurrentPortn OBJECT-TYPE
	SYNTAX  Unsigned32 (0..65536)
	MAX-ACCESS read-write
	STATUS current
	DESCRIPTION
        "
        Default Client transceiver Channel 
        :This register configures the start-up 
        laser channel of the client  transceiver
        "
	::= { pmo6006CfgClientOtxtlhEntry 7 }


pmo6006CfgClientGridCurrentPortn OBJECT-TYPE
	SYNTAX  Unsigned32 (0..65536)
	MAX-ACCESS read-write
	STATUS current
	DESCRIPTION
        "
        Default Client transceiver Grid 
        :This register configures the start-up 
        laser grid of the client transceiver
        "
	::= { pmo6006CfgClientOtxtlhEntry 8 }


pmo6006CfgClientFoPortn OBJECT-TYPE
	SYNTAX  Unsigned32 (0..65536)
	MAX-ACCESS read-write
	STATUS current
	DESCRIPTION
        "
        Default Client first Frequency 
        :This register configures the start-up 
        first frequency of the client transceiver
        "
	::= { pmo6006CfgClientOtxtlhEntry 9 }


--- *****************************************************
---     LEAF for the table Group labels
--- *****************************************************

pmo6006CfgLabels OBJECT IDENTIFIER ::= { pmo6006Config 2 }



--- *****************************************************
---     LEAF for the table 0003
--- *****************************************************

pmo6006CfgLabelclientTable OBJECT-TYPE
	SYNTAX  SEQUENCE OF Pmo6006CfgLabelclientEntry
	MAX-ACCESS not-accessible
	STATUS current
	DESCRIPTION
        "
        List of  Article
        "
	::= { pmo6006CfgLabels 1 }


pmo6006CfgLabelclientEntry OBJECT-TYPE
	SYNTAX Pmo6006CfgLabelclientEntry
	MAX-ACCESS not-accessible
	STATUS current
	DESCRIPTION
        "
        Row definition for the labels
         table
        "
	INDEX   { pmo6006CfgLabelclientIndex }
	::= { pmo6006CfgLabelclientTable 1 }


Pmo6006CfgLabelclientEntry ::=
	SEQUENCE {
	pmo6006CfgLabelclientIndex
		INTEGER,
	pmo6006CfgLabelclientPortn
		DisplayString
	}


pmo6006CfgLabelclientIndex OBJECT-TYPE
	SYNTAX  INTEGER(0..128)
	MAX-ACCESS  read-only
	STATUS current
	DESCRIPTION
        "
        Index definition for the labelclient 
        table
        "
	::= { pmo6006CfgLabelclientEntry 1 }


pmo6006CfgLabelclientPortn OBJECT-TYPE
	SYNTAX  DisplayString( SIZE(1..16))
	MAX-ACCESS read-write
	STATUS current
	DESCRIPTION
        "
        Default settings on the label
         of the Ports :These registers
         configures the default initialisation 
        settings of the labels of the ports.
        "
	::= { pmo6006CfgLabelclientEntry 3 }


--- *****************************************************
---     LEAF for the table 0004
--- *****************************************************

pmo6006CfgLabellineTable OBJECT-TYPE
	SYNTAX  SEQUENCE OF Pmo6006CfgLabellineEntry
	MAX-ACCESS not-accessible
	STATUS current
	DESCRIPTION
        "
        List of  Article
        "
	::= { pmo6006CfgLabels 2 }


pmo6006CfgLabellineEntry OBJECT-TYPE
	SYNTAX Pmo6006CfgLabellineEntry
	MAX-ACCESS not-accessible
	STATUS current
	DESCRIPTION
        "
        Row definition for the labels
         table
        "
	INDEX   { pmo6006CfgLabellineIndex }
	::= { pmo6006CfgLabellineTable 1 }


Pmo6006CfgLabellineEntry ::=
	SEQUENCE {
	pmo6006CfgLabellineIndex
		INTEGER,
	pmo6006CfgLabellinePortn
		DisplayString
	}


pmo6006CfgLabellineIndex OBJECT-TYPE
	SYNTAX  INTEGER(0..128)
	MAX-ACCESS  read-only
	STATUS current
	DESCRIPTION
        "
        Index definition for the labelline 
        table
        "
	::= { pmo6006CfgLabellineEntry 1 }


pmo6006CfgLabellinePortn OBJECT-TYPE
	SYNTAX  DisplayString( SIZE(1..16))
	MAX-ACCESS read-write
	STATUS current
	DESCRIPTION
        "
        Default settings on the label
         of the lines :These registers
         configures the default initialisation 
        settings of the labels of the lines.
        "
	::= { pmo6006CfgLabellineEntry 3 }


--- *****************************************************
---     LEAF for the table Group other
--- *****************************************************

pmo6006CfgOther OBJECT IDENTIFIER ::= { pmo6006Config 3 }



--- *****************************************************
---     LEAF for the table 2300
--- *****************************************************

pmo6006tablemoduleOther OBJECT IDENTIFIER ::= { pmo6006CfgOther 1 }



pmo6006Cfgmode OBJECT-TYPE
	  SYNTAX Unsigned32 (0..65536)
	  MAX-ACCESS read-write
	  STATUS current
	  DESCRIPTION
        "
        Default settings on Module :This 
        register selects the configuration 
        mode of the module
        "
	  ::= { pmo6006tablemoduleOther 2 }



--- *****************************************************
---     LEAF for the table Group odu2Clienta
--- *****************************************************

pmo6006CfgOdu2Clienta OBJECT IDENTIFIER ::= { pmo6006Config 4 }



--- *****************************************************
---     LEAF for the table 29C0
--- *****************************************************

pmo6006CfgClientStartupOduTable OBJECT-TYPE
	SYNTAX  SEQUENCE OF Pmo6006CfgClientStartupOduEntry
	MAX-ACCESS not-accessible
	STATUS current
	DESCRIPTION
        "
        List of  Article
        "
	::= { pmo6006CfgOdu2Clienta 1 }


pmo6006CfgClientStartupOduEntry OBJECT-TYPE
	SYNTAX Pmo6006CfgClientStartupOduEntry
	MAX-ACCESS not-accessible
	STATUS current
	DESCRIPTION
        "
        Row definition for the odu2Clienta 
        table
        "
	INDEX   { pmo6006CfgClientStartupOduIndex }
	::= { pmo6006CfgClientStartupOduTable 1 }


Pmo6006CfgClientStartupOduEntry ::=
	SEQUENCE {
	pmo6006CfgClientStartupOduIndex
		INTEGER,
	pmo6006CfgOdu2ReserveLsbPortn
		Unsigned32,
	pmo6006CfgOdu2DegthresholdPortn
		Unsigned32,
	pmo6006CfgOdu2DegmPortn
		Unsigned32,
	pmo6006CfgOdu2SettingsPortn
		Unsigned32
	}


pmo6006CfgClientStartupOduIndex OBJECT-TYPE
	SYNTAX  INTEGER(0..128)
	MAX-ACCESS  read-only
	STATUS current
	DESCRIPTION
        "
        Index definition for the clientStartupOdu 
        table
        "
	::= { pmo6006CfgClientStartupOduEntry 1 }


pmo6006CfgOdu2ReserveLsbPortn OBJECT-TYPE
	SYNTAX  Unsigned32 (0..65536)
	MAX-ACCESS read-write
	STATUS current
	DESCRIPTION
        "
        :
        "
	::= { pmo6006CfgClientStartupOduEntry 3 }


pmo6006CfgOdu2DegthresholdPortn OBJECT-TYPE
	SYNTAX  Unsigned32 (0..65536)
	MAX-ACCESS read-write
	STATUS current
	DESCRIPTION
        "
        ODU2 Degrade Threshold :
        "
	::= { pmo6006CfgClientStartupOduEntry 4 }


pmo6006CfgOdu2DegmPortn OBJECT-TYPE
	SYNTAX  Unsigned32 (0..65536)
	MAX-ACCESS read-write
	STATUS current
	DESCRIPTION
        "
        ODU2 Degrade Confirmation :
        "
	::= { pmo6006CfgClientStartupOduEntry 5 }


pmo6006CfgOdu2SettingsPortn OBJECT-TYPE
	SYNTAX  Unsigned32 (0..65536)
	MAX-ACCESS read-write
	STATUS current
	DESCRIPTION
        "
        ODU2 Settings :
        "
	::= { pmo6006CfgClientStartupOduEntry 6 }


--- *****************************************************
---     LEAF for the table Group otu2Line
--- *****************************************************

pmo6006CfgOtu2Line OBJECT IDENTIFIER ::= { pmo6006Config 5 }



--- *****************************************************
---     LEAF for the table 29E0
--- *****************************************************

pmo6006CfgLinexStartupOtuTable OBJECT-TYPE
	SYNTAX  SEQUENCE OF Pmo6006CfgLinexStartupOtuEntry
	MAX-ACCESS not-accessible
	STATUS current
	DESCRIPTION
        "
        List of  Article
        "
	::= { pmo6006CfgOtu2Line 1 }


pmo6006CfgLinexStartupOtuEntry OBJECT-TYPE
	SYNTAX Pmo6006CfgLinexStartupOtuEntry
	MAX-ACCESS not-accessible
	STATUS current
	DESCRIPTION
        "
        Row definition for the otu2Line 
        table
        "
	INDEX   { pmo6006CfgLinexStartupOtuIndex }
	::= { pmo6006CfgLinexStartupOtuTable 1 }


Pmo6006CfgLinexStartupOtuEntry ::=
	SEQUENCE {
	pmo6006CfgLinexStartupOtuIndex
		INTEGER,
	pmo6006CfgOtu2ReserveMsbPortn
		Unsigned32,
	pmo6006CfgOtu2DegthresholdPortn
		Unsigned32,
	pmo6006CfgOtu2DegmPortn
		Unsigned32,
	pmo6006CfgOtu2SettingsPortn
		Unsigned32
	}


pmo6006CfgLinexStartupOtuIndex OBJECT-TYPE
	SYNTAX  INTEGER(0..128)
	MAX-ACCESS  read-only
	STATUS current
	DESCRIPTION
        "
        Index definition for the linexStartupOtu 
        table
        "
	::= { pmo6006CfgLinexStartupOtuEntry 1 }


pmo6006CfgOtu2ReserveMsbPortn OBJECT-TYPE
	SYNTAX  Unsigned32 (0..65536)
	MAX-ACCESS read-write
	STATUS current
	DESCRIPTION
        "
        :
        "
	::= { pmo6006CfgLinexStartupOtuEntry 3 }


pmo6006CfgOtu2DegthresholdPortn OBJECT-TYPE
	SYNTAX  Unsigned32 (0..65536)
	MAX-ACCESS read-write
	STATUS current
	DESCRIPTION
        "
        OTU2 Degrade Threshold :
        "
	::= { pmo6006CfgLinexStartupOtuEntry 4 }


pmo6006CfgOtu2DegmPortn OBJECT-TYPE
	SYNTAX  Unsigned32 (0..65536)
	MAX-ACCESS read-write
	STATUS current
	DESCRIPTION
        "
        OTU2 Degrade Confirmation :
        "
	::= { pmo6006CfgLinexStartupOtuEntry 5 }


pmo6006CfgOtu2SettingsPortn OBJECT-TYPE
	SYNTAX  Unsigned32 (0..65536)
	MAX-ACCESS read-write
	STATUS current
	DESCRIPTION
        "
        OTU2 Settings :
        "
	::= { pmo6006CfgLinexStartupOtuEntry 6 }


--- *****************************************************
---     LEAF for the table Group sapiTxClient
--- *****************************************************

pmo6006CfgSapiTxClient OBJECT IDENTIFIER ::= { pmo6006Config 6 }



--- *****************************************************
---     LEAF for the table 2A10
--- *****************************************************

pmo6006CfgClientSapiTxOduTable OBJECT-TYPE
	SYNTAX  SEQUENCE OF Pmo6006CfgClientSapiTxOduEntry
	MAX-ACCESS not-accessible
	STATUS current
	DESCRIPTION
        "
        List of  Article
        "
	::= { pmo6006CfgSapiTxClient 1 }


pmo6006CfgClientSapiTxOduEntry OBJECT-TYPE
	SYNTAX Pmo6006CfgClientSapiTxOduEntry
	MAX-ACCESS not-accessible
	STATUS current
	DESCRIPTION
        "
        Row definition for the sapiTxClient 
        table
        "
	INDEX   { pmo6006CfgClientSapiTxOduIndex }
	::= { pmo6006CfgClientSapiTxOduTable 1 }


Pmo6006CfgClientSapiTxOduEntry ::=
	SEQUENCE {
	pmo6006CfgClientSapiTxOduIndex
		INTEGER,
	pmo6006CfgClientSapiTxSetupPortn
		DisplayString
	}


pmo6006CfgClientSapiTxOduIndex OBJECT-TYPE
	SYNTAX  INTEGER(0..128)
	MAX-ACCESS  read-only
	STATUS current
	DESCRIPTION
        "
        Index definition for the clientSapiTxOdu 
        table
        "
	::= { pmo6006CfgClientSapiTxOduEntry 1 }


pmo6006CfgClientSapiTxSetupPortn OBJECT-TYPE
	SYNTAX  DisplayString( SIZE(1..16))
	MAX-ACCESS read-write
	STATUS current
	DESCRIPTION
        "
        Client Transmitted SAPI :This
         register defines the value of
         the transmitted Trace Identifier 
        on the line output
        "
	::= { pmo6006CfgClientSapiTxOduEntry 3 }


--- *****************************************************
---     LEAF for the table Group sapiExpClient
--- *****************************************************

pmo6006CfgSapiExpClient OBJECT IDENTIFIER ::= { pmo6006Config 7 }



--- *****************************************************
---     LEAF for the table 2A30
--- *****************************************************

pmo6006CfgClientSapiExpOduTable OBJECT-TYPE
	SYNTAX  SEQUENCE OF Pmo6006CfgClientSapiExpOduEntry
	MAX-ACCESS not-accessible
	STATUS current
	DESCRIPTION
        "
        List of  Article
        "
	::= { pmo6006CfgSapiExpClient 1 }


pmo6006CfgClientSapiExpOduEntry OBJECT-TYPE
	SYNTAX Pmo6006CfgClientSapiExpOduEntry
	MAX-ACCESS not-accessible
	STATUS current
	DESCRIPTION
        "
        Row definition for the sapiExpClient 
        table
        "
	INDEX   { pmo6006CfgClientSapiExpOduIndex }
	::= { pmo6006CfgClientSapiExpOduTable 1 }


Pmo6006CfgClientSapiExpOduEntry ::=
	SEQUENCE {
	pmo6006CfgClientSapiExpOduIndex
		INTEGER,
	pmo6006CfgClientSapiExpSetupPortn
		DisplayString
	}


pmo6006CfgClientSapiExpOduIndex OBJECT-TYPE
	SYNTAX  INTEGER(0..128)
	MAX-ACCESS  read-only
	STATUS current
	DESCRIPTION
        "
        Index definition for the clientSapiExpOdu 
        table
        "
	::= { pmo6006CfgClientSapiExpOduEntry 1 }


pmo6006CfgClientSapiExpSetupPortn OBJECT-TYPE
	SYNTAX  DisplayString( SIZE(1..16))
	MAX-ACCESS read-write
	STATUS current
	DESCRIPTION
        "
        Client Expected SAPI :This register 
        defines the value of the expected 
        Trace Identifier on the line input
        "
	::= { pmo6006CfgClientSapiExpOduEntry 3 }


--- *****************************************************
---     LEAF for the table Group sapiAccClient
--- *****************************************************

pmo6006CfgSapiAccClient OBJECT IDENTIFIER ::= { pmo6006Config 8 }



--- *****************************************************
---     LEAF for the table 2A50
--- *****************************************************

pmo6006CfgClientSapiAccOduTable OBJECT-TYPE
	SYNTAX  SEQUENCE OF Pmo6006CfgClientSapiAccOduEntry
	MAX-ACCESS not-accessible
	STATUS current
	DESCRIPTION
        "
        List of  Article
        "
	::= { pmo6006CfgSapiAccClient 1 }


pmo6006CfgClientSapiAccOduEntry OBJECT-TYPE
	SYNTAX Pmo6006CfgClientSapiAccOduEntry
	MAX-ACCESS not-accessible
	STATUS current
	DESCRIPTION
        "
        Row definition for the sapiAccClient 
        table
        "
	INDEX   { pmo6006CfgClientSapiAccOduIndex }
	::= { pmo6006CfgClientSapiAccOduTable 1 }


Pmo6006CfgClientSapiAccOduEntry ::=
	SEQUENCE {
	pmo6006CfgClientSapiAccOduIndex
		INTEGER,
	pmo6006CfgClientSapiAccSetupPortn
		DisplayString
	}


pmo6006CfgClientSapiAccOduIndex OBJECT-TYPE
	SYNTAX  INTEGER(0..128)
	MAX-ACCESS  read-only
	STATUS current
	DESCRIPTION
        "
        Index definition for the clientSapiAccOdu 
        table
        "
	::= { pmo6006CfgClientSapiAccOduEntry 1 }


pmo6006CfgClientSapiAccSetupPortn OBJECT-TYPE
	SYNTAX  DisplayString( SIZE(1..16))
	MAX-ACCESS read-write
	STATUS deprecated
	DESCRIPTION
        "
        Client Accepted SAPI :This register 
        defines the value of the accepted 
        Trace Identifier on the line input
        "
	::= { pmo6006CfgClientSapiAccOduEntry 3 }


--- *****************************************************
---     LEAF for the table Group dapiTxClient
--- *****************************************************

pmo6006CfgDapiTxClient OBJECT IDENTIFIER ::= { pmo6006Config 9 }



--- *****************************************************
---     LEAF for the table 2A90
--- *****************************************************

pmo6006CfgClientDapiTxOduTable OBJECT-TYPE
	SYNTAX  SEQUENCE OF Pmo6006CfgClientDapiTxOduEntry
	MAX-ACCESS not-accessible
	STATUS current
	DESCRIPTION
        "
        List of  Article
        "
	::= { pmo6006CfgDapiTxClient 1 }


pmo6006CfgClientDapiTxOduEntry OBJECT-TYPE
	SYNTAX Pmo6006CfgClientDapiTxOduEntry
	MAX-ACCESS not-accessible
	STATUS current
	DESCRIPTION
        "
        Row definition for the dapiTxClient 
        table
        "
	INDEX   { pmo6006CfgClientDapiTxOduIndex }
	::= { pmo6006CfgClientDapiTxOduTable 1 }


Pmo6006CfgClientDapiTxOduEntry ::=
	SEQUENCE {
	pmo6006CfgClientDapiTxOduIndex
		INTEGER,
	pmo6006CfgClientDapiTxSetupPortn
		DisplayString
	}


pmo6006CfgClientDapiTxOduIndex OBJECT-TYPE
	SYNTAX  INTEGER(0..128)
	MAX-ACCESS  read-only
	STATUS current
	DESCRIPTION
        "
        Index definition for the clientDapiTxOdu 
        table
        "
	::= { pmo6006CfgClientDapiTxOduEntry 1 }


pmo6006CfgClientDapiTxSetupPortn OBJECT-TYPE
	SYNTAX  DisplayString( SIZE(1..16))
	MAX-ACCESS read-write
	STATUS current
	DESCRIPTION
        "
        Client Transmitted DAPI :This
         register defines the value of
         the transmitted Trace Identifier 
        on the line output
        "
	::= { pmo6006CfgClientDapiTxOduEntry 3 }


--- *****************************************************
---     LEAF for the table Group dapiExpClient
--- *****************************************************

pmo6006CfgDapiExpClient OBJECT IDENTIFIER ::= { pmo6006Config 10 }



--- *****************************************************
---     LEAF for the table 2AB0
--- *****************************************************

pmo6006CfgClientDapiExpOduTable OBJECT-TYPE
	SYNTAX  SEQUENCE OF Pmo6006CfgClientDapiExpOduEntry
	MAX-ACCESS not-accessible
	STATUS current
	DESCRIPTION
        "
        List of  Article
        "
	::= { pmo6006CfgDapiExpClient 1 }


pmo6006CfgClientDapiExpOduEntry OBJECT-TYPE
	SYNTAX Pmo6006CfgClientDapiExpOduEntry
	MAX-ACCESS not-accessible
	STATUS current
	DESCRIPTION
        "
        Row definition for the dapiExpClient 
        table
        "
	INDEX   { pmo6006CfgClientDapiExpOduIndex }
	::= { pmo6006CfgClientDapiExpOduTable 1 }


Pmo6006CfgClientDapiExpOduEntry ::=
	SEQUENCE {
	pmo6006CfgClientDapiExpOduIndex
		INTEGER,
	pmo6006CfgClientDapiExpSetupPortn
		DisplayString
	}


pmo6006CfgClientDapiExpOduIndex OBJECT-TYPE
	SYNTAX  INTEGER(0..128)
	MAX-ACCESS  read-only
	STATUS current
	DESCRIPTION
        "
        Index definition for the clientDapiExpOdu 
        table
        "
	::= { pmo6006CfgClientDapiExpOduEntry 1 }


pmo6006CfgClientDapiExpSetupPortn OBJECT-TYPE
	SYNTAX  DisplayString( SIZE(1..16))
	MAX-ACCESS read-write
	STATUS current
	DESCRIPTION
        "
        Client Expected DAPI :This register 
        defines the value of the expected 
        Trace Identifier on the line input
        "
	::= { pmo6006CfgClientDapiExpOduEntry 3 }


--- *****************************************************
---     LEAF for the table Group dapiAccClient
--- *****************************************************

pmo6006CfgDapiAccClient OBJECT IDENTIFIER ::= { pmo6006Config 11 }



--- *****************************************************
---     LEAF for the table 2AD0
--- *****************************************************

pmo6006CfgClientDapiAccOduTable OBJECT-TYPE
	SYNTAX  SEQUENCE OF Pmo6006CfgClientDapiAccOduEntry
	MAX-ACCESS not-accessible
	STATUS current
	DESCRIPTION
        "
        List of  Article
        "
	::= { pmo6006CfgDapiAccClient 1 }


pmo6006CfgClientDapiAccOduEntry OBJECT-TYPE
	SYNTAX Pmo6006CfgClientDapiAccOduEntry
	MAX-ACCESS not-accessible
	STATUS current
	DESCRIPTION
        "
        Row definition for the dapiAccClient 
        table
        "
	INDEX   { pmo6006CfgClientDapiAccOduIndex }
	::= { pmo6006CfgClientDapiAccOduTable 1 }


Pmo6006CfgClientDapiAccOduEntry ::=
	SEQUENCE {
	pmo6006CfgClientDapiAccOduIndex
		INTEGER,
	pmo6006CfgClientDapiAccSetupPortn
		DisplayString
	}


pmo6006CfgClientDapiAccOduIndex OBJECT-TYPE
	SYNTAX  INTEGER(0..128)
	MAX-ACCESS  read-only
	STATUS current
	DESCRIPTION
        "
        Index definition for the clientDapiAccOdu 
        table
        "
	::= { pmo6006CfgClientDapiAccOduEntry 1 }


pmo6006CfgClientDapiAccSetupPortn OBJECT-TYPE
	SYNTAX  DisplayString( SIZE(1..16))
	MAX-ACCESS read-write
	STATUS deprecated
	DESCRIPTION
        "
        Client Accepted DAPI :This register 
        defines the value of the accepted 
        Trace Identifier on the line input
        "
	::= { pmo6006CfgClientDapiAccOduEntry 3 }


--- *****************************************************
---     LEAF for the table Group sapiTxLine
--- *****************************************************

pmo6006CfgSapiTxLine OBJECT IDENTIFIER ::= { pmo6006Config 12 }



--- *****************************************************
---     LEAF for the table 2B10
--- *****************************************************

pmo6006CfgLineSapiTxOtuTable OBJECT-TYPE
	SYNTAX  SEQUENCE OF Pmo6006CfgLineSapiTxOtuEntry
	MAX-ACCESS not-accessible
	STATUS current
	DESCRIPTION
        "
        List of  Article
        "
	::= { pmo6006CfgSapiTxLine 1 }


pmo6006CfgLineSapiTxOtuEntry OBJECT-TYPE
	SYNTAX Pmo6006CfgLineSapiTxOtuEntry
	MAX-ACCESS not-accessible
	STATUS current
	DESCRIPTION
        "
        Row definition for the sapiTxLine 
        table
        "
	INDEX   { pmo6006CfgLineSapiTxOtuIndex }
	::= { pmo6006CfgLineSapiTxOtuTable 1 }


Pmo6006CfgLineSapiTxOtuEntry ::=
	SEQUENCE {
	pmo6006CfgLineSapiTxOtuIndex
		INTEGER,
	pmo6006CfgLineSapiTxSetupPortn
		DisplayString
	}


pmo6006CfgLineSapiTxOtuIndex OBJECT-TYPE
	SYNTAX  INTEGER(0..128)
	MAX-ACCESS  read-only
	STATUS current
	DESCRIPTION
        "
        Index definition for the lineSapiTxOtu 
        table
        "
	::= { pmo6006CfgLineSapiTxOtuEntry 1 }


pmo6006CfgLineSapiTxSetupPortn OBJECT-TYPE
	SYNTAX  DisplayString( SIZE(1..16))
	MAX-ACCESS read-write
	STATUS current
	DESCRIPTION
        "
        Line Transmitted SAPI :This register 
        defines the value of the transmitted 
        Trace Identifier on the line output
        "
	::= { pmo6006CfgLineSapiTxOtuEntry 3 }


--- *****************************************************
---     LEAF for the table Group sapiExpLine
--- *****************************************************

pmo6006CfgSapiExpLine OBJECT IDENTIFIER ::= { pmo6006Config 13 }



--- *****************************************************
---     LEAF for the table 2B30
--- *****************************************************

pmo6006CfgLineSapiExpOtuTable OBJECT-TYPE
	SYNTAX  SEQUENCE OF Pmo6006CfgLineSapiExpOtuEntry
	MAX-ACCESS not-accessible
	STATUS current
	DESCRIPTION
        "
        List of  Article
        "
	::= { pmo6006CfgSapiExpLine 1 }


pmo6006CfgLineSapiExpOtuEntry OBJECT-TYPE
	SYNTAX Pmo6006CfgLineSapiExpOtuEntry
	MAX-ACCESS not-accessible
	STATUS current
	DESCRIPTION
        "
        Row definition for the sapiExpLine 
        table
        "
	INDEX   { pmo6006CfgLineSapiExpOtuIndex }
	::= { pmo6006CfgLineSapiExpOtuTable 1 }


Pmo6006CfgLineSapiExpOtuEntry ::=
	SEQUENCE {
	pmo6006CfgLineSapiExpOtuIndex
		INTEGER,
	pmo6006CfgLineSapiExpSetupPortn
		DisplayString
	}


pmo6006CfgLineSapiExpOtuIndex OBJECT-TYPE
	SYNTAX  INTEGER(0..128)
	MAX-ACCESS  read-only
	STATUS current
	DESCRIPTION
        "
        Index definition for the lineSapiExpOtu 
        table
        "
	::= { pmo6006CfgLineSapiExpOtuEntry 1 }


pmo6006CfgLineSapiExpSetupPortn OBJECT-TYPE
	SYNTAX  DisplayString( SIZE(1..16))
	MAX-ACCESS read-write
	STATUS current
	DESCRIPTION
        "
        Line Expected SAPI :This register 
        defines the value of the expected 
        Trace Identifier on the line input
        "
	::= { pmo6006CfgLineSapiExpOtuEntry 3 }


--- *****************************************************
---     LEAF for the table Group sapiAccLine
--- *****************************************************

pmo6006CfgSapiAccLine OBJECT IDENTIFIER ::= { pmo6006Config 14 }



--- *****************************************************
---     LEAF for the table 2B50
--- *****************************************************

pmo6006CfgLineSapiAccOtuTable OBJECT-TYPE
	SYNTAX  SEQUENCE OF Pmo6006CfgLineSapiAccOtuEntry
	MAX-ACCESS not-accessible
	STATUS current
	DESCRIPTION
        "
        List of  Article
        "
	::= { pmo6006CfgSapiAccLine 1 }


pmo6006CfgLineSapiAccOtuEntry OBJECT-TYPE
	SYNTAX Pmo6006CfgLineSapiAccOtuEntry
	MAX-ACCESS not-accessible
	STATUS current
	DESCRIPTION
        "
        Row definition for the sapiAccLine 
        table
        "
	INDEX   { pmo6006CfgLineSapiAccOtuIndex }
	::= { pmo6006CfgLineSapiAccOtuTable 1 }


Pmo6006CfgLineSapiAccOtuEntry ::=
	SEQUENCE {
	pmo6006CfgLineSapiAccOtuIndex
		INTEGER,
	pmo6006CfgLineSapiAccSetupPortn
		DisplayString
	}


pmo6006CfgLineSapiAccOtuIndex OBJECT-TYPE
	SYNTAX  INTEGER(0..128)
	MAX-ACCESS  read-only
	STATUS current
	DESCRIPTION
        "
        Index definition for the lineSapiAccOtu 
        table
        "
	::= { pmo6006CfgLineSapiAccOtuEntry 1 }


pmo6006CfgLineSapiAccSetupPortn OBJECT-TYPE
	SYNTAX  DisplayString( SIZE(1..16))
	MAX-ACCESS read-write
	STATUS deprecated
	DESCRIPTION
        "
        Line Accepted SAPI :This register 
        defines the value of the accepted 
        Trace Identifier on the line input
        "
	::= { pmo6006CfgLineSapiAccOtuEntry 3 }


--- *****************************************************
---     LEAF for the table Group dapiTxLine
--- *****************************************************

pmo6006CfgDapiTxLine OBJECT IDENTIFIER ::= { pmo6006Config 15 }



--- *****************************************************
---     LEAF for the table 2B90
--- *****************************************************

pmo6006CfgLineDapiTxOtuTable OBJECT-TYPE
	SYNTAX  SEQUENCE OF Pmo6006CfgLineDapiTxOtuEntry
	MAX-ACCESS not-accessible
	STATUS current
	DESCRIPTION
        "
        List of  Article
        "
	::= { pmo6006CfgDapiTxLine 1 }


pmo6006CfgLineDapiTxOtuEntry OBJECT-TYPE
	SYNTAX Pmo6006CfgLineDapiTxOtuEntry
	MAX-ACCESS not-accessible
	STATUS current
	DESCRIPTION
        "
        Row definition for the dapiTxLine 
        table
        "
	INDEX   { pmo6006CfgLineDapiTxOtuIndex }
	::= { pmo6006CfgLineDapiTxOtuTable 1 }


Pmo6006CfgLineDapiTxOtuEntry ::=
	SEQUENCE {
	pmo6006CfgLineDapiTxOtuIndex
		INTEGER,
	pmo6006CfgLineDapiTxSetupPortn
		DisplayString
	}


pmo6006CfgLineDapiTxOtuIndex OBJECT-TYPE
	SYNTAX  INTEGER(0..128)
	MAX-ACCESS  read-only
	STATUS current
	DESCRIPTION
        "
        Index definition for the lineDapiTxOtu 
        table
        "
	::= { pmo6006CfgLineDapiTxOtuEntry 1 }


pmo6006CfgLineDapiTxSetupPortn OBJECT-TYPE
	SYNTAX  DisplayString( SIZE(1..16))
	MAX-ACCESS read-write
	STATUS current
	DESCRIPTION
        "
        Line Transmitted DAPI :This register 
        defines the value of the transmitted 
        Trace Identifier on the line output
        "
	::= { pmo6006CfgLineDapiTxOtuEntry 3 }


--- *****************************************************
---     LEAF for the table Group dapiExpLine
--- *****************************************************

pmo6006CfgDapiExpLine OBJECT IDENTIFIER ::= { pmo6006Config 16 }



--- *****************************************************
---     LEAF for the table 2BB0
--- *****************************************************

pmo6006CfgLineDapiExpOtuTable OBJECT-TYPE
	SYNTAX  SEQUENCE OF Pmo6006CfgLineDapiExpOtuEntry
	MAX-ACCESS not-accessible
	STATUS current
	DESCRIPTION
        "
        List of  Article
        "
	::= { pmo6006CfgDapiExpLine 1 }


pmo6006CfgLineDapiExpOtuEntry OBJECT-TYPE
	SYNTAX Pmo6006CfgLineDapiExpOtuEntry
	MAX-ACCESS not-accessible
	STATUS current
	DESCRIPTION
        "
        Row definition for the dapiExpLine 
        table
        "
	INDEX   { pmo6006CfgLineDapiExpOtuIndex }
	::= { pmo6006CfgLineDapiExpOtuTable 1 }


Pmo6006CfgLineDapiExpOtuEntry ::=
	SEQUENCE {
	pmo6006CfgLineDapiExpOtuIndex
		INTEGER,
	pmo6006CfgLineDapiExpSetupPortn
		DisplayString
	}


pmo6006CfgLineDapiExpOtuIndex OBJECT-TYPE
	SYNTAX  INTEGER(0..128)
	MAX-ACCESS  read-only
	STATUS current
	DESCRIPTION
        "
        Index definition for the lineDapiExpOtu 
        table
        "
	::= { pmo6006CfgLineDapiExpOtuEntry 1 }


pmo6006CfgLineDapiExpSetupPortn OBJECT-TYPE
	SYNTAX  DisplayString( SIZE(1..16))
	MAX-ACCESS read-write
	STATUS current
	DESCRIPTION
        "
        Line Expected DAPI :This register 
        defines the value of the expected 
        Trace Identifier on the line input
        "
	::= { pmo6006CfgLineDapiExpOtuEntry 3 }


--- *****************************************************
---     LEAF for the table Group dapiAccLine
--- *****************************************************

pmo6006CfgDapiAccLine OBJECT IDENTIFIER ::= { pmo6006Config 17 }



--- *****************************************************
---     LEAF for the table 2BD0
--- *****************************************************

pmo6006CfgLineDapiAccOtuTable OBJECT-TYPE
	SYNTAX  SEQUENCE OF Pmo6006CfgLineDapiAccOtuEntry
	MAX-ACCESS not-accessible
	STATUS current
	DESCRIPTION
        "
        List of  Article
        "
	::= { pmo6006CfgDapiAccLine 1 }


pmo6006CfgLineDapiAccOtuEntry OBJECT-TYPE
	SYNTAX Pmo6006CfgLineDapiAccOtuEntry
	MAX-ACCESS not-accessible
	STATUS current
	DESCRIPTION
        "
        Row definition for the dapiAccLine 
        table
        "
	INDEX   { pmo6006CfgLineDapiAccOtuIndex }
	::= { pmo6006CfgLineDapiAccOtuTable 1 }


Pmo6006CfgLineDapiAccOtuEntry ::=
	SEQUENCE {
	pmo6006CfgLineDapiAccOtuIndex
		INTEGER,
	pmo6006CfgLineDapiAccSetupPortn
		DisplayString
	}


pmo6006CfgLineDapiAccOtuIndex OBJECT-TYPE
	SYNTAX  INTEGER(0..128)
	MAX-ACCESS  read-only
	STATUS current
	DESCRIPTION
        "
        Index definition for the lineDapiAccOtu 
        table
        "
	::= { pmo6006CfgLineDapiAccOtuEntry 1 }


pmo6006CfgLineDapiAccSetupPortn OBJECT-TYPE
	SYNTAX  DisplayString( SIZE(1..16))
	MAX-ACCESS read-write
	STATUS deprecated
	DESCRIPTION
        "
        Line Accepted DAPI :This register 
        defines the value of the accepted 
        Trace Identifier on the line input
        "
	::= { pmo6006CfgLineDapiAccOtuEntry 3 }


--- *****************************************************
---     LEAF for the table Group startuptablefive
--- *****************************************************

pmo6006CfgStartuptablefive OBJECT IDENTIFIER ::= { pmo6006Config 18 }



--- *****************************************************
---     LEAF for the table 0005
--- *****************************************************

pmo6006CfgOtxtlhcapabilitiesTable OBJECT-TYPE
	SYNTAX  SEQUENCE OF Pmo6006CfgOtxtlhcapabilitiesEntry
	MAX-ACCESS not-accessible
	STATUS current
	DESCRIPTION
        "
        List of  Article
        "
	::= { pmo6006CfgStartuptablefive 1 }


pmo6006CfgOtxtlhcapabilitiesEntry OBJECT-TYPE
	SYNTAX Pmo6006CfgOtxtlhcapabilitiesEntry
	MAX-ACCESS not-accessible
	STATUS current
	DESCRIPTION
        "
        Row definition for the startuptablefive 
        table
        "
	INDEX   { pmo6006CfgOtxtlhcapabilitiesIndex }
	::= { pmo6006CfgOtxtlhcapabilitiesTable 1 }


Pmo6006CfgOtxtlhcapabilitiesEntry ::=
	SEQUENCE {
	pmo6006CfgOtxtlhcapabilitiesIndex
		INTEGER,
	pmo6006CfgComponentTypePortn
		Unsigned32,
	pmo6006CfgMiscellaneousPortn
		Unsigned32,
	pmo6006CfgFirstChannelPortn
		Unsigned32,
	pmo6006CfgLastChannelPortn
		Unsigned32,
	pmo6006CfgGridPortn
		Unsigned32
	}


pmo6006CfgOtxtlhcapabilitiesIndex OBJECT-TYPE
	SYNTAX  INTEGER(0..128)
	MAX-ACCESS  read-only
	STATUS current
	DESCRIPTION
        "
        Index definition for the otxtlhcapabilities 
        table
        "
	::= { pmo6006CfgOtxtlhcapabilitiesEntry 1 }


pmo6006CfgComponentTypePortn OBJECT-TYPE
	SYNTAX  Unsigned32 (0..65536)
	MAX-ACCESS read-only
	STATUS current
	DESCRIPTION
        "
        Component parameters :This OID 
        defines the component parameters
        "
	::= { pmo6006CfgOtxtlhcapabilitiesEntry 3 }


pmo6006CfgMiscellaneousPortn OBJECT-TYPE
	SYNTAX  Unsigned32 (0..65536)
	MAX-ACCESS read-only
	STATUS current
	DESCRIPTION
        "
        Miscellaneous default settings 
        :This OID defines the miscellaneous 
        parameters
        "
	::= { pmo6006CfgOtxtlhcapabilitiesEntry 4 }


pmo6006CfgFirstChannelPortn OBJECT-TYPE
	SYNTAX  Unsigned32 (0..65536)
	MAX-ACCESS read-only
	STATUS current
	DESCRIPTION
        "
        Number of the first channel of 
        the component :This OID defines 
        the first channel number of the 
        PM
        "
	::= { pmo6006CfgOtxtlhcapabilitiesEntry 5 }


pmo6006CfgLastChannelPortn OBJECT-TYPE
	SYNTAX  Unsigned32 (0..65536)
	MAX-ACCESS read-only
	STATUS current
	DESCRIPTION
        "
        Number of the last channel of
         the component :This OID defines 
        the last channel number of the
         PM
        "
	::= { pmo6006CfgOtxtlhcapabilitiesEntry 6 }


pmo6006CfgGridPortn OBJECT-TYPE
	SYNTAX  Unsigned32 (0..65536)
	MAX-ACCESS read-only
	STATUS current
	DESCRIPTION
        "
        Grid value of the component :This 
        OID defines the grid of the PM
        "
	::= { pmo6006CfgOtxtlhcapabilitiesEntry 7 }



pmo6006CfgWriteConfiguration  OBJECT-TYPE
	SYNTAX EkiOnOff
	MAX-ACCESS read-write
	STATUS current
	DESCRIPTION
	"Write configuration to module:This OID 
	 writes the complete configuration to the module"
	::= { pmo6006Config 257 }






--- *****************************************************
---     TRAP OBJECTS
--- *****************************************************

pmo6006trapPortNumber OBJECT-TYPE
	SYNTAX INTEGER(1..64)
	MAX-ACCESS read-only
	STATUS current
	DESCRIPTION
	"Last port which generates a trap"
	::= { pmo6006traps 2 }

pmo6006trapLineNumber OBJECT-TYPE
	SYNTAX INTEGER(1..64)
	MAX-ACCESS read-only
	STATUS current
	DESCRIPTION
	"Last Line which generates a trap"
	::= { pmo6006traps 3 }

pmo6006trapBoardNumber OBJECT-TYPE
	SYNTAX INTEGER(1..64)
	MAX-ACCESS read-only
	STATUS current
	DESCRIPTION
	"Last module which generates a trap"
	::= { pmo6006traps 4 }







--- *****************************************************
---     LINE TRAPS
--- *****************************************************

pmo6006LineTrapNotUrgentGoesOn NOTIFICATION-TYPE
	OBJECTS {pmo6006AlmLineDdmWarningPortn, pmo6006trapLineNumber, pmo6006trapBoardNumber}
	STATUS current
	--&FILTNAME    "PMO6006 Line Not Urgent ON"
	--&ACTIONS     { log, minor }
	--&MATCH       { pmo6006AlmLineDdmWarningPortn "on", pmo6006trapLineNumber "$2", pmo6006trapBoardNumber "$3"}
	--&MESG        "DDM Warning appears on Line Port $2 of PMO6006 in Slot $3 ($A)"
	DESCRIPTION "Not urgent Line default is activated"
	::= { pmo6006traps 30 }

pmo6006LineTrapNotUrgentGoesOff NOTIFICATION-TYPE
	OBJECTS {pmo6006AlmLineDdmWarningPortn, pmo6006trapLineNumber, pmo6006trapBoardNumber}
	STATUS current
	--&FILTNAME    "PMO6006 Line Not Urgent OFF"
	--&ACTIONS     { log, normal }
	--&CLEARS      { "PMO6006 Line Not Urgent ON" }
	--&MATCH       { pmo6006AlmLineDdmWarningPortn "on", pmo6006trapLineNumber "$2", pmo6006trapBoardNumber "$3"}
	--&MESG        "DDM Warning disappears on Line Port $2 of PMO6006 in Slot $3 ($A)"
	DESCRIPTION "Not urgent Line default disappeared"
	::= { pmo6006traps 31 }

pmo6006LineTrapUrgentGoesOn NOTIFICATION-TYPE
	OBJECTS {pmo6006AlmLineDdmAlmPortn, pmo6006trapLineNumber, pmo6006trapBoardNumber}
	STATUS current
	--&FILTNAME    "PMO6006 Line Urgent ON"
	--&ACTIONS     { log, major }
	--&MATCH       { pmo6006AlmLineDdmAlmPortn "on", pmo6006trapLineNumber "$2", pmo6006trapBoardNumber "$3"}
	--&MESG        "DDM Alarm appears on Line Port $2 of PMO6006 in Slot $3 ($A)"
	DESCRIPTION "Urgent Line default is activated"
	::= { pmo6006traps 32 }

pmo6006LineTrapUrgentGoesOff NOTIFICATION-TYPE
	OBJECTS {pmo6006AlmLineDdmAlmPortn, pmo6006trapLineNumber, pmo6006trapBoardNumber}
	STATUS current
	--&FILTNAME    "PMO6006 Line Urgent OFF"
	--&ACTIONS     { log, normal }
	--&CLEARS      { "PMO6006 Line Urgent ON" }
	--&MATCH       { pmo6006AlmLineDdmAlmPortn "on", pmo6006trapLineNumber "$2", pmo6006trapBoardNumber "$3"}
	--&MESG        "DDM Alarm disappears on Line Port $2 of PMO6006 in Slot $3 ($A)"
	DESCRIPTION "Urgent Line default disappeared"
	::= { pmo6006traps 33 }

pmo6006LineTrapCritGoesOn NOTIFICATION-TYPE
	OBJECTS {pmo6006AlmLineFailPortn , pmo6006AlmLineHwFailPortn , pmo6006trapLineNumber, pmo6006trapBoardNumber}
	STATUS current
	--&FILTNAME    "PMO6006 Line Fail ON"
	--&ACTIONS     { log, critical }
	--&MATCH       { pmo6006AlmLineFailPortn "on", pmo6006AlmLineHwFailPortn "*", pmo6006trapLineNumber "$3", pmo6006trapBoardNumber "$4"}
	--&MESG        "Line Port $3 Down on PMO6006 in Slot $4 ($A)"
	
	--&FILTNAME    "PMO6006 Line HW Fail ON (Hidden)"
	--&ACTIONS     { info }
	--&MATCH       { pmo6006AlmLineFailPortn "*", pmo6006AlmLineHwFailPortn "on", pmo6006trapLineNumber "$3", pmo6006trapBoardNumber "$4"}
	--&MESG        "Line Port $3 Down on PMO6006 in Slot $4 ($A)"
	DESCRIPTION "Critical Line default is activated"
	::= { pmo6006traps 34 }

pmo6006LineTrapCritGoesOff NOTIFICATION-TYPE
	OBJECTS {pmo6006AlmLineFailPortn , pmo6006AlmLineHwFailPortn , pmo6006trapLineNumber, pmo6006trapBoardNumber}
	STATUS current
	--&FILTNAME    "PMO6006 Line Fail OFF"
	--&ACTIONS     { log,  normal }
	--&CLEARS      { "PMO6006 Line Fail ON" }
	--&MATCH       { pmo6006AlmLineFailPortn "on", pmo6006AlmLineHwFailPortn "*", pmo6006trapLineNumber "$3", pmo6006trapBoardNumber "$4"}
	--&MESG        "Line Port $3 Up on PMO6006 in Slot $4 ($A)"

	--&FILTNAME    "PMO6006 Line HW Fail OFF (Hidden)"
	--&ACTIONS     { info }
	--&MATCH       { pmo6006AlmLineFailPortn "*", pmo6006AlmLineHwFailPortn "on", pmo6006trapLineNumber "$3", pmo6006trapBoardNumber "$4"}
	--&MESG        "Line Port $3 Up on PMO6006 in Slot $4 ($A)"
	DESCRIPTION "Critical Line default disappeared"
	::= { pmo6006traps 35 }






--- *****************************************************
---     CLIENT TRAPS
--- *****************************************************

pmo6006ClientTrapNotUrgentGoesOn NOTIFICATION-TYPE
	OBJECTS {pmo6006AlmSfpDdmWarningPortn, pmo6006trapPortNumber, pmo6006trapBoardNumber}
	STATUS current
		--&FILTNAME    "PMO6006 Client Not Urgent ON"
		--&ACTIONS     { log, minor }
		--&MATCH       { pmo6006AlmSfpDdmWarningPortn "on", pmo6006trapPortNumber "$2", pmo6006trapBoardNumber "$3"}
		--&MESG        "DDM Warning appears on Client Port $2 of PMO6006 in Slot $3 ($A)"
	DESCRIPTION "Not urgent client default is activated"
	::= { pmo6006traps 40 }

pmo6006ClientTrapNotUrgentGoesOff NOTIFICATION-TYPE
	OBJECTS {pmo6006AlmSfpDdmWarningPortn, pmo6006trapPortNumber, pmo6006trapBoardNumber}
	STATUS current
		--&FILTNAME    "PMO6006 Client Not Urgent OFF"
		--&ACTIONS     { log, normal }
		--&CLEARS      { "PMO6006 Client Not Urgent ON" }
		--&MATCH       { pmo6006AlmSfpDdmWarningPortn "on", pmo6006trapPortNumber "$2", pmo6006trapBoardNumber "$3"}
		--&MESG        "DDM Warning appears on Client Port $2 of PMO6006 in Slot $3 ($A)"
	DESCRIPTION "Not urgent client default disappeared"
	::= { pmo6006traps 41 }

pmo6006ClientTrapUrgentGoesOn NOTIFICATION-TYPE
	OBJECTS {pmo6006AlmSfpDdmAlmPortn, pmo6006trapPortNumber, pmo6006trapBoardNumber}
	STATUS current
		--&FILTNAME    "PMO6006 Client Urgent ON"
		--&ACTIONS     { log, major }
		--&MATCH       { pmo6006AlmSfpDdmAlmPortn "on", pmo6006trapPortNumber "$2", pmo6006trapBoardNumber "$3"}
		--&MESG        "DDM Alarm appears on Client Port $2 of PMO6006 in Slot $3 ($A)"
	DESCRIPTION "Urgent client default is activated"
	::= { pmo6006traps 42 }

pmo6006ClientTrapUrgentGoesOff NOTIFICATION-TYPE
	OBJECTS {pmo6006AlmSfpDdmAlmPortn, pmo6006trapPortNumber, pmo6006trapBoardNumber}
	STATUS current
		--&FILTNAME    "PMO6006 Client Urgent OFF"
		--&ACTIONS     { log, normal }
		--&CLEARS      { "PMO6006 Client Urgent ON" }
		--&MATCH       { pmo6006AlmSfpDdmAlmPortn "on", pmo6006trapPortNumber "$2", pmo6006trapBoardNumber "$3"}
		--&MESG        "DDM Alarm disappears on Client Port $2 of PMO6006 in Slot $3 ($A)"
	DESCRIPTION "Urgent client default disappeared"
	::= { pmo6006traps 43 }

pmo6006ClientTrapCritGoesOn NOTIFICATION-TYPE
	OBJECTS {pmo6006AlmFailAccPortn, pmo6006AlmHwFailAccPortn, pmo6006trapPortNumber, pmo6006trapBoardNumber}
	STATUS current
		--&FILTNAME    "PMO6006 Client Fail ON"
		--&ACTIONS     { log, critical }
		--&MATCH       { pmo6006AlmFailAccPortn "on", pmo6006AlmHwFailAccPortn "*", pmo6006trapPortNumber "$3", pmo6006trapBoardNumber "$4"}
		--&MESG        "Client Port $3 Down on PMO6006 in Slot $4 ($A)"
		
		--&FILTNAME    "PMO6006 Client HW Fail ON (Hidden)"
		--&ACTIONS     { info }
		--&MATCH       { pmo6006AlmFailAccPortn "*", pmo6006AlmHwFailAccPortn "on", pmo6006trapPortNumber "$3", pmo6006trapBoardNumber "$4"}
		--&MESG        "Client Port $3 Down on PMO6006 in Slot $4 ($A)"
	DESCRIPTION "Critical client default is activated"
	::= { pmo6006traps 44 }

pmo6006ClientTrapCritGoesOff NOTIFICATION-TYPE
	OBJECTS {pmo6006AlmFailAccPortn, pmo6006AlmHwFailAccPortn, pmo6006trapPortNumber, pmo6006trapBoardNumber}
	STATUS current
		--&FILTNAME    "PMO6006 Client Fail OFF"
		--&ACTIONS     { log, normal }
		--&CLEARS      { "PMO6006 Client Fail ON" }
		--&MATCH       { pmo6006AlmFailAccPortn "on", pmo6006AlmHwFailAccPortn "*", pmo6006trapPortNumber "$3", pmo6006trapBoardNumber "$4"}
		--&MESG        "Client Port $3 Up on PMO6006 in Slot $4 ($A)"
		
		--&FILTNAME    "PMO6006 Client HW Fail OFF (Hidden)"
		--&ACTIONS     { info }
		--&MATCH       { pmo6006AlmFailAccPortn "*", pmo6006AlmHwFailAccPortn "on", pmo6006trapPortNumber "$3", pmo6006trapBoardNumber "$4"}
		--&MESG        "Client Port $3 Up on PMO6006 in Slot $4 ($A)"
	DESCRIPTION "Critical client default disappeared"
	::= { pmo6006traps 45 }






--- *****************************************************
---     HW TRAPS
--- *****************************************************

pmo6006PowerTrapUrgentGoesOn NOTIFICATION-TYPE
	OBJECTS {pmo6006AlmDefFuseB, pmo6006AlmDefFuseA , pmo6006trapBoardNumber}
	STATUS current
		--&FILTNAME    "PMO6006 Fuse A Fail ON"
		--&ACTIONS     { log, major }
		--&MATCH       { pmo6006AlmDefFuseB "*", pmo6006AlmDefFuseA "on", pmo6006trapBoardNumber "$3"}
		--&MESG        "Power Input A Fail on PMO6006 in Slot $3 ($A)"
	
		--&FILTNAME    "PMO6006 Fuse B Fail ON"
		--&ACTIONS     { log, major }
		--&MATCH       { pmo6006AlmDefFuseB "on", pmo6006AlmDefFuseA "*", pmo6006trapBoardNumber "$3"}
		--&MESG        "Power Input B Fail on PMO6006 in Slot $3 ($A)"
	DESCRIPTION "Urgent power supply default is activated"
	::= { pmo6006traps 50 }

pmo6006PowerTrapUrgentGoesOff NOTIFICATION-TYPE
	OBJECTS {pmo6006AlmDefFuseB, pmo6006AlmDefFuseA , pmo6006trapBoardNumber}
	STATUS current
		--&FILTNAME    "PMO6006 Fuse A&B Fail OFF"
		--&ACTIONS     { log, normal}
		--&CLEARS      { "PMO6006 Fuse A Fail ON", "PMO6006 Fuse B Fail ON" }
		--&MATCH       { pmo6006AlmDefFuseB "on", pmo6006AlmDefFuseA "on", pmo6006trapBoardNumber "$3"}
		--&MESG        "Power Inputs A and B Present on PMO6006 in Slot $3 ($A)"
	DESCRIPTION "Urgent power supply default disappeared"
	::= { pmo6006traps 51 }






END
