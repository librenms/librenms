-- *****************************************************************
-- EKINOPS-Pm1004.TXT:  MIB
--
--MIB Part Number:3MI00010AMAE 
--MIB Version:02
--
-- Copyright (c) 2016 by Ekinops
-- All rights reserved.
-- 
-- *****************************************************************

EKINOPS-Pm1004-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress                
        		FROM SNMPv2-SMI
 	TEXTUAL-CONVENTION,
	DisplayString
                FROM SNMPv2-TC;

modulePm1004 MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.net"
        DESCRIPTION
          "MIB for managing Ekinops modules with PM1004 software"
	REVISION "200611100000Z"
	DESCRIPTION
	  "Initial Version."
	REVISION "200702210000Z"
	DESCRIPTION
	  "Adding module init fail alarms"
	REVISION "200706270000Z"
	DESCRIPTION
	  "Adding DCC alarms"
	REVISION "200709270000Z"
	DESCRIPTION
	  "Adding Performance monitoring and J0 objects
	   Update Ekinops address"
	REVISION "200711140000Z"
	DESCRIPTION
	  "Helps on objects, Ports Labels"
	REVISION "200807010000Z"
	DESCRIPTION
	  "Add OTX-TLH features"

	REVISION "200903160000Z"
	DESCRIPTION
	  "Clear Channel protocol insertion"
	REVISION "200904070000Z"
	DESCRIPTION
	  "Storm info suppress, Cosmetics for mib compilers"
	REVISION "200904090000Z"
	DESCRIPTION
	  "Add DCC ans MAINTENANCE control"
	REVISION "200905150000Z"
	DESCRIPTION
	  "CondType parameters insertion"
	REVISION "201001280000Z"
	DESCRIPTION
	  "XFP-T and OTX-VLH parameters"
	REVISION "201002180000Z"
	DESCRIPTION
	  "Probcause,AlarmType - NMS"
	REVISION "201003180000Z"
	DESCRIPTION
	  "OTX-VLH Reset"
	REVISION "201011090000Z"
	DESCRIPTION
	  "Formulas in comments and Event on XFP init"
	REVISION "201207030000Z"
	DESCRIPTION
	  "Minor cosmetic updates"
	REVISION "201304020000Z"
	DESCRIPTION
	  "S1,K1,K2 suppress"
	REVISION "201403270000Z"
	DESCRIPTION
	  "Probcause,AlarmType - NMS completion"
	REVISION "201412220000Z"
	DESCRIPTION
	  "Labels cosmetic updates"
	REVISION "201605190000Z"
	DESCRIPTION
	  "New AlarmType - synthesisAlarm(12)"
	REVISION "201606020000Z"
	DESCRIPTION
	  "Capabilities objects of Table 5"
        ::= { ekinops 18 }



--- *****************************************************
---     LEAF LEVEL 2
--- *****************************************************


pm1004alarms OBJECT IDENTIFIER ::= { modulePm1004 2 }	
pm1004AlmOther OBJECT IDENTIFIER ::= { pm1004alarms 1 }
pm1004AlmOtherNurg OBJECT IDENTIFIER ::= { pm1004AlmOther 1 }
pm1004AlmOtherUrg OBJECT IDENTIFIER ::= { pm1004AlmOther 2 }
pm1004AlmOtherCrit OBJECT IDENTIFIER ::= { pm1004AlmOther 3 }

pm1004AlmClient OBJECT IDENTIFIER ::= { pm1004alarms 2 }
pm1004AlmClientNurg OBJECT IDENTIFIER ::= { pm1004AlmClient 1 }
pm1004AlmClientUrg OBJECT IDENTIFIER ::= { pm1004AlmClient 2 }
pm1004AlmClientCrit OBJECT IDENTIFIER ::= { pm1004AlmClient 3 }
	
pm1004AlmLine OBJECT IDENTIFIER ::= { pm1004alarms 3 }
pm1004AlmLineNurg OBJECT IDENTIFIER ::= { pm1004AlmLine 1 }
pm1004AlmLineUrg OBJECT IDENTIFIER ::= { pm1004AlmLine 2 }
pm1004AlmLineCrit OBJECT IDENTIFIER ::= { pm1004AlmLine 3 }





pm1004measures OBJECT IDENTIFIER ::= { modulePm1004 3 }	
pm1004MesrOther OBJECT IDENTIFIER ::= { pm1004measures 1 }	
pm1004MesrClient OBJECT IDENTIFIER ::= { pm1004measures 2 }	
pm1004MesrLine OBJECT IDENTIFIER ::= { pm1004measures 3 }	




pm1004counters OBJECT IDENTIFIER ::= { modulePm1004 4 }
pm1004CntOther OBJECT IDENTIFIER ::= { pm1004counters 1 }
pm1004CntClient OBJECT IDENTIFIER ::= { pm1004counters 2 }
pm1004CntLine OBJECT IDENTIFIER ::= { pm1004counters 3 }


pm1004controlsWrite OBJECT IDENTIFIER ::= { modulePm1004 6 }
pm1004CtrlOther OBJECT IDENTIFIER ::= { pm1004controlsWrite 1 }
pm1004CtrlClient OBJECT IDENTIFIER ::= { pm1004controlsWrite 2 }
pm1004CtrlLine OBJECT IDENTIFIER ::= { pm1004controlsWrite 3 }

pm1004ri OBJECT IDENTIFIER ::= { modulePm1004 7 }
pm1004riTable OBJECT IDENTIFIER ::= { pm1004ri 1 }

pm1004download OBJECT IDENTIFIER ::= { modulePm1004 8 }
pm1004DwlOther OBJECT IDENTIFIER ::= { pm1004download 1 }
pm1004DwlClient OBJECT IDENTIFIER ::= { pm1004download 2 }
pm1004DwlLine OBJECT IDENTIFIER ::= { pm1004download 3 }


pm1004Config OBJECT IDENTIFIER ::= { modulePm1004 9 }

pm1004traps OBJECT IDENTIFIER ::= { modulePm1004 10 }

pm1004Monitoring OBJECT IDENTIFIER ::= { modulePm1004 11}

pm1004MonOther OBJECT IDENTIFIER ::= { pm1004Monitoring 1 }
pm1004MonSync OBJECT IDENTIFIER ::= { pm1004MonOther 1 }
pm1004MonTimeStamp OBJECT IDENTIFIER ::= { pm1004MonOther 2 }

pm1004MonClient OBJECT IDENTIFIER ::= { pm1004Monitoring 2 }
pm1004MonClientPerformance OBJECT IDENTIFIER ::= { pm1004MonClient 1 }
pm1004MonClientTraceIdentifier OBJECT IDENTIFIER ::= { pm1004MonClient 2 }

pm1004MonLine OBJECT IDENTIFIER ::= { pm1004Monitoring 3 }
pm1004MonLinePerformance OBJECT IDENTIFIER ::= { pm1004MonLine 1 }
pm1004MonLineTraceIdentifier OBJECT IDENTIFIER ::= { pm1004MonLine 2 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************


Pm1004OtxMode ::= TEXTUAL-CONVENTION
    STATUS      current
    DESCRIPTION "Different modes on OTX-TLH on line ports"
    SYNTAX INTEGER {
		otx80mode(1),
		otx60mode(2),
		otxadjustmode(4)
           }

Pm1004OtxGrid ::= TEXTUAL-CONVENTION
    STATUS      current
    DESCRIPTION "Different grids on OTX-TLH on line ports"
    SYNTAX INTEGER {
		otxgrid200(200),
		otxgrid100(100),
		otxgrid50(50)
           }

Pm1004AdjustValue ::= TEXTUAL-CONVENTION
    STATUS      current
    DESCRIPTION "Different values in Adjust mode on OTX-TLH on line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm1004OtxChannel ::= TEXTUAL-CONVENTION
    STATUS      current
    DESCRIPTION "Channel selection on OTX-TLH on line ports"
    SYNTAX INTEGER 


--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm1004RinvReloadInventory OBJECT-TYPE
  SYNTAX EkiOnOff
  MAX-ACCESS read-write
  STATUS current
  DESCRIPTION
        "Reload the inventory: This OID triggers an 
         inventory reload."
  ::= { pm1004ri 2 }

pm1004RinvHwPlatform OBJECT-TYPE
  SYNTAX DisplayString
  MAX-ACCESS read-only
  STATUS current
  DESCRIPTION
        "HW platform description: This OID contains the 
         description of the Hardware platform."
  ::= { pm1004ri 3 }
  
pm1004RinvModulePlatform OBJECT-TYPE
  SYNTAX DisplayString
  MAX-ACCESS read-only
  STATUS current
  DESCRIPTION
        "Module platform description: This OID contains the 
         description of the Module."
  ::= { pm1004ri 4 }
  
pm1004RinvSwPlatform OBJECT-TYPE
  SYNTAX DisplayString
  MAX-ACCESS read-only
  STATUS current
  DESCRIPTION
        "SW platform description: This OID contains the 
         description of the Software platform."
  ::= { pm1004ri 5 }
  
pm1004RinvGwPlatform OBJECT-TYPE
  SYNTAX DisplayString
  MAX-ACCESS read-only
  STATUS current
  DESCRIPTION
        "GW platform desciption: This OID contains the 
         description of the Gateware platform."
  ::= { pm1004ri 6 }


pm1004RinvSfpTable OBJECT-TYPE
      SYNTAX  SEQUENCE OF Pm1004RinvSfpEntry
      MAX-ACCESS  not-accessible
      STATUS  current
      DESCRIPTION
              "List of the SFPs on the selected module"
      ::= { pm1004riTable 1 }

pm1004RinvSfpEntry OBJECT-TYPE
        SYNTAX  Pm1004RinvSfpEntry
        MAX-ACCESS  not-accessible
        STATUS  current
        DESCRIPTION
              "Row definition for the SFP table"
        INDEX   { pm1004RinvSfpIndex }
        ::= { pm1004RinvSfpTable 1 }
    


Pm1004RinvSfpEntry::=
        SEQUENCE {
          pm1004RinvSfpIndex 
              Integer32,
          pm1004Rinvsfp
              DisplayString
        }


    pm1004RinvSfpIndex OBJECT-TYPE
        SYNTAX  Integer32(1..16)
        MAX-ACCESS  read-only
        STATUS  current
        DESCRIPTION
              "Index for SFP table"
        ::= { pm1004RinvSfpEntry 1 }


    pm1004Rinvsfp OBJECT-TYPE
        SYNTAX  DisplayString
        MAX-ACCESS  read-only
        STATUS  current
        DESCRIPTION
              "Inventory for the SFP: This OID contains the inventory for the SFP"
        ::= { pm1004RinvSfpEntry 2 }




pm1004RinvLineTable OBJECT-TYPE
      SYNTAX  SEQUENCE OF Pm1004RinvLineEntry
      MAX-ACCESS  not-accessible
      STATUS  current
      DESCRIPTION
              "List of the XFPs on the selected module"
      ::= { pm1004riTable 2 }

pm1004RinvLineEntry OBJECT-TYPE
        SYNTAX  Pm1004RinvLineEntry
        MAX-ACCESS  not-accessible
        STATUS  current
        DESCRIPTION
              "Row definition for the XFP table"
        INDEX   { pm1004RinvLineIndex }
        ::= { pm1004RinvLineTable 1 }
    


Pm1004RinvLineEntry::=
        SEQUENCE {
          pm1004RinvLineIndex 
              Integer32,
          pm1004RinvxfpLine
              DisplayString
        }


    pm1004RinvLineIndex OBJECT-TYPE
        SYNTAX  Integer32(1..16)
        MAX-ACCESS  read-only
        STATUS  current
        DESCRIPTION
              "Index for XFP table"
        ::= { pm1004RinvLineEntry 1 }


    pm1004RinvxfpLine OBJECT-TYPE
        SYNTAX  DisplayString
        MAX-ACCESS  read-only
        STATUS  current
        DESCRIPTION
              "Inventory for the XFP: This OID contains the inventory for the XFP"
        ::= { pm1004RinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm1004AlmsynthAlm0 OBJECT IDENTIFIER ::= { pm1004AlmOtherCrit 0 }




pm1004AlmDefFuseB OBJECT-TYPE
	  SYNTAX EkiOnOff
	  MAX-ACCESS read-only
	  STATUS current
	  DESCRIPTION
        "
        Fuse B Fail :This OID indicates 
        that the fuse of the power input 
        B is in fail condition  <Help>
          Status of the Fuse B <Condtype> 
        DEF_FUSE_B <Probcause> powerProblem 
        (36) <Alarmtype> equipmentAlarm 
        (5) <Polarity> (2) 
        "
	  ::= { pm1004AlmsynthAlm0 16 }



pm1004AlmDefFuseA OBJECT-TYPE
	  SYNTAX EkiOnOff
	  MAX-ACCESS read-only
	  STATUS current
	  DESCRIPTION
        "
        Fuse A Fail :This OID indicates 
        that the fuse of the power input 
        A is in fail condition  <Help>
          Status of the Fuse A <Condtype> 
        DEF_FUSE_A <Probcause> powerProblem 
        (36) <Alarmtype> equipmentAlarm 
        (5) <Polarity> (2) 
        "
	  ::= { pm1004AlmsynthAlm0 15 }



pm1004AlmModGlobFail OBJECT-TYPE
	  SYNTAX EkiOnOff
	  MAX-ACCESS read-only
	  STATUS current
	  DESCRIPTION
        "
        Module Failure :This OID is set 
        on detection of a failure originating 
        from the PM <Condtype> MOD_GLOB_FAIL 
        <Probcause> equipmentMalfunction 
        (16) <Alarmtype> synthesisAlarm 
        (12)  <Polarity> (2) 
        "
	  ::= { pm1004AlmsynthAlm0 9 }



--- *****************************************************
---     LEAF for the synthAlm2 article
--- *****************************************************
pm1004AlmsynthAlm2 OBJECT IDENTIFIER ::= { pm1004AlmOtherNurg 2 }




pm1004AlmMaintenanceOn OBJECT-TYPE
	  SYNTAX EkiOnOff
	  MAX-ACCESS read-only
	  STATUS current
	  DESCRIPTION
        "
        Maintenance Mode :This OID indicates 
        that the PM is in maintenance mode. 
         <Help>  This alarm indicates that 
        the maintenance mode is enabled 
        on the PM <Condtype> MAINTENANCE_ON 
        <Probcause> other (1) <Alarmtype> 
        other (1) <Polarity> (2) 
        "
	  ::= { pm1004AlmsynthAlm2 5 }



pm1004AlmCorrelatOff OBJECT-TYPE
	  SYNTAX EkiOnOff
	  MAX-ACCESS read-only
	  STATUS current
	  DESCRIPTION
        "
        Not Used :This OID, when set,
         indicates that alarm correlation 
        is not being performed. <Condtype> 
        CORRELAT_OFF <Probcause> other
         (1) <Alarmtype> other (1) <Polarity> 
        (2) 
        "
	  ::= { pm1004AlmsynthAlm2 4 }



pm1004AlmConfTableLoad OBJECT-TYPE
	  SYNTAX EkiOnOff
	  MAX-ACCESS read-only
	  STATUS current
	  DESCRIPTION
        "
        PM Configuration Load :This OID 
         is at 1 during the loading of
         configuration tables in the modules 
        RAM. <Condtype> CONF_TABLE_LOAD 
        <Probcause> other (1) <Alarmtype> 
        other (1) <Polarity> (2) 
        "
	  ::= { pm1004AlmsynthAlm2 3 }



pm1004AlmInvUpload OBJECT-TYPE
	  SYNTAX EkiOnOff
	  MAX-ACCESS read-only
	  STATUS current
	  DESCRIPTION
        "
        Inventory Upload :This OID is
         at 1 during the uploading of PM 
        inventory information. <Condtype> 
        INV_UPLOAD <Probcause> other (1) 
        <Alarmtype> other (1) <Polarity> 
        (2) 
        "
	  ::= { pm1004AlmsynthAlm2 2 }



pm1004AlmConfTableSave OBJECT-TYPE
	  SYNTAX EkiOnOff
	  MAX-ACCESS read-only
	  STATUS current
	  DESCRIPTION
        "
        PM Configuration Save :This OID 
        is at 1 during the saving of a
         new configuration table in the 
        module Flash memory. <Condtype> 
        CONF_TABLE_SAVE <Probcause> other 
        (1) <Alarmtype> other (1) <Polarity> 
        (2) 
        "
	  ::= { pm1004AlmsynthAlm2 1 }



--- *********************************************************
---     TABLE for the pm1004AlmsynthAlmLine articles
--- *********************************************************

pm1004AlmsynthAlmLineTable OBJECT-TYPE
	SYNTAX  SEQUENCE OF Pm1004AlmsynthAlmLineEntry
	MAX-ACCESS not-accessible
	STATUS current
	DESCRIPTION
        "
        List of pm1004AlmsynthAlmLine
         Article
        "
	::= { pm1004AlmLineCrit 7 }


pm1004AlmsynthAlmLineEntry OBJECT-TYPE
	SYNTAX Pm1004AlmsynthAlmLineEntry
	MAX-ACCESS not-accessible
	STATUS current
	DESCRIPTION
        "
        Row definition for the pm1004AlmsynthAlmLine 
        table
        "
	INDEX   { pm1004AlmsynthAlmLineIndex }
	::= { pm1004AlmsynthAlmLineTable 1 }


Pm1004AlmsynthAlmLineEntry ::=
	SEQUENCE {
	pm1004AlmsynthAlmLineIndex
		INTEGER,
	pm1004AlmLineActivePortn
		EkiOnOff,
	pm1004AlmLineFailPortn
		EkiOnOff,
	pm1004AlmLineDdmAlmPortn
		EkiOnOff,
	pm1004AlmLineDdmWarningPortn
		EkiOnOff,
	pm1004AlmUpRdiInsPortn
		EkiOnOff,
	pm1004AlmLineLocalOosPortn
		EkiOnOff,
	pm1004AlmXfpTxOffPortn
		EkiOnOff,
	pm1004AlmLineHwFailPortn
		EkiOnOff,
	pm1004AlmXfpInitNotComplPortn
		EkiOnOff,
	pm1004AlmXfpAbsentPortn
		EkiOnOff
	}


pm1004AlmsynthAlmLineIndex OBJECT-TYPE
	SYNTAX  INTEGER(0..128)
	MAX-ACCESS  read-only
	STATUS current
	DESCRIPTION
        "
        Index definition for the pm1004AlmsynthAlmLine 
        table
        "
	::= { pm1004AlmsynthAlmLineEntry 1 }


pm1004AlmLineActivePortn OBJECT-TYPE
	SYNTAX  EkiOnOff
	MAX-ACCESS read-only
	STATUS current
	DESCRIPTION
        "
        Line Active :This bit indicates 
        the line #n is active on receive 
        side  <Help>  This status indicates 
        whether the line is active or standby. 
        <Condtype> LINE_ACTIVE <Probcause> 
        informationalStatus(1000) <Alarmtype> 
        other (1) <Polarity> (2) 
        "
	::= { pm1004AlmsynthAlmLineEntry 17 }


pm1004AlmLineFailPortn OBJECT-TYPE
	SYNTAX  EkiOnOff
	MAX-ACCESS read-only
	STATUS current
	DESCRIPTION
        "
        Line Port Failure :This OID indicates 
        a failure on the line port <Condtype> 
        LINE_FAIL <Probcause> equipmentMalfunction 
        (16) <Alarmtype> synthesisAlarm 
        (12)  <Polarity> (2) 
        "
	::= { pm1004AlmsynthAlmLineEntry 13 }


pm1004AlmLineDdmAlmPortn OBJECT-TYPE
	SYNTAX  EkiOnOff
	MAX-ACCESS read-only
	STATUS current
	DESCRIPTION
        "
        Alarm On Line Optical Module DDM 
        :This OID indicates an alarm is 
        present coming out of Line optical 
        interface DDM  <Help>  This alarm 
        indicates if a DDM Warning has
         been detected on the line transceiver 
        <Condtype> LINE_DDM_ALM <Probcause> 
        equipmentMalfunction (16) <Alarmtype> 
        synthesisAlarm (12)  <Polarity> 
        (2) 
        "
	::= { pm1004AlmsynthAlmLineEntry 11 }


pm1004AlmLineDdmWarningPortn OBJECT-TYPE
	SYNTAX  EkiOnOff
	MAX-ACCESS read-only
	STATUS current
	DESCRIPTION
        "
        Warning On Line Optical Module 
        DDM :This OID indicates a warning 
        is present coming out of Line optical 
        interface DDM  <Help>  This status 
        indicates if a MS-RDI/L-RDI is
         currently inserted on the line 
        interface. <Condtype> LINE_DDM_WARNING 
        <Probcause> equipmentMalfunction 
        (16) <Alarmtype> synthesisAlarm 
        (12)  <Polarity> (2) 
        "
	::= { pm1004AlmsynthAlmLineEntry 10 }


pm1004AlmUpRdiInsPortn OBJECT-TYPE
	SYNTAX  EkiOnOff
	MAX-ACCESS read-only
	STATUS current
	DESCRIPTION
        "
        SM-BDI Inserted On Line :This
         OID indicates an upstream SM-BDI 
        has been inserted in the outgoing 
        G709 signal.   <Help>  This status 
        indicates if a SM-BDI is currently 
        inserted on the line interface. 
        <Condtype> UP_RDI_INS <Probcause> 
        informationalStatus(1000) <Alarmtype> 
        other (1) <Polarity> (2) 
        "
	::= { pm1004AlmsynthAlmLineEntry 9 }


pm1004AlmLineLocalOosPortn OBJECT-TYPE
	SYNTAX  EkiOnOff
	MAX-ACCESS read-only
	STATUS current
	DESCRIPTION
        "
        Line Port In Service :This OID 
        indicates that the Line port is 
        In Service (1) of Out or Service 
        (2)  <Help>  This status indicates 
        if the line port is in service
         <Condtype> LINE_LOCAL_OOS <Probcause> 
        informationalStatus(1000) <Alarmtype> 
        other (1) <Polarity> (2) 
        "
	::= { pm1004AlmsynthAlmLineEntry 7 }


pm1004AlmXfpTxOffPortn OBJECT-TYPE
	SYNTAX  EkiOnOff
	MAX-ACCESS read-only
	STATUS current
	DESCRIPTION
        "
        Line Optical Module Laser Shutdown 
        :This OID indicates the line optical 
        output power is on  <Help>  This 
        status indicates if the line transceiver 
        laser is ON or OFF <Condtype> XFP_TX_OFF 
        <Probcause> other (1) <Alarmtype> 
        equipmentAlarm (5) <Polarity> (2)
         
        "
	::= { pm1004AlmsynthAlmLineEntry 6 }


pm1004AlmLineHwFailPortn OBJECT-TYPE
	SYNTAX  EkiOnOff
	MAX-ACCESS read-only
	STATUS current
	DESCRIPTION
        "
        Line Port HW Failure :This OID 
        indicates a failure on line port, 
        most probably caused by a HW issue 
        <Condtype> LINE_HW_FAIL <Probcause> 
        equipmentMalfunction (16) <Alarmtype> 
        synthesisAlarm (12)  <Polarity> 
        (2) 
        "
	::= { pm1004AlmsynthAlmLineEntry 5 }


pm1004AlmXfpInitNotComplPortn OBJECT-TYPE
	SYNTAX  EkiOnOff
	MAX-ACCESS read-only
	STATUS current
	DESCRIPTION
        "
        Line Optical Module Ready :This 
        OID indicates that the optical
         interface (XFP or OTX) is not
         operational.  <Help>  This status 
        indicates if the line transceiver 
        has been correctly initialized
         <Condtype> XFP_INIT_NOT_COMPL
         <Probcause> equipmentMalfunction 
        (16) <Alarmtype> equipmentAlarm 
        (5) <Polarity> (2) <Event> ObjectCDIN
        V
        "
	::= { pm1004AlmsynthAlmLineEntry 3 }


pm1004AlmXfpAbsentPortn OBJECT-TYPE
	SYNTAX  EkiOnOff
	MAX-ACCESS read-only
	STATUS current
	DESCRIPTION
        "
        Line Optical Module Absent :This 
        OID indicates that the line optical 
        interface (XFP or OTX) is not plugged 
        in.  <Help>  This alarm indicates 
        if the line transceiver is present. 
        <Condtype> XFP_ABSENT <Probcause> 
        inputOutputDeviceError (24) <Alarmtype> 
        equipmentAlarm (5) <Polarity> (2) 
        <Event> ObjectCDINV
        "
	::= { pm1004AlmsynthAlmLineEntry 2 }


--- *********************************************************
---     TABLE for the pm1004AlmsynthAlmPort articles
--- *********************************************************

pm1004AlmsynthAlmPortTable OBJECT-TYPE
	SYNTAX  SEQUENCE OF Pm1004AlmsynthAlmPortEntry
	MAX-ACCESS not-accessible
	STATUS current
	DESCRIPTION
        "
        List of pm1004AlmsynthAlmPort
         Article
        "
	::= { pm1004AlmClientCrit 8 }


pm1004AlmsynthAlmPortEntry OBJECT-TYPE
	SYNTAX Pm1004AlmsynthAlmPortEntry
	MAX-ACCESS not-accessible
	STATUS current
	DESCRIPTION
        "
        Row definition for the pm1004AlmsynthAlmPort 
        table
        "
	INDEX   { pm1004AlmsynthAlmPortIndex }
	::= { pm1004AlmsynthAlmPortTable 1 }


Pm1004AlmsynthAlmPortEntry ::=
	SEQUENCE {
	pm1004AlmsynthAlmPortIndex
		INTEGER,
	pm1004AlmUpCsfPortn
		EkiOnOff,
	pm1004AlmFailAccPortn
		EkiOnOff,
	pm1004AlmSfpDdmAlmPortn
		EkiOnOff,
	pm1004AlmSfpDdmWarningPortn
		EkiOnOff,
	pm1004AlmDwCaisPortn
		EkiOnOff,
	pm1004AlmClientRemoteOosPortn
		EkiOnOff,
	pm1004AlmClientLocalOosPortn
		EkiOnOff,
	pm1004AlmDwLsdPortn
		EkiOnOff,
	pm1004AlmHwFailAccPortn
		EkiOnOff,
	pm1004AlmDdmAbsentPortn
		EkiOnOff,
	pm1004AlmSfpAbsentPortn
		EkiOnOff
	}


pm1004AlmsynthAlmPortIndex OBJECT-TYPE
	SYNTAX  INTEGER(0..128)
	MAX-ACCESS  read-only
	STATUS current
	DESCRIPTION
        "
        Index definition for the pm1004AlmsynthAlmPort 
        table
        "
	::= { pm1004AlmsynthAlmPortEntry 1 }


pm1004AlmUpCsfPortn OBJECT-TYPE
	SYNTAX  EkiOnOff
	MAX-ACCESS read-only
	STATUS current
	DESCRIPTION
        "
        Client Signal Fail Inserted :This 
        OID indicates a CSF has been inserted 
        in the upstream client port.  <Help> 
         This status indicates if a Client 
        Signal Fail is currently inserted 
        on the line signal for this client 
        port <Condtype> UP_CSF_1 <Probcause> 
        other (1) <Alarmtype> other (1) 
        <Polarity> (2) 
        "
	::= { pm1004AlmsynthAlmPortEntry 17 }


pm1004AlmFailAccPortn OBJECT-TYPE
	SYNTAX  EkiOnOff
	MAX-ACCESS read-only
	STATUS current
	DESCRIPTION
        "
        Client Access Fail :This OID indicates 
        a failure on the Client port <Condtype> 
        FAIL_ACC_1 <Probcause> equipmentMalfunction 
        (16) <Alarmtype> synthesisAlarm 
        (12)  <Polarity> (2) 
        "
	::= { pm1004AlmsynthAlmPortEntry 13 }


pm1004AlmSfpDdmAlmPortn OBJECT-TYPE
	SYNTAX  EkiOnOff
	MAX-ACCESS read-only
	STATUS current
	DESCRIPTION
        "
        Alarm On Client SFP DDM :This
         OID indicates an alarm is being 
        received from the Client SFP DDM 
         <Help>  This alarm indicates if 
        a DDM Alarm has been detected on 
        the client transceiver <Condtype> 
        SFP_DDM_ALM_1 <Probcause> equipmentMalfunction 
        (16) <Alarmtype> synthesisAlarm 
        (12)  <Polarity> (2) 
        "
	::= { pm1004AlmsynthAlmPortEntry 11 }


pm1004AlmSfpDdmWarningPortn OBJECT-TYPE
	SYNTAX  EkiOnOff
	MAX-ACCESS read-only
	STATUS current
	DESCRIPTION
        "
        Warning On Client SFP DDM :This 
        OID indicates a warning is being 
        received from the Client SFP DDM 
         <Help>  This alarm indicates if 
        a DDM Warning has been detected 
        on the client transceiver <Condtype> 
        SFP_DDM_WARNING_1 <Probcause> equipmentMalfunction 
        (16) <Alarmtype> synthesisAlarm 
        (12)  <Polarity> (2) 
        "
	::= { pm1004AlmsynthAlmPortEntry 10 }


pm1004AlmDwCaisPortn OBJECT-TYPE
	SYNTAX  EkiOnOff
	MAX-ACCESS read-only
	STATUS current
	DESCRIPTION
        "
        Client AIS Inserted :This OID
         indicates a CAIS has been inserted 
        on the output client port.  <Help> 
         This status indicates if a Client 
        Alarm Indication Signal is currently 
        inserted on the client interface 
        <Condtype> DW_CAIS_1 <Probcause> 
        informationalStatus(1000) <Alarmtype> 
        other (1) <Polarity> (2) 
        "
	::= { pm1004AlmsynthAlmPortEntry 9 }


pm1004AlmClientRemoteOosPortn OBJECT-TYPE
	SYNTAX  EkiOnOff
	MAX-ACCESS read-only
	STATUS current
	DESCRIPTION
        "
        Remote Client Port In Service
         :This OID indicates that the remote 
        Client port is In Service (1) or 
        Out of Service (2)  <Help>  This 
        status indicates if the remote
         client port is in service <Condtype> 
        CLIENT_REMOTE_OOS <Probcause> informationalStatus(1000) 
        <Alarmtype> other (1) <Polarity> 
        (2) 
        "
	::= { pm1004AlmsynthAlmPortEntry 8 }


pm1004AlmClientLocalOosPortn OBJECT-TYPE
	SYNTAX  EkiOnOff
	MAX-ACCESS read-only
	STATUS current
	DESCRIPTION
        "
        Local Client Port In Service :This 
        OID indicates that the local Client 
        port is In Service (1) or Out of 
        Service (2)  <Help>  This status 
        indicates if the local client port 
        is in service <Condtype> CLIENT_LOCAL_OOS 
        <Probcause> informationalStatus(1000) 
        <Alarmtype> other (1) <Polarity> 
        (2) 
        "
	::= { pm1004AlmsynthAlmPortEntry 7 }


pm1004AlmDwLsdPortn OBJECT-TYPE
	SYNTAX  EkiOnOff
	MAX-ACCESS read-only
	STATUS current
	DESCRIPTION
        "
        Client SFP Laser Shutdown :This 
        OID indicates the Client SFP transmitter 
        output is ON.   <Help>  This status 
        indicates if the client transceiver 
        laser is ON or OFF <Condtype> DW_LSD_1 
        <Probcause> other (1) <Alarmtype> 
        equipmentAlarm (5) <Polarity> (2)
         
        "
	::= { pm1004AlmsynthAlmPortEntry 6 }


pm1004AlmHwFailAccPortn OBJECT-TYPE
	SYNTAX  EkiOnOff
	MAX-ACCESS read-only
	STATUS current
	DESCRIPTION
        "
        Client HW Fail :This OID indicates 
        a failure on client port, most
         probably caused by a HW issue. 
        <Condtype> HW_FAIL_ACC_1 <Probcause> 
        equipmentMalfunction (16) <Alarmtype> 
        synthesisAlarm (12)  <Polarity> 
        (2) 
        "
	::= { pm1004AlmsynthAlmPortEntry 5 }


pm1004AlmDdmAbsentPortn OBJECT-TYPE
	SYNTAX  EkiOnOff
	MAX-ACCESS read-only
	STATUS current
	DESCRIPTION
        "
        DDM Supported On Client SFP :This 
        OID indicates that the Client SFP 
        module supports the Digital Diagnostic 
        Monitoring function  <Help>  This 
        status indicates if the client
         transceiver includes the DDM feature 
        <Condtype> DDM_ABSENT_1 <Probcause> 
        informationalStatus(1000) <Alarmtype> 
        other (1) <Polarity> (2) 
        "
	::= { pm1004AlmsynthAlmPortEntry 3 }


pm1004AlmSfpAbsentPortn OBJECT-TYPE
	SYNTAX  EkiOnOff
	MAX-ACCESS read-only
	STATUS current
	DESCRIPTION
        "
        Client SFP Absent :This OID indicates 
        that the SFP module is not present 
        in the client port.  <Help>  This 
        alarm indicates if the client transceiver 
        is present. <Condtype> SFP_ABSENT_1 
        <Probcause> inputOutputDeviceError 
        (24) <Alarmtype> equipmentAlarm 
        (5) <Polarity> (2) <Event> ObjectCDIN
        V
        "
	::= { pm1004AlmsynthAlmPortEntry 2 }


--- *********************************************************
---     TABLE for the pm1004AlmaccessioAlm articles
--- *********************************************************

pm1004AlmaccessioAlmTable OBJECT-TYPE
	SYNTAX  SEQUENCE OF Pm1004AlmaccessioAlmEntry
	MAX-ACCESS not-accessible
	STATUS current
	DESCRIPTION
        "
        List of pm1004AlmaccessioAlm Articl
        e
        "
	::= { pm1004AlmClientCrit 16 }


pm1004AlmaccessioAlmEntry OBJECT-TYPE
	SYNTAX Pm1004AlmaccessioAlmEntry
	MAX-ACCESS not-accessible
	STATUS current
	DESCRIPTION
        "
        Row definition for the pm1004AlmaccessioAlm 
        table
        "
	INDEX   { pm1004AlmaccessioAlmIndex }
	::= { pm1004AlmaccessioAlmTable 1 }


Pm1004AlmaccessioAlmEntry ::=
	SEQUENCE {
	pm1004AlmaccessioAlmIndex
		INTEGER,
	pm1004AlmUpLosPortn
		EkiOnOff,
	pm1004AlmDwLasFailPortn
		EkiOnOff
	}


pm1004AlmaccessioAlmIndex OBJECT-TYPE
	SYNTAX  INTEGER(0..128)
	MAX-ACCESS  read-only
	STATUS current
	DESCRIPTION
        "
        Index definition for the pm1004AlmaccessioAlm 
        table
        "
	::= { pm1004AlmaccessioAlmEntry 1 }


pm1004AlmUpLosPortn OBJECT-TYPE
	SYNTAX  EkiOnOff
	MAX-ACCESS read-only
	STATUS current
	DESCRIPTION
        "
        Client Input Loss Of Signal :This 
        OID indicates that no signal is 
        present on the SFP of the client 
        port  <Help>  This alarm indicates 
        if an optical signal is detected 
        on the client transceiver input 
        <Condtype> UP_LOS_1 <Probcause> 
        receiveFailure (41) <Alarmtype> 
        physicalViolation (9) <Polarity> 
        (2) 
        "
	::= { pm1004AlmaccessioAlmEntry 5 }


pm1004AlmDwLasFailPortn OBJECT-TYPE
	SYNTAX  EkiOnOff
	MAX-ACCESS read-only
	STATUS current
	DESCRIPTION
        "
        Client SFP Tx Failed :This OID 
        indicates that the transmitter
         fails for the SFP plugged into 
        the client port (this alarm reports 
        the transmitter failure alarm generated 
        by the SFPs)  <Help>  This alarm 
        indicates if the laser of the client 
        transceiver is in <Condtype> DW_LAS_FAIL_1 
        <Probcause> transmitterFailure
         (56) <Alarmtype> equipmentAlarm 
        (5) <Polarity> (2) 
        "
	::= { pm1004AlmaccessioAlmEntry 2 }


--- *********************************************************
---     TABLE for the pm1004AlmsfpAlmDdm articles
--- *********************************************************

pm1004AlmsfpAlmDdmTable OBJECT-TYPE
	SYNTAX  SEQUENCE OF Pm1004AlmsfpAlmDdmEntry
	MAX-ACCESS not-accessible
	STATUS current
	DESCRIPTION
        "
        List of pm1004AlmsfpAlmDdm Articl
        e
        "
	::= { pm1004AlmClientUrg 32 }


pm1004AlmsfpAlmDdmEntry OBJECT-TYPE
	SYNTAX Pm1004AlmsfpAlmDdmEntry
	MAX-ACCESS not-accessible
	STATUS current
	DESCRIPTION
        "
        Row definition for the pm1004AlmsfpAlmDdm 
        table
        "
	INDEX   { pm1004AlmsfpAlmDdmIndex }
	::= { pm1004AlmsfpAlmDdmTable 1 }


Pm1004AlmsfpAlmDdmEntry ::=
	SEQUENCE {
	pm1004AlmsfpAlmDdmIndex
		INTEGER,
	pm1004AlmRxPwrHighAlaPortn
		EkiOnOff,
	pm1004AlmRxPwrLowAlaPortn
		EkiOnOff,
	pm1004AlmTempHighAlaPortn
		EkiOnOff,
	pm1004AlmTempLowAlaPortn
		EkiOnOff,
	pm1004AlmVccHighAlaPortn
		EkiOnOff,
	pm1004AlmVccLowAlaPortn
		EkiOnOff,
	pm1004AlmTxBiasHighAlaPortn
		EkiOnOff,
	pm1004AlmTxBiasLowAlaPortn
		EkiOnOff,
	pm1004AlmTxPwrHighAlaPortn
		EkiOnOff,
	pm1004AlmTxPwrLowAlaPortn
		EkiOnOff
	}


pm1004AlmsfpAlmDdmIndex OBJECT-TYPE
	SYNTAX  INTEGER(0..128)
	MAX-ACCESS  read-only
	STATUS current
	DESCRIPTION
        "
        Index definition for the pm1004AlmsfpAlmDdm 
        table
        "
	::= { pm1004AlmsfpAlmDdmEntry 1 }


pm1004AlmRxPwrHighAlaPortn OBJECT-TYPE
	SYNTAX  EkiOnOff
	MAX-ACCESS read-only
	STATUS current
	DESCRIPTION
        "
        Client SFP Rx Power High :Alarm 
        indicating that the SFP input power 
        of port is higher than the threshold 
        value written in the SFP EEPROM 
        <Condtype> RX_PWR_HIGH_ALA_1 <Probcause> 
        receiveFailure (41) <Alarmtype> 
        equipmentAlarm (5) <Polarity> (2)
         
        "
	::= { pm1004AlmsfpAlmDdmEntry 17 }


pm1004AlmRxPwrLowAlaPortn OBJECT-TYPE
	SYNTAX  EkiOnOff
	MAX-ACCESS read-only
	STATUS current
	DESCRIPTION
        "
        Client SFP Rx Power Low :Alarm 
        indicating that the SFP input power 
        of port is lower than the threshold 
        value written in the SFP EEPROM 
        <Condtype> RX_PWR_LOW_ALA_1 <Probcause> 
        receiveFailure (41) <Alarmtype> 
        equipmentAlarm (5) <Polarity> (2)
         
        "
	::= { pm1004AlmsfpAlmDdmEntry 16 }


pm1004AlmTempHighAlaPortn OBJECT-TYPE
	SYNTAX  EkiOnOff
	MAX-ACCESS read-only
	STATUS current
	DESCRIPTION
        "
        Client SFP Temp High :Alarm indicating 
        that the SFP temperature of port 
        is higher than the threshold value 
        written in the SFP EEPROM <Condtype> 
        TEMP_HIGH_ALA_1 <Probcause> temperatureUnacceptable 
        (51) <Alarmtype> equipmentAlarm 
        (5) <Polarity> (2) 
        "
	::= { pm1004AlmsfpAlmDdmEntry 9 }


pm1004AlmTempLowAlaPortn OBJECT-TYPE
	SYNTAX  EkiOnOff
	MAX-ACCESS read-only
	STATUS current
	DESCRIPTION
        "
        Client SFP Temp Low :Alarm indicating 
        that the SFP temperature of port 
        is lower than the threshold value 
        written in the SFP EEPROM <Condtype> 
        TEMP_LOW_ALA_1 <Probcause> temperatureUnacceptable 
        (51) <Alarmtype> equipmentAlarm 
        (5) <Polarity> (2) 
        "
	::= { pm1004AlmsfpAlmDdmEntry 8 }


pm1004AlmVccHighAlaPortn OBJECT-TYPE
	SYNTAX  EkiOnOff
	MAX-ACCESS read-only
	STATUS current
	DESCRIPTION
        "
        Client SFP Power Supply High :Alarm 
        indicating that the SFP power supply 
        of port is higher than the threshold 
        value written in the SFP EEPROM 
         <Condtype> VCC_HIGH_ALA_1 <Probcause> 
        powerProblem (36) <Alarmtype> equipmentAlarm 
        (5) <Polarity> (2) 
        "
	::= { pm1004AlmsfpAlmDdmEntry 7 }


pm1004AlmVccLowAlaPortn OBJECT-TYPE
	SYNTAX  EkiOnOff
	MAX-ACCESS read-only
	STATUS current
	DESCRIPTION
        "
        Client SFP Power Supply Low :Alarm 
        indicating that the SFP power supply 
        of port is lower than the threshold 
        value written in the SFP EEPROM 
         <Condtype> VCC_LOW_ALA_1 <Probcause> 
        powerProblem (36) <Alarmtype> equipmentAlarm 
        (5) <Polarity> (2) 
        "
	::= { pm1004AlmsfpAlmDdmEntry 6 }


pm1004AlmTxBiasHighAlaPortn OBJECT-TYPE
	SYNTAX  EkiOnOff
	MAX-ACCESS read-only
	STATUS current
	DESCRIPTION
        "
        Client SFP Bias High :Alarm indicating 
        that the SFP laser bias current 
        of port is higher than the threshold 
        value written in the SFP EEPROM 
        <Condtype> TX_BIAS_HIGH_ALA_1 <Probcause> 
        transmitterFailure (56) <Alarmtype> 
        equipmentAlarm (5) <Polarity> (2)
         
        "
	::= { pm1004AlmsfpAlmDdmEntry 5 }


pm1004AlmTxBiasLowAlaPortn OBJECT-TYPE
	SYNTAX  EkiOnOff
	MAX-ACCESS read-only
	STATUS current
	DESCRIPTION
        "
        Client SFP Bias Low :Alarm indicating 
        that the SFP laser bias current 
        of port is lower than the threshold 
        value written in the SFP EEPROM 
        <Condtype> TX_BIAS_LOW_ALA_1 <Probcause> 
        transmitterFailure (56) <Alarmtype> 
        equipmentAlarm (5) <Polarity> (2)
         
        "
	::= { pm1004AlmsfpAlmDdmEntry 4 }


pm1004AlmTxPwrHighAlaPortn OBJECT-TYPE
	SYNTAX  EkiOnOff
	MAX-ACCESS read-only
	STATUS current
	DESCRIPTION
        "
        Client SFP Tx Power High :Alarm 
        indicating that the SFP output
         power of port is higher than the 
        threshold value written in the
         SFP EEPROM <Condtype> TX_PWR_HIGH_ALA_1 
        <Probcause> transmitterFailure
         (56) <Alarmtype> equipmentAlarm 
        (5) <Polarity> (2) 
        "
	::= { pm1004AlmsfpAlmDdmEntry 3 }


pm1004AlmTxPwrLowAlaPortn OBJECT-TYPE
	SYNTAX  EkiOnOff
	MAX-ACCESS read-only
	STATUS current
	DESCRIPTION
        "
        Client SFP Tx Power Low :Alarm 
        indicating that the SFP output
         power of port is lower than the 
        threshold value written in the
         SFP EEPROM <Condtype> TX_PWR_LOW_ALA_1 
        <Probcause> transmitterFailure
         (56) <Alarmtype> equipmentAlarm 
        (5) <Polarity> (2) 
        "
	::= { pm1004AlmsfpAlmDdmEntry 2 }


--- *********************************************************
---     TABLE for the pm1004AlmsfpWarnDdm articles
--- *********************************************************

pm1004AlmsfpWarnDdmTable OBJECT-TYPE
	SYNTAX  SEQUENCE OF Pm1004AlmsfpWarnDdmEntry
	MAX-ACCESS not-accessible
	STATUS current
	DESCRIPTION
        "
        List of pm1004AlmsfpWarnDdm Articl
        e
        "
	::= { pm1004AlmClientNurg 48 }


pm1004AlmsfpWarnDdmEntry OBJECT-TYPE
	SYNTAX Pm1004AlmsfpWarnDdmEntry
	MAX-ACCESS not-accessible
	STATUS current
	DESCRIPTION
        "
        Row definition for the pm1004AlmsfpWarnDdm 
        table
        "
	INDEX   { pm1004AlmsfpWarnDdmIndex }
	::= { pm1004AlmsfpWarnDdmTable 1 }


Pm1004AlmsfpWarnDdmEntry ::=
	SEQUENCE {
	pm1004AlmsfpWarnDdmIndex
		INTEGER,
	pm1004AlmRxPwrHighWngPortn
		EkiOnOff,
	pm1004AlmRxPwrLowWngPortn
		EkiOnOff,
	pm1004AlmTempHighWngPortn
		EkiOnOff,
	pm1004AlmTempLowWngPortn
		EkiOnOff,
	pm1004AlmVccHighWngPortn
		EkiOnOff,
	pm1004AlmVccLowWngPortn
		EkiOnOff,
	pm1004AlmTxBiasHighWngPortn
		EkiOnOff,
	pm1004AlmTxBiasLowWngPortn
		EkiOnOff,
	pm1004AlmTxPwrHighWngPortn
		EkiOnOff,
	pm1004AlmTxPwLowWngPortn
		EkiOnOff
	}


pm1004AlmsfpWarnDdmIndex OBJECT-TYPE
	SYNTAX  INTEGER(0..128)
	MAX-ACCESS  read-only
	STATUS current
	DESCRIPTION
        "
        Index definition for the pm1004AlmsfpWarnDdm 
        table
        "
	::= { pm1004AlmsfpWarnDdmEntry 1 }


pm1004AlmRxPwrHighWngPortn OBJECT-TYPE
	SYNTAX  EkiOnOff
	MAX-ACCESS read-only
	STATUS current
	DESCRIPTION
        "
        Client SFP Rx Power High Warning 
        :Warning indicating that the SFP 
        input power of port is higher than 
        the threshold value written in
         the SFP EEPROM <Condtype> RX_PWR_HIGH_WNG_1 
        <Probcause> receiveFailure (41) 
        <Alarmtype> equipmentAlarm (5)
         <Polarity> (2) 
        "
	::= { pm1004AlmsfpWarnDdmEntry 17 }


pm1004AlmRxPwrLowWngPortn OBJECT-TYPE
	SYNTAX  EkiOnOff
	MAX-ACCESS read-only
	STATUS current
	DESCRIPTION
        "
        Client SFP Rx Power Low Warning 
        :Warning indicating that the SFP 
        input power of port is lower than 
        the threshold value written in
         the SFP EEPROM <Condtype> RX_PWR_LOW_WNG_1 
        <Probcause> receiveFailure (41) 
        <Alarmtype> equipmentAlarm (5)
         <Polarity> (2) 
        "
	::= { pm1004AlmsfpWarnDdmEntry 16 }


pm1004AlmTempHighWngPortn OBJECT-TYPE
	SYNTAX  EkiOnOff
	MAX-ACCESS read-only
	STATUS current
	DESCRIPTION
        "
        Client SFP Temp High Warning :Warning 
        indicating that the SFP temperature 
        of port is higher than the threshold 
        value written in the SFP EEPROM 
        <Condtype> TEMP_HIGH_WNG_1 <Probcause> 
        temperatureUnacceptable (51) <Alarmtype> 
        equipmentAlarm (5) <Polarity> (2)
         
        "
	::= { pm1004AlmsfpWarnDdmEntry 9 }


pm1004AlmTempLowWngPortn OBJECT-TYPE
	SYNTAX  EkiOnOff
	MAX-ACCESS read-only
	STATUS current
	DESCRIPTION
        "
        Client SFP Temp Low Warning :Warning 
        indicating that the SFP temperature 
        of port is lower than the threshold 
        value written in the SFP EEPROM 
        <Condtype> TEMP_LOW_WNG_1 <Probcause> 
        temperatureUnacceptable (51) <Alarmtype> 
        equipmentAlarm (5) <Polarity> (2)
         
        "
	::= { pm1004AlmsfpWarnDdmEntry 8 }


pm1004AlmVccHighWngPortn OBJECT-TYPE
	SYNTAX  EkiOnOff
	MAX-ACCESS read-only
	STATUS current
	DESCRIPTION
        "
        Client SFP Power Supply High Warning 
        :Warning indicating that the SFP 
        power supply of port is higher
         than the threshold value written 
        in the SFP EEPROM  <Condtype> VCC_HIGH_WNG_1 
        <Probcause> powerProblem (36) <Alarmtype> 
        equipmentAlarm (5) <Polarity> (2)
         
        "
	::= { pm1004AlmsfpWarnDdmEntry 7 }


pm1004AlmVccLowWngPortn OBJECT-TYPE
	SYNTAX  EkiOnOff
	MAX-ACCESS read-only
	STATUS current
	DESCRIPTION
        "
        Client SFP Power Supply Low Warning 
        :Warning indicating that the SFP 
        power supply of port is lower than 
        the threshold value written in
         the SFP EEPROM  <Condtype> VCC_LOW_WNG_1 
        <Probcause> powerProblem (36) <Alarmtype> 
        equipmentAlarm (5) <Polarity> (2)
         
        "
	::= { pm1004AlmsfpWarnDdmEntry 6 }


pm1004AlmTxBiasHighWngPortn OBJECT-TYPE
	SYNTAX  EkiOnOff
	MAX-ACCESS read-only
	STATUS current
	DESCRIPTION
        "
        Client SFP Bias High Warning :Warning 
        indicating that the SFP laser bias 
        current of port is higher than
         the threshold value written in 
        the SFP EEPROM <Condtype> TX_BIAS_HIGH_WNG_1 
        <Probcause> transmitterFailure
         (56) <Alarmtype> equipmentAlarm 
        (5) <Polarity> (2) 
        "
	::= { pm1004AlmsfpWarnDdmEntry 5 }


pm1004AlmTxBiasLowWngPortn OBJECT-TYPE
	SYNTAX  EkiOnOff
	MAX-ACCESS read-only
	STATUS current
	DESCRIPTION
        "
        Client SFP Bias Low Warning :Warning 
        indicating that the SFP laser bias 
        current of port is lower than the 
        threshold value written in the
         SFP EEPROM <Condtype> TX_BIAS_LOW_WNG_1 
        <Probcause> transmitterFailure
         (56) <Alarmtype> equipmentAlarm 
        (5) <Polarity> (2) 
        "
	::= { pm1004AlmsfpWarnDdmEntry 4 }


pm1004AlmTxPwrHighWngPortn OBJECT-TYPE
	SYNTAX  EkiOnOff
	MAX-ACCESS read-only
	STATUS current
	DESCRIPTION
        "
        Client SFP Tx Power High Warning 
        :Warning indicating that the SFP 
        output power of port is higher
         than the threshold value written 
        in the SFP EEPROM <Condtype> TX_PWR_HIGH_WNG_1 
        <Probcause> transmitterFailure
         (56) <Alarmtype> equipmentAlarm 
        (5) <Polarity> (2) 
        "
	::= { pm1004AlmsfpWarnDdmEntry 3 }


pm1004AlmTxPwLowWngPortn OBJECT-TYPE
	SYNTAX  EkiOnOff
	MAX-ACCESS read-only
	STATUS current
	DESCRIPTION
        "
        Client SFP Tx Power Low Warning 
        :Warning indicating that the SFP 
        output power of port is lower than 
        the threshold value written in
         the SFP EEPROM <Condtype> TX_PW_LOW_WNG_1 
        <Probcause> transmitterFailure
         (56) <Alarmtype> equipmentAlarm 
        (5) <Polarity> (2) 
        "
	::= { pm1004AlmsfpWarnDdmEntry 2 }


--- *********************************************************
---     TABLE for the pm1004AlmmapperDeAlm articles
--- *********************************************************

pm1004AlmmapperDeAlmTable OBJECT-TYPE
	SYNTAX  SEQUENCE OF Pm1004AlmmapperDeAlmEntry
	MAX-ACCESS not-accessible
	STATUS current
	DESCRIPTION
        "
        List of pm1004AlmmapperDeAlm Articl
        e
        "
	::= { pm1004AlmClientCrit 72 }


pm1004AlmmapperDeAlmEntry OBJECT-TYPE
	SYNTAX Pm1004AlmmapperDeAlmEntry
	MAX-ACCESS not-accessible
	STATUS current
	DESCRIPTION
        "
        Row definition for the pm1004AlmmapperDeAlm 
        table
        "
	INDEX   { pm1004AlmmapperDeAlmIndex }
	::= { pm1004AlmmapperDeAlmTable 1 }


Pm1004AlmmapperDeAlmEntry ::=
	SEQUENCE {
	pm1004AlmmapperDeAlmIndex
		INTEGER,
	pm1004AlmDwBufferOvlPortn
		EkiOnOff,
	pm1004AlmDwCsfDetPortn
		EkiOnOff,
	pm1004AlmUpBufferOvlPortn
		EkiOnOff,
	pm1004AlmUpAccOosPortn
		EkiOnOff
	}


pm1004AlmmapperDeAlmIndex OBJECT-TYPE
	SYNTAX  INTEGER(0..128)
	MAX-ACCESS  read-only
	STATUS current
	DESCRIPTION
        "
        Index definition for the pm1004AlmmapperDeAlm 
        table
        "
	::= { pm1004AlmmapperDeAlmEntry 1 }


pm1004AlmDwBufferOvlPortn OBJECT-TYPE
	SYNTAX  EkiOnOff
	MAX-ACCESS read-only
	STATUS current
	DESCRIPTION
        "
        Client Downstream Buffer Overload 
        :This OID indicates that the de-mapper 
        buffer for client port is in overload. 
         <Help>  This alarm indicates if 
        there is a downstream FIFO overload 
        for this client port <Condtype> 
        DW_BUFFER_OVL_1 <Probcause> equipmentMalfunction 
        (16) <Alarmtype> equipmentAlarm 
        (5) <Polarity> (2) 
        "
	::= { pm1004AlmmapperDeAlmEntry 15 }


pm1004AlmDwCsfDetPortn OBJECT-TYPE
	SYNTAX  EkiOnOff
	MAX-ACCESS read-only
	STATUS current
	DESCRIPTION
        "
        Client Signal Fail Detected :This 
        OID indicates that a CSF has been 
        detected on client port in the
         downstream direction   <Help>
          This alarm indicates if a Client 
        Signal Fail has been detected in 
        the incoming line frame for this 
        client port <Condtype> DW_CSF_DET_1 
        <Probcause> receiveFailure (41) 
        <Alarmtype> equipmentAlarm (5)
         <Polarity> (2) 
        "
	::= { pm1004AlmmapperDeAlmEntry 12 }


pm1004AlmUpBufferOvlPortn OBJECT-TYPE
	SYNTAX  EkiOnOff
	MAX-ACCESS read-only
	STATUS current
	DESCRIPTION
        "
        Client Upstream Buffer Overload 
        :This OID indicates that the rate 
        adaptation buffer for client port 
        is in overload.  <Help>  This alarm 
        indicates if there is a upstream 
        FIFO overload for this client port 
        <Condtype> UP_BUFFER_OVL_1 <Probcause> 
        receiveFailure (41) <Alarmtype> 
        integrityViolation (7) <Polarity> 
        (2) 
        "
	::= { pm1004AlmmapperDeAlmEntry 11 }


pm1004AlmUpAccOosPortn OBJECT-TYPE
	SYNTAX  EkiOnOff
	MAX-ACCESS read-only
	STATUS current
	DESCRIPTION
        "
        Client Loss Of Frame :This OID 
        indicates the upstream client input 
        port is in Loss of Frame condition 
         <Help>  This alarm indicates if 
        there is a Loss of Frame is detected 
        on the client input signal <Condtype> 
        UP_ACC_OOS_1 <Probcause> receiveFailure 
        (41) <Alarmtype> integrityViolation 
        (7) <Polarity> (2) 
        "
	::= { pm1004AlmmapperDeAlmEntry 2 }


--- *********************************************************
---     TABLE for the pm1004Almk1K2Client articles
--- *********************************************************

pm1004Almk1K2ClientTable OBJECT-TYPE
	SYNTAX  SEQUENCE OF Pm1004Almk1K2ClientEntry
	MAX-ACCESS not-accessible
	STATUS current
	DESCRIPTION
        "
        List of pm1004Almk1K2Client Articl
        e
        "
	::= { pm1004AlmClientNurg 96 }


pm1004Almk1K2ClientEntry OBJECT-TYPE
	SYNTAX Pm1004Almk1K2ClientEntry
	MAX-ACCESS not-accessible
	STATUS current
	DESCRIPTION
        "
        Row definition for the pm1004Almk1K2Client 
        table
        "
	INDEX   { pm1004Almk1K2ClientIndex }
	::= { pm1004Almk1K2ClientTable 1 }


Pm1004Almk1K2ClientEntry ::=
	SEQUENCE {
	pm1004Almk1K2ClientIndex
		INTEGER,
	pm1004Almk1K2ClientPortn
		INTEGER 
	}


pm1004Almk1K2ClientIndex OBJECT-TYPE
	SYNTAX  INTEGER(0..128)
	MAX-ACCESS  read-only
	STATUS current
	DESCRIPTION
        "
        Index definition for the pm1004Almk1K2Client 
        table
        "
	::= { pm1004Almk1K2ClientEntry 1 }


pm1004Almk1K2ClientPortn OBJECT-TYPE
	SYNTAX  INTEGER (0..65535)
	MAX-ACCESS read-only
	STATUS current
	DESCRIPTION
        "
        Client K1-K2 Extracted Value :This 
        OID gives the value of K1 (LSB) 
        and K2 (MSB) extracted from the 
        overhead of the received OC-48c/STM-16c 
        signal <Condtype> CLIENT_1_K1_8 
        <Probcause> other (1) <Alarmtype> 
        other (1) <Polarity> (2)
        "
	::= { pm1004Almk1K2ClientEntry 2 }


--- *********************************************************
---     TABLE for the pm1004AlmaccessioSdhAlarm articles
--- *********************************************************

pm1004AlmaccessioSdhAlarmTable OBJECT-TYPE
	SYNTAX  SEQUENCE OF Pm1004AlmaccessioSdhAlarmEntry
	MAX-ACCESS not-accessible
	STATUS current
	DESCRIPTION
        "
        List of pm1004AlmaccessioSdhAlarm 
        Article
        "
	::= { pm1004AlmClientCrit 104 }


pm1004AlmaccessioSdhAlarmEntry OBJECT-TYPE
	SYNTAX Pm1004AlmaccessioSdhAlarmEntry
	MAX-ACCESS not-accessible
	STATUS current
	DESCRIPTION
        "
        Row definition for the pm1004AlmaccessioSdhAlarm 
        table
        "
	INDEX   { pm1004AlmaccessioSdhAlarmIndex }
	::= { pm1004AlmaccessioSdhAlarmTable 1 }


Pm1004AlmaccessioSdhAlarmEntry ::=
	SEQUENCE {
	pm1004AlmaccessioSdhAlarmIndex
		INTEGER,
	pm1004AlmClientOofPortn
		EkiOnOff,
	pm1004AlmClientRdiDetPortn
		EkiOnOff,
	pm1004AlmClientAisDetPortn
		EkiOnOff,
	pm1004AlmTxLossOfLockPortn
		EkiOnOff,
	pm1004AlmRxLossOfLockPortn
		EkiOnOff,
	pm1004AlmFifoErrPortn
		EkiOnOff
	}


pm1004AlmaccessioSdhAlarmIndex OBJECT-TYPE
	SYNTAX  INTEGER(0..128)
	MAX-ACCESS  read-only
	STATUS current
	DESCRIPTION
        "
        Index definition for the pm1004AlmaccessioSdhAlarm 
        table
        "
	::= { pm1004AlmaccessioSdhAlarmEntry 1 }


pm1004AlmClientOofPortn OBJECT-TYPE
	SYNTAX  EkiOnOff
	MAX-ACCESS read-only
	STATUS current
	DESCRIPTION
        "
        Client Out Of Frame :This OID
         indicates that an Out Of Frame 
        condition has been detected on
         the OC-48/STM-16 client input
         stream   <Help>  This alarm indicates 
        if there is a Out of Frame is detected 
        on the client input signal <Condtype> 
        CLIENT_OOF_1 <Probcause> receiveFailure 
        (41) <Alarmtype> integrityViolation 
        (7) <Polarity> (2) 
        "
	::= { pm1004AlmaccessioSdhAlarmEntry 8 }


pm1004AlmClientRdiDetPortn OBJECT-TYPE
	SYNTAX  EkiOnOff
	MAX-ACCESS read-only
	STATUS current
	DESCRIPTION
        "
        Client MS-RDI :This OID indicates 
        that a MS-RDI has been detected 
        on the client input stream  <Help> 
         This alarm indicates if there
         is a MS-RDI/L-RDI is detected
         on the client input signal <Condtype> 
        CLIENT_RDI_DET_1 <Probcause> remoteNodeTransmissionError 
        (43) <Alarmtype> other (1) <Polarity> 
        (2) 
        "
	::= { pm1004AlmaccessioSdhAlarmEntry 7 }


pm1004AlmClientAisDetPortn OBJECT-TYPE
	SYNTAX  EkiOnOff
	MAX-ACCESS read-only
	STATUS current
	DESCRIPTION
        "
        Client MS-AIS :This OID indicates 
        that a MS-AIS has been detected 
        on the client input stream  <Help> 
         This alarm indicates if there
         is a MS-AIS/L-AIS is detected
         on the client input signal <Condtype> 
        CLIENT_AIS_DET_1 <Probcause> receiveFailure 
        (41) <Alarmtype> operationalViolation 
        (8) <Polarity> (2) 
        "
	::= { pm1004AlmaccessioSdhAlarmEntry 6 }


pm1004AlmTxLossOfLockPortn OBJECT-TYPE
	SYNTAX  EkiOnOff
	MAX-ACCESS read-only
	STATUS current
	DESCRIPTION
        "
        Client Tx Clock Lock Error :This 
        OID indicates that the transmit 
        clock of the client transceiver 
        is not locke <Condtype> TX_LOSS_OF_LOCK_1 
        <Probcause> transmitterFailure
         (56) <Alarmtype> equipmentAlarm 
        (5) <Polarity> (2) 
        "
	::= { pm1004AlmaccessioSdhAlarmEntry 5 }


pm1004AlmRxLossOfLockPortn OBJECT-TYPE
	SYNTAX  EkiOnOff
	MAX-ACCESS read-only
	STATUS current
	DESCRIPTION
        "
        Client Rx Clock Lock Error :This 
        OID indicates the recovered receive 
        clock of the client transceiver 
        is not locked <Condtype> RX_LOSS_OF_LOCK_1 
        <Probcause> receiveFailure (41) 
        <Alarmtype> equipmentAlarm (5)
         <Polarity> (2) 
        "
	::= { pm1004AlmaccessioSdhAlarmEntry 4 }


pm1004AlmFifoErrPortn OBJECT-TYPE
	SYNTAX  EkiOnOff
	MAX-ACCESS read-only
	STATUS current
	DESCRIPTION
        "
        Client Transceiver Fifo Error
         :This OID indicates that an error 
        has been detected in the FIFO of 
        the client transceiver <Condtype> 
        FIFO_ERR_1 <Probcause> transmitterFailure 
        (56) <Alarmtype> equipmentAlarm 
        (5) <Polarity> (2) 
        "
	::= { pm1004AlmaccessioSdhAlarmEntry 3 }


--- *********************************************************
---     TABLE for the pm1004Almj0Alarm articles
--- *********************************************************

pm1004Almj0AlarmTable OBJECT-TYPE
	SYNTAX  SEQUENCE OF Pm1004Almj0AlarmEntry
	MAX-ACCESS not-accessible
	STATUS current
	DESCRIPTION
        "
        List of pm1004Almj0Alarm Articl
        e
        "
	::= { pm1004MonClientTraceIdentifier 2112 }


pm1004Almj0AlarmEntry OBJECT-TYPE
	SYNTAX Pm1004Almj0AlarmEntry
	MAX-ACCESS not-accessible
	STATUS current
	DESCRIPTION
        "
        Row definition for the pm1004Almj0Alarm 
        table
        "
	INDEX   { pm1004Almj0AlarmIndex }
	::= { pm1004Almj0AlarmTable 1 }


Pm1004Almj0AlarmEntry ::=
	SEQUENCE {
	pm1004Almj0AlarmIndex
		INTEGER,
	pm1004AlmCrc7ErrorPortn
		EkiOnOff,
	pm1004AlmJ0TiiAlarmPortn
		EkiOnOff,
	pm1004AlmJ0TimAlarmPortn
		EkiOnOff
	}


pm1004Almj0AlarmIndex OBJECT-TYPE
	SYNTAX  INTEGER(0..128)
	MAX-ACCESS  read-only
	STATUS current
	DESCRIPTION
        "
        Index definition for the pm1004Almj0Alarm 
        table
        "
	::= { pm1004Almj0AlarmEntry 1 }


pm1004AlmCrc7ErrorPortn OBJECT-TYPE
	SYNTAX  EkiOnOff
	MAX-ACCESS read-only
	STATUS current
	DESCRIPTION
        "
        CRC Error On Trace Identifier
         :This OID indicates that a CRC 
        error has been detected in the
         stable Trace Identifier on the 
        client input stream <Condtype>
         CRC7_ERROR_1 <Probcause> other 
        (1) <Alarmtype> other (1) <Polarity> 
        (2) 
        "
	::= { pm1004Almj0AlarmEntry 4 }


pm1004AlmJ0TiiAlarmPortn OBJECT-TYPE
	SYNTAX  EkiOnOff
	MAX-ACCESS read-only
	STATUS current
	DESCRIPTION
        "
        Trace Identifier Unstable :This 
        OID indicates the Trace Identifier 
        is unstable on the client input 
        stream <Condtype> J0_TII_ALARM_1 
        <Probcause> other (1) <Alarmtype> 
        other (1) <Polarity> (2) 
        "
	::= { pm1004Almj0AlarmEntry 3 }


pm1004AlmJ0TimAlarmPortn OBJECT-TYPE
	SYNTAX  EkiOnOff
	MAX-ACCESS read-only
	STATUS current
	DESCRIPTION
        "
        Trace Identifier Mismatch :This 
        OID indicates a Trace Identifier 
        Mismatch has been detected on the 
        client input stream <Condtype>
         J0_TIM_ALARM_1 <Probcause> other 
        (1) <Alarmtype> other (1) <Polarity> 
        (2) 
        "
	::= { pm1004Almj0AlarmEntry 2 }


--- *********************************************************
---     TABLE for the pm1004AlmdfrmAlm articles
--- *********************************************************

pm1004AlmdfrmAlmTable OBJECT-TYPE
	SYNTAX  SEQUENCE OF Pm1004AlmdfrmAlmEntry
	MAX-ACCESS not-accessible
	STATUS current
	DESCRIPTION
        "
        List of pm1004AlmdfrmAlm Articl
        e
        "
	::= { pm1004AlmLineCrit 128 }


pm1004AlmdfrmAlmEntry OBJECT-TYPE
	SYNTAX Pm1004AlmdfrmAlmEntry
	MAX-ACCESS not-accessible
	STATUS current
	DESCRIPTION
        "
        Row definition for the pm1004AlmdfrmAlm 
        table
        "
	INDEX   { pm1004AlmdfrmAlmIndex }
	::= { pm1004AlmdfrmAlmTable 1 }


Pm1004AlmdfrmAlmEntry ::=
	SEQUENCE {
	pm1004AlmdfrmAlmIndex
		INTEGER,
	pm1004AlmDwLofPortn
		EkiOnOff,
	pm1004AlmDwOofPortn
		EkiOnOff,
	pm1004AlmDwRdiDetPortn
		EkiOnOff,
	pm1004AlmDwAisDetPortn
		EkiOnOff
	}


pm1004AlmdfrmAlmIndex OBJECT-TYPE
	SYNTAX  INTEGER(0..128)
	MAX-ACCESS  read-only
	STATUS current
	DESCRIPTION
        "
        Index definition for the pm1004AlmdfrmAlm 
        table
        "
	::= { pm1004AlmdfrmAlmEntry 1 }


pm1004AlmDwLofPortn OBJECT-TYPE
	SYNTAX  EkiOnOff
	MAX-ACCESS read-only
	STATUS current
	DESCRIPTION
        "
        Line Loss Of Frame :This OID indicates 
        that a Loss Of Frame has been detected 
        on G709 input signal  <Help>  This 
        alarm indicates if there is a G,709 
        Loss of Frame is detected on the 
        line input signal <Condtype> DW_LOF_1 
        <Probcause> receiveFailure (41) 
        <Alarmtype> integrityViolation
         (7) <Polarity> (2) 
        "
	::= { pm1004AlmdfrmAlmEntry 5 }


pm1004AlmDwOofPortn OBJECT-TYPE
	SYNTAX  EkiOnOff
	MAX-ACCESS read-only
	STATUS current
	DESCRIPTION
        "
        Line Out Of Frame :This OID indicates 
        that an Out Of Frame has been detected 
        on G709 input signal  <Help>  This 
        alarm indicates if there is a G,709 
        Out of Frame is detected on the 
        line input signal <Condtype> DW_OOF_1 
        <Probcause> receiveFailure (41) 
        <Alarmtype> integrityViolation
         (7) <Polarity> (2) 
        "
	::= { pm1004AlmdfrmAlmEntry 4 }


pm1004AlmDwRdiDetPortn OBJECT-TYPE
	SYNTAX  EkiOnOff
	MAX-ACCESS read-only
	STATUS current
	DESCRIPTION
        "
        OTU2 SM-BDI Detected On Line Input 
        :This OID indicates that an SM-BDI 
        has been detected on G709 input 
        signal  <Help>  This alarm indicates 
        if there is a SM-BDI is detected 
        on the line input signal <Condtype> 
        DW_RDI_DET_1 <Probcause> remoteNodeTransmissionError 
        (43) <Alarmtype> other (1) <Polarity> 
        (2) 
        "
	::= { pm1004AlmdfrmAlmEntry 3 }


pm1004AlmDwAisDetPortn OBJECT-TYPE
	SYNTAX  EkiOnOff
	MAX-ACCESS read-only
	STATUS current
	DESCRIPTION
        "
        ODU2 AIS Detected On Line Input 
        :This OID indicates that an ODU2-AIS 
        has been detected on G709 input 
        signal  <Help>  This alarm indicates 
        if there is a ODU2 AIS is detected 
        on the line input signal <Condtype> 
        DW_AIS_DET_1 <Probcause> receiveFailure 
        (41) <Alarmtype> operationalViolation 
        (8) <Polarity> (2) 
        "
	::= { pm1004AlmdfrmAlmEntry 2 }


--- *********************************************************
---     TABLE for the pm1004AlmdfrmBer articles
--- *********************************************************

pm1004AlmdfrmBerTable OBJECT-TYPE
	SYNTAX  SEQUENCE OF Pm1004AlmdfrmBerEntry
	MAX-ACCESS not-accessible
	STATUS current
	DESCRIPTION
        "
        List of pm1004AlmdfrmBer Articl
        e
        "
	::= { pm1004AlmLineUrg 129 }


pm1004AlmdfrmBerEntry OBJECT-TYPE
	SYNTAX Pm1004AlmdfrmBerEntry
	MAX-ACCESS not-accessible
	STATUS current
	DESCRIPTION
        "
        Row definition for the pm1004AlmdfrmBer 
        table
        "
	INDEX   { pm1004AlmdfrmBerIndex }
	::= { pm1004AlmdfrmBerTable 1 }


Pm1004AlmdfrmBerEntry ::=
	SEQUENCE {
	pm1004AlmdfrmBerIndex
		INTEGER,
	pm1004AlmLineDegradePortn
		EkiOnOff,
	pm1004AlmLineSignalFailPortn
		EkiOnOff,
	pm1004AlmLineSignalDegradePortn
		EkiOnOff
	}


pm1004AlmdfrmBerIndex OBJECT-TYPE
	SYNTAX  INTEGER(0..128)
	MAX-ACCESS  read-only
	STATUS current
	DESCRIPTION
        "
        Index definition for the pm1004AlmdfrmBer 
        table
        "
	::= { pm1004AlmdfrmBerEntry 1 }


pm1004AlmLineDegradePortn OBJECT-TYPE
	SYNTAX  EkiOnOff
	MAX-ACCESS read-only
	STATUS current
	DESCRIPTION
        "
        Fixed Line Signal Degrade :This 
        OID indicates that the line input 
        signal is DEGRADE. The assetion 
        hysteresis is fixed to 10-8 (assertion) 
        and 10-9 (de-assertion) <Condtype> 
        LINE_DEGRADE_1 <Probcause> degradedSignal 
        (13) <Alarmtype> qualityOfServiceAlarm 
        (3) <Polarity> (2) 
        "
	::= { pm1004AlmdfrmBerEntry 6 }


pm1004AlmLineSignalFailPortn OBJECT-TYPE
	SYNTAX  EkiOnOff
	MAX-ACCESS read-only
	STATUS current
	DESCRIPTION
        "
        Custom Line Signal Fail :This
         OID indicates that the line input 
        signal is FAIL. The assertion hysteresis 
        can be customized by the host <Condtype> 
        LINE_SIGNAL_FAIL_1 <Probcause>
         receiveFailure (41) <Alarmtype> 
        integrityViolation (7) <Polarity> 
        (2) 
        "
	::= { pm1004AlmdfrmBerEntry 3 }


pm1004AlmLineSignalDegradePortn OBJECT-TYPE
	SYNTAX  EkiOnOff
	MAX-ACCESS read-only
	STATUS current
	DESCRIPTION
        "
        Custom Line Signal Degrade :This 
        OID indicates that the line input 
        signal is DEGRADE. The assertion 
        hysteresis can customized by the 
        host <Condtype> LINE_SIGNAL_DEGRADE_1 
        <Probcause> degradedSignal (13) 
        <Alarmtype> qualityOfServiceAlarm 
        (3) <Polarity> (2) 
        "
	::= { pm1004AlmdfrmBerEntry 2 }


--- *********************************************************
---     TABLE for the pm1004AlmlineSyncAlarms articles
--- *********************************************************

pm1004AlmlineSyncAlarmsTable OBJECT-TYPE
	SYNTAX  SEQUENCE OF Pm1004AlmlineSyncAlarmsEntry
	MAX-ACCESS not-accessible
	STATUS current
	DESCRIPTION
        "
        List of pm1004AlmlineSyncAlarms 
        Article
        "
	::= { pm1004AlmLineCrit 133 }


pm1004AlmlineSyncAlarmsEntry OBJECT-TYPE
	SYNTAX Pm1004AlmlineSyncAlarmsEntry
	MAX-ACCESS not-accessible
	STATUS current
	DESCRIPTION
        "
        Row definition for the pm1004AlmlineSyncAlarms 
        table
        "
	INDEX   { pm1004AlmlineSyncAlarmsIndex }
	::= { pm1004AlmlineSyncAlarmsTable 1 }


Pm1004AlmlineSyncAlarmsEntry ::=
	SEQUENCE {
	pm1004AlmlineSyncAlarmsIndex
		INTEGER,
	pm1004AlmDwLosPortn
		EkiOnOff,
	pm1004AlmUpLockerrPortn
		EkiOnOff,
	pm1004AlmDwLockerrPortn
		EkiOnOff
	}


pm1004AlmlineSyncAlarmsIndex OBJECT-TYPE
	SYNTAX  INTEGER(0..128)
	MAX-ACCESS  read-only
	STATUS current
	DESCRIPTION
        "
        Index definition for the pm1004AlmlineSyncAlarms 
        table
        "
	::= { pm1004AlmlineSyncAlarmsEntry 1 }


pm1004AlmDwLosPortn OBJECT-TYPE
	SYNTAX  EkiOnOff
	MAX-ACCESS read-only
	STATUS current
	DESCRIPTION
        "
        Line Input Loss Of Signal :This 
        OID indicates a loss of signal
         on the 10 Gb/s input.  <Help>
          This alarm indicates if an optical 
        signal is detected on the line
         transceiver input <Condtype> DW_LOS 
        <Probcause> receiveFailure (41) 
        <Alarmtype> physicalViolation (9) 
        <Polarity> (2) 
        "
	::= { pm1004AlmlineSyncAlarmsEntry 17 }


pm1004AlmUpLockerrPortn OBJECT-TYPE
	SYNTAX  EkiOnOff
	MAX-ACCESS read-only
	STATUS current
	DESCRIPTION
        "
        Upstream Clock Lock Error :This 
        OID indicates that the serializer 
        output 10 Gb/s clock multiplier 
        unit is not locked. <Condtype>
         UP_LOCKERR <Probcause> receiveFailure 
        (41) <Alarmtype> equipmentAlarm 
        (5) <Polarity> (2) 
        "
	::= { pm1004AlmlineSyncAlarmsEntry 14 }


pm1004AlmDwLockerrPortn OBJECT-TYPE
	SYNTAX  EkiOnOff
	MAX-ACCESS read-only
	STATUS current
	DESCRIPTION
        "
        Downstream Clock Lock Error :This 
        OID indicates that the deserializer 
        input 10 Gb/s clock recovery is 
        not locked. <Condtype> DW_LOCKERR 
        <Probcause> receiveFailure (41) 
        <Alarmtype> equipmentAlarm (5)
         <Polarity> (2) 
        "
	::= { pm1004AlmlineSyncAlarmsEntry 13 }


--- *****************************************************
---     LEAF for the modInitFailLevel2 article
--- *****************************************************
pm1004AlmmodInitFailLevel2 OBJECT IDENTIFIER ::= { pm1004AlmOtherUrg 194 }




pm1004AlmSwInitFail OBJECT-TYPE
	  SYNTAX EkiOnOff
	  MAX-ACCESS read-only
	  STATUS current
	  DESCRIPTION
        "
        SW Init Fail :This OID indicates 
        that the SW intialization has caused 
        unknown intial conditions  <Help> 
         This alarm indicates if the SW 
        module is correctly initialized 
        <Condtype> SW_INIT_FAIL <Probcause> 
        softwareError (47) <Alarmtype>
         processingErrorAlarm (4) <Polarity> 
        (2) 
        "
	  ::= { pm1004AlmmodInitFailLevel2 5 }



pm1004AlmResetHwInitFail OBJECT-TYPE
	  SYNTAX EkiOnOff
	  MAX-ACCESS read-only
	  STATUS current
	  DESCRIPTION
        "
        Reset HW Init Fail :This OID indicates 
        that the HW intialization has caused 
        unknown intial conditions  <Help> 
         This alarm indicates if the HW 
        has been correctly initialized
         <Condtype> RESET_HW_INIT_FAIL
         <Probcause> softwareError (47) 
        <Alarmtype> processingErrorAlarm 
        (4) <Polarity> (2) 
        "
	  ::= { pm1004AlmmodInitFailLevel2 4 }



pm1004AlmBootUndone OBJECT-TYPE
	  SYNTAX EkiOnOff
	  MAX-ACCESS read-only
	  STATUS current
	  DESCRIPTION
        "
        Boot Undone :This OID indicates 
        that the boot has not been correctly 
        achieved  <Help>  This alarm indicates 
        if the module has correctly boot 
        <Condtype> BOOT_UNDONE <Probcause> 
        softwareError (47) <Alarmtype>
         processingErrorAlarm (4) <Polarity> 
        (2) 
        "
	  ::= { pm1004AlmmodInitFailLevel2 3 }



pm1004AlmNextColdBootForced OBJECT-TYPE
	  SYNTAX EkiOnOff
	  MAX-ACCESS read-only
	  STATUS current
	  DESCRIPTION
        "
        Next Cold Boot Forced :This OID 
        indicates that the next Reset will 
        be forced Cold  <Help>  This alarm 
        indicates that the next reset of 
        the module will be forced to cold 
        reset <Condtype> NEXT_COLD_BOOT_FORCED 
        <Probcause> informationalStatus(1000) 
        <Alarmtype> other (1) <Polarity> 
        (2) 
        "
	  ::= { pm1004AlmmodInitFailLevel2 2 }



pm1004AlmLedFail OBJECT-TYPE
	  SYNTAX EkiOnOff
	  MAX-ACCESS read-only
	  STATUS current
	  DESCRIPTION
        "
        Led Fail :This OID indicates that 
        Led register has not been correctly 
        initalized  <Help>  This alarm
         indicates if the module LEDs are 
        correctly initialized <Condtype> 
        LED_FAIL <Probcause> softwareError 
        (47) <Alarmtype> processingErrorAlarm 
        (4) <Polarity> (2) 
        "
	  ::= { pm1004AlmmodInitFailLevel2 1 }



--- *****************************************************
---     LEAF for the modInitFailLevel3 article
--- *****************************************************
pm1004AlmmodInitFailLevel3 OBJECT IDENTIFIER ::= { pm1004AlmOtherUrg 195 }




pm1004AlmClient4InitFail OBJECT-TYPE
	  SYNTAX EkiOnOff
	  MAX-ACCESS read-only
	  STATUS current
	  DESCRIPTION
        "
        Client4 Init Fail :This OID indicates 
        that Client 4 registers subset
         has not been correctly initialized 
         <Help>  This alarm indicates if 
        the client port 4 is correctly
         initialized <Condtype> CLIENT4_INIT_FAIL 
        <Probcause> softwareError (47)
         <Alarmtype> processingErrorAlarm 
        (4) <Polarity> (2) 
        "
	  ::= { pm1004AlmmodInitFailLevel3 12 }



pm1004AlmClient3InitFail OBJECT-TYPE
	  SYNTAX EkiOnOff
	  MAX-ACCESS read-only
	  STATUS current
	  DESCRIPTION
        "
        Client3 Init Fail :This OID indicates 
        that Client 3 registers subset
         has not been correctly initialized 
         <Help>  This alarm indicates if 
        the client port 3 is correctly
         initialized <Condtype> CLIENT3_INIT_FAIL 
        <Probcause> softwareError (47)
         <Alarmtype> processingErrorAlarm 
        (4) <Polarity> (2) 
        "
	  ::= { pm1004AlmmodInitFailLevel3 11 }



pm1004AlmClient2InitFail OBJECT-TYPE
	  SYNTAX EkiOnOff
	  MAX-ACCESS read-only
	  STATUS current
	  DESCRIPTION
        "
        Client2 Init Fail :This OID indicates 
        that Client 2 registers subset
         has not been correctly initialized 
         <Help>  This alarm indicates if 
        the client port 2 is correctly
         initialized <Condtype> CLIENT2_INIT_FAIL 
        <Probcause> softwareError (47)
         <Alarmtype> processingErrorAlarm 
        (4) <Polarity> (2) 
        "
	  ::= { pm1004AlmmodInitFailLevel3 10 }



pm1004AlmClient1InitFail OBJECT-TYPE
	  SYNTAX EkiOnOff
	  MAX-ACCESS read-only
	  STATUS current
	  DESCRIPTION
        "
        Client1 Init Fail :This OID indicates 
        that Client 1 registers subset
         has not been correctly initialized 
         <Help>  This alarm indicates if 
        the client port 1 is correctly
         initialized <Condtype> CLIENT1_INIT_FAIL 
        <Probcause> softwareError (47)
         <Alarmtype> processingErrorAlarm 
        (4) <Polarity> (2) 
        "
	  ::= { pm1004AlmmodInitFailLevel3 9 }



pm1004AlmLine2InitFail OBJECT-TYPE
	  SYNTAX EkiOnOff
	  MAX-ACCESS read-only
	  STATUS current
	  DESCRIPTION
        "
        Line2 Init Fail :This OID indicates 
        that the Line register subset has 
        not been correctly initialized
          <Help>  This alarm indicates
         if the line port 2 is correctly 
        initialized <Condtype> LINE2_INIT_FAIL 
        <Probcause> softwareError (47)
         <Alarmtype> processingErrorAlarm 
        (4) <Polarity> (2) 
        "
	  ::= { pm1004AlmmodInitFailLevel3 8 }



pm1004AlmLine1InitFail OBJECT-TYPE
	  SYNTAX EkiOnOff
	  MAX-ACCESS read-only
	  STATUS current
	  DESCRIPTION
        "
        Line1 Init Fail :This OID indicates 
        that the Line registersvsubset
         has not been correctly initialized 
         <Help>  This alarm indicates if 
        the line port 1 is correctly initialized 
        <Condtype> LINE1_INIT_FAIL <Probcause> 
        softwareError (47) <Alarmtype>
         processingErrorAlarm (4) <Polarity> 
        (2) 
        "
	  ::= { pm1004AlmmodInitFailLevel3 7 }



pm1004AlmXfp2InitFail OBJECT-TYPE
	  SYNTAX EkiOnOff
	  MAX-ACCESS read-only
	  STATUS current
	  DESCRIPTION
        "
        XFP2 Init Fail :This OID indicates 
        that the XFP has not been correctly 
        initialized  <Help>  This alarm 
        indicates if the line transceiver 
        2 is correctly initialized <Condtype> 
        XFP2_INIT_FAIL <Probcause> softwareError 
        (47) <Alarmtype> processingErrorAlarm 
        (4) <Polarity> (2) 
        "
	  ::= { pm1004AlmmodInitFailLevel3 6 }



pm1004AlmXfp1InitFail OBJECT-TYPE
	  SYNTAX EkiOnOff
	  MAX-ACCESS read-only
	  STATUS current
	  DESCRIPTION
        "
        XFP1 Init Fail :This OID indicates 
        that the XFP has not been correctly 
        initialized  <Help>  This alarm 
        indicates if the line transceiver 
        1 is correctly initialized <Condtype> 
        XFP1_INIT_FAIL <Probcause> softwareError 
        (47) <Alarmtype> processingErrorAlarm 
        (4) <Polarity> (2) 
        "
	  ::= { pm1004AlmmodInitFailLevel3 5 }



pm1004AlmInitModuleFail OBJECT-TYPE
	  SYNTAX EkiOnOff
	  MAX-ACCESS read-only
	  STATUS current
	  DESCRIPTION
        "
        Init Module Fail :This OID indicates 
        that the Module has not been correctly 
        initialized  <Help>  This alarm 
        indicates if the SW module is correctly 
        initialized <Condtype> INIT_MODULE_FAIL 
        <Probcause> softwareError (47)
         <Alarmtype> processingErrorAlarm 
        (4) <Polarity> (2) 
        "
	  ::= { pm1004AlmmodInitFailLevel3 3 }



pm1004AlmObmTypeReadFail OBJECT-TYPE
	  SYNTAX EkiOnOff
	  MAX-ACCESS read-only
	  STATUS current
	  DESCRIPTION
        "
        OBM Type Read Fail :This OID indicates 
        that OBM type has not been recognized 
         <Help>  This alarm indicates if 
        the OBM board has been correctly 
        identified <Condtype> OBM_TYPE_READ_FAIL 
        <Probcause> softwareError (47)
         <Alarmtype> processingErrorAlarm 
        (4) <Polarity> (2) 
        "
	  ::= { pm1004AlmmodInitFailLevel3 2 }



pm1004AlmGwIdentFail OBJECT-TYPE
	  SYNTAX EkiOnOff
	  MAX-ACCESS read-only
	  STATUS current
	  DESCRIPTION
        "
        GW Ident Fail :This OID indicates 
        that GW identification has not
         been read  <Help>  This alarm
         indicates if the GW has been correctly 
        identified <Condtype> GW_IDENT_FAIL 
        <Probcause> softwareError (47)
         <Alarmtype> processingErrorAlarm 
        (4) <Polarity> (2) 
        "
	  ::= { pm1004AlmmodInitFailLevel3 1 }



--- *********************************************************
---     TABLE for the pm1004AlmlineXfp1Alarm articles
--- *********************************************************

pm1004AlmlineXfp1AlarmTable OBJECT-TYPE
	SYNTAX  SEQUENCE OF Pm1004AlmlineXfp1AlarmEntry
	MAX-ACCESS not-accessible
	STATUS current
	DESCRIPTION
        "
        List of pm1004AlmlineXfp1Alarm 
        Article
        "
	::= { pm1004AlmLineUrg 208 }


pm1004AlmlineXfp1AlarmEntry OBJECT-TYPE
	SYNTAX Pm1004AlmlineXfp1AlarmEntry
	MAX-ACCESS not-accessible
	STATUS current
	DESCRIPTION
        "
        Row definition for the pm1004AlmlineXfp1Alarm 
        table
        "
	INDEX   { pm1004AlmlineXfp1AlarmIndex }
	::= { pm1004AlmlineXfp1AlarmTable 1 }


Pm1004AlmlineXfp1AlarmEntry ::=
	SEQUENCE {
	pm1004AlmlineXfp1AlarmIndex
		INTEGER,
	pm1004AlmRxPowerHighAlarmPortn
		EkiOnOff,
	pm1004AlmRxPowerLowAlarmPortn
		EkiOnOff,
	pm1004AlmTempHighAlarmPortn
		EkiOnOff,
	pm1004AlmTempLowAlarmPortn
		EkiOnOff,
	pm1004AlmTxBiasHighAlarmPortn
		EkiOnOff,
	pm1004AlmTxBiasLowAlarmPortn
		EkiOnOff,
	pm1004AlmTxPowerHighAlarmPortn
		EkiOnOff,
	pm1004AlmTxPowerLowAlarmPortn
		EkiOnOff
	}


pm1004AlmlineXfp1AlarmIndex OBJECT-TYPE
	SYNTAX  INTEGER(0..128)
	MAX-ACCESS  read-only
	STATUS current
	DESCRIPTION
        "
        Index definition for the pm1004AlmlineXfp1Alarm 
        table
        "
	::= { pm1004AlmlineXfp1AlarmEntry 1 }


pm1004AlmRxPowerHighAlarmPortn OBJECT-TYPE
	SYNTAX  EkiOnOff
	MAX-ACCESS read-only
	STATUS current
	DESCRIPTION
        "
        Line Optical Rx Power High :Alarm 
        indicating that the XFP received 
        optical power is higher than the 
        threshold value written in the
         XFP EEPROM <Condtype> RX_POWER_HIGH_ALARM_1 
        <Probcause> receiveFailure (41) 
        <Alarmtype> equipmentAlarm (5)
         <Polarity> (2) 
        "
	::= { pm1004AlmlineXfp1AlarmEntry 17 }


pm1004AlmRxPowerLowAlarmPortn OBJECT-TYPE
	SYNTAX  EkiOnOff
	MAX-ACCESS read-only
	STATUS current
	DESCRIPTION
        "
        Line Optical Rx Power Low :Alarm 
        indicating that the XFP received 
        optical power is lower than the 
        threshold value written in the
         XFP EEPROM  <Condtype> RX_POWER_LOW_ALARM_1 
        <Probcause> receiveFailure (41) 
        <Alarmtype> equipmentAlarm (5)
         <Polarity> (2) 
        "
	::= { pm1004AlmlineXfp1AlarmEntry 16 }


pm1004AlmTempHighAlarmPortn OBJECT-TYPE
	SYNTAX  EkiOnOff
	MAX-ACCESS read-only
	STATUS current
	DESCRIPTION
        "
        Line Transceiver Temp High :Alarm 
        indicating that the XFP/OTX temperature 
        is higher than the threshold value 
        written in the XFP EEPROM <Condtype> 
        TEMP_HIGH_ALARM_1 <Probcause> temperatureUnacceptable 
        (51) <Alarmtype> equipmentAlarm 
        (5) <Polarity> (2) 
        "
	::= { pm1004AlmlineXfp1AlarmEntry 9 }


pm1004AlmTempLowAlarmPortn OBJECT-TYPE
	SYNTAX  EkiOnOff
	MAX-ACCESS read-only
	STATUS current
	DESCRIPTION
        "
        Line Transceiver Temp Low :Alarm 
        indicating that the XFP/OTX temperature 
        is lower than the threshold value 
        written in the XFP/OTX EEPROM <Condtype> 
        TEMP_LOW_ALARM_1 <Probcause> temperatureUnacceptable 
        (51) <Alarmtype> equipmentAlarm 
        (5) <Polarity> (2) 
        "
	::= { pm1004AlmlineXfp1AlarmEntry 8 }


pm1004AlmTxBiasHighAlarmPortn OBJECT-TYPE
	SYNTAX  EkiOnOff
	MAX-ACCESS read-only
	STATUS current
	DESCRIPTION
        "
        Line Transceiver Bias High :Alarm 
        indicating that the XFP/OTX transmitter 
        laser bias current is higher than 
        the threshold value written in
         the XFP EEPROM <Condtype> TX_BIAS_HIGH_ALARM_1 
        <Probcause> transmitterFailure
         (56) <Alarmtype> equipmentAlarm 
        (5) <Polarity> (2) 
        "
	::= { pm1004AlmlineXfp1AlarmEntry 5 }


pm1004AlmTxBiasLowAlarmPortn OBJECT-TYPE
	SYNTAX  EkiOnOff
	MAX-ACCESS read-only
	STATUS current
	DESCRIPTION
        "
        Line Transceiver Bias Low :Alarm 
        indicating that the XFP/OTX transmitter 
        laser bias current is lower than 
        the threshold value written in
         the XFP/OTX EEPROM <Condtype>
         TX_BIAS_LOW_ALARM_1 <Probcause> 
        transmitterFailure (56) <Alarmtype> 
        equipmentAlarm (5) <Polarity> (2)
         
        "
	::= { pm1004AlmlineXfp1AlarmEntry 4 }


pm1004AlmTxPowerHighAlarmPortn OBJECT-TYPE
	SYNTAX  EkiOnOff
	MAX-ACCESS read-only
	STATUS current
	DESCRIPTION
        "
        Line Optical Tx Power High :Alarm 
        indicating that the XFP/OTX transmitter 
        transmitter output power is higher 
        than the threshold value written 
        in the XFP EEPROM <Condtype> TX_POWER_HIGH_ALARM_1 
        <Probcause> transmitterFailure
         (56) <Alarmtype> equipmentAlarm 
        (5) <Polarity> (2) 
        "
	::= { pm1004AlmlineXfp1AlarmEntry 3 }


pm1004AlmTxPowerLowAlarmPortn OBJECT-TYPE
	SYNTAX  EkiOnOff
	MAX-ACCESS read-only
	STATUS current
	DESCRIPTION
        "
        Line Optical Tx Power Low :Alarm 
        indicating that the XFP/OTX transmitter 
        transmitter output power is lower 
        than the threshold value written 
        in the XFP/OTX EEPROM <Condtype> 
        TX_POWER_LOW_ALARM_1 <Probcause> 
        transmitterFailure (56) <Alarmtype> 
        equipmentAlarm (5) <Polarity> (2)
         
        "
	::= { pm1004AlmlineXfp1AlarmEntry 2 }


--- *********************************************************
---     TABLE for the pm1004AlmlineXfp1Warnings articles
--- *********************************************************

pm1004AlmlineXfp1WarningsTable OBJECT-TYPE
	SYNTAX  SEQUENCE OF Pm1004AlmlineXfp1WarningsEntry
	MAX-ACCESS not-accessible
	STATUS current
	DESCRIPTION
        "
        List of pm1004AlmlineXfp1Warnings 
        Article
        "
	::= { pm1004AlmLineNurg 209 }


pm1004AlmlineXfp1WarningsEntry OBJECT-TYPE
	SYNTAX Pm1004AlmlineXfp1WarningsEntry
	MAX-ACCESS not-accessible
	STATUS current
	DESCRIPTION
        "
        Row definition for the pm1004AlmlineXfp1Warnings 
        table
        "
	INDEX   { pm1004AlmlineXfp1WarningsIndex }
	::= { pm1004AlmlineXfp1WarningsTable 1 }


Pm1004AlmlineXfp1WarningsEntry ::=
	SEQUENCE {
	pm1004AlmlineXfp1WarningsIndex
		INTEGER,
	pm1004AlmRxPowerHighWarningPortn
		EkiOnOff,
	pm1004AlmRxPowerLowWarningPortn
		EkiOnOff,
	pm1004AlmTempHighWarningPortn
		EkiOnOff,
	pm1004AlmTempLowWarningPortn
		EkiOnOff,
	pm1004AlmTxBiasHighWarningPortn
		EkiOnOff,
	pm1004AlmTxBiasLowWarningPortn
		EkiOnOff,
	pm1004AlmTxPowerHighWarningPortn
		EkiOnOff,
	pm1004AlmTxPowerLowWarningPortn
		EkiOnOff
	}


pm1004AlmlineXfp1WarningsIndex OBJECT-TYPE
	SYNTAX  INTEGER(0..128)
	MAX-ACCESS  read-only
	STATUS current
	DESCRIPTION
        "
        Index definition for the pm1004AlmlineXfp1Warnings 
        table
        "
	::= { pm1004AlmlineXfp1WarningsEntry 1 }


pm1004AlmRxPowerHighWarningPortn OBJECT-TYPE
	SYNTAX  EkiOnOff
	MAX-ACCESS read-only
	STATUS current
	DESCRIPTION
        "
        Line Optical Rx Power High Warning 
        :Warning indicating that the XFP 
        received optical power is higher 
        than the threshold value written 
        in the XFP EEPROM <Condtype> RX_POWER_HIGH_WARNING_1 
        <Probcause> receiveFailure (41) 
        <Alarmtype> equipmentAlarm (5)
         <Polarity> (2) 
        "
	::= { pm1004AlmlineXfp1WarningsEntry 17 }


pm1004AlmRxPowerLowWarningPortn OBJECT-TYPE
	SYNTAX  EkiOnOff
	MAX-ACCESS read-only
	STATUS current
	DESCRIPTION
        "
        Line Optical Rx Power Low Warning 
        :Warning indicating that the XFP 
        received optical power is lower 
        than the threshold value written 
        in the XFP EEPROM  <Condtype> RX_POWER_LOW_WARNING_1 
        <Probcause> receiveFailure (41) 
        <Alarmtype> equipmentAlarm (5)
         <Polarity> (2) 
        "
	::= { pm1004AlmlineXfp1WarningsEntry 16 }


pm1004AlmTempHighWarningPortn OBJECT-TYPE
	SYNTAX  EkiOnOff
	MAX-ACCESS read-only
	STATUS current
	DESCRIPTION
        "
        Line Transceiver Temp High Warning 
        :Warning indicating that the XFP/OTX 
        temperature is higher than the
         threshold value written in the 
        XFP EEPROM <Condtype> TEMP_HIGH_WARNING_1 
        <Probcause> temperatureUnacceptable 
        (51) <Alarmtype> equipmentAlarm 
        (5) <Polarity> (2) 
        "
	::= { pm1004AlmlineXfp1WarningsEntry 9 }


pm1004AlmTempLowWarningPortn OBJECT-TYPE
	SYNTAX  EkiOnOff
	MAX-ACCESS read-only
	STATUS current
	DESCRIPTION
        "
        Line Transceiver Temp Low Warning 
        :Warning indicating that the XFP/OTX 
        temperature is lower than the threshold 
        value written in the XFP/OTX EEPROM 
        <Condtype> TEMP_LOW_WARNING_1 <Probcause> 
        temperatureUnacceptable (51) <Alarmtype> 
        equipmentAlarm (5) <Polarity> (2)
         
        "
	::= { pm1004AlmlineXfp1WarningsEntry 8 }


pm1004AlmTxBiasHighWarningPortn OBJECT-TYPE
	SYNTAX  EkiOnOff
	MAX-ACCESS read-only
	STATUS current
	DESCRIPTION
        "
        Line Transceiver Bias High Warning 
        :Warning indicating that the XFP/OTX 
        transmitter laser bias current
         is higher than the threshold value 
        written in the XFP EEPROM <Condtype> 
        TX_BIAS_HIGH_WARNING_1 <Probcause> 
        transmitterFailure (56) <Alarmtype> 
        equipmentAlarm (5) <Polarity> (2)
         
        "
	::= { pm1004AlmlineXfp1WarningsEntry 5 }


pm1004AlmTxBiasLowWarningPortn OBJECT-TYPE
	SYNTAX  EkiOnOff
	MAX-ACCESS read-only
	STATUS current
	DESCRIPTION
        "
        Line Transceiver Bias Low Warning 
        :Warning indicating that the XFP/OTX 
        transmitter laser bias current
         is lower than the threshold value 
        written in the XFP/OTX EEPROM <Condtype> 
        TX_BIAS_LOW_WARNING_1 <Probcause> 
        transmitterFailure (56) <Alarmtype> 
        equipmentAlarm (5) <Polarity> (2)
         
        "
	::= { pm1004AlmlineXfp1WarningsEntry 4 }


pm1004AlmTxPowerHighWarningPortn OBJECT-TYPE
	SYNTAX  EkiOnOff
	MAX-ACCESS read-only
	STATUS current
	DESCRIPTION
        "
        Line Optical Tx Power High Warning 
        :Warning indicating that the XFP/OTX 
        transmitter transmitter output
         power is higher than the threshold 
        value written in the XFP EEPROM 
        <Condtype> TX_POWER_HIGH_WARNING_1 
        <Probcause> transmitterFailure
         (56) <Alarmtype> equipmentAlarm 
        (5) <Polarity> (2) 
        "
	::= { pm1004AlmlineXfp1WarningsEntry 3 }


pm1004AlmTxPowerLowWarningPortn OBJECT-TYPE
	SYNTAX  EkiOnOff
	MAX-ACCESS read-only
	STATUS current
	DESCRIPTION
        "
        Line Optical Tx Power Low Warning 
        :Warning indicating that the XFP/OTX 
        transmitter transmitter output
         power is lower than the threshold 
        value written in the XFP/OTX EEPROM 
        <Condtype> TX_POWER_LOW_WARNING_1 
        <Probcause> transmitterFailure
         (56) <Alarmtype> equipmentAlarm 
        (5) <Polarity> (2) 
        "
	::= { pm1004AlmlineXfp1WarningsEntry 2 }


--- *********************************************************
---     TABLE for the pm1004AlmlineXfp1Alarms articles
--- *********************************************************

pm1004AlmlineXfp1AlarmsTable OBJECT-TYPE
	SYNTAX  SEQUENCE OF Pm1004AlmlineXfp1AlarmsEntry
	MAX-ACCESS not-accessible
	STATUS current
	DESCRIPTION
        "
        List of pm1004AlmlineXfp1Alarms 
        Article
        "
	::= { pm1004AlmLineCrit 211 }


pm1004AlmlineXfp1AlarmsEntry OBJECT-TYPE
	SYNTAX Pm1004AlmlineXfp1AlarmsEntry
	MAX-ACCESS not-accessible
	STATUS current
	DESCRIPTION
        "
        Row definition for the pm1004AlmlineXfp1Alarms 
        table
        "
	INDEX   { pm1004AlmlineXfp1AlarmsIndex }
	::= { pm1004AlmlineXfp1AlarmsTable 1 }


Pm1004AlmlineXfp1AlarmsEntry ::=
	SEQUENCE {
	pm1004AlmlineXfp1AlarmsIndex
		INTEGER,
	pm1004AlmApdSupplyFaultPortn
		EkiOnOff,
	pm1004AlmTecFaultPortn
		EkiOnOff,
	pm1004AlmWavelengthUnlockedPortn
		EkiOnOff,
	pm1004AlmChannelNotAcquiredPortn
		EkiOnOff,
	pm1004AlmTxNrPortn
		EkiOnOff,
	pm1004AlmTxFaultPortn
		EkiOnOff,
	pm1004AlmTxCdrNotLockedPortn
		EkiOnOff,
	pm1004AlmRxNrPortn
		EkiOnOff,
	pm1004AlmRxCdrNotLockedPortn
		EkiOnOff,
	pm1004AlmModNrPortn
		EkiOnOff
	}


pm1004AlmlineXfp1AlarmsIndex OBJECT-TYPE
	SYNTAX  INTEGER(0..128)
	MAX-ACCESS  read-only
	STATUS current
	DESCRIPTION
        "
        Index definition for the pm1004AlmlineXfp1Alarms 
        table
        "
	::= { pm1004AlmlineXfp1AlarmsEntry 1 }


pm1004AlmApdSupplyFaultPortn OBJECT-TYPE
	SYNTAX  EkiOnOff
	MAX-ACCESS read-only
	STATUS current
	DESCRIPTION
        "
        Line Rx Photodiode Power Failed 
        :This OID indicates a failure on 
        the APD power supply  <Help>  This 
        alarm indicates if the APD power 
        supply is in fail condition <Condtype> 
        APD_SUPPLY_FAULT_1 <Probcause>
         receiverFailure (42) <Alarmtype> 
        equipmentAlarm (5) <Polarity> (2)
         
        "
	::= { pm1004AlmlineXfp1AlarmsEntry 17 }


pm1004AlmTecFaultPortn OBJECT-TYPE
	SYNTAX  EkiOnOff
	MAX-ACCESS read-only
	STATUS current
	DESCRIPTION
        "
        Line Optical Tx Temp Regul Failed 
        :This OID indicates a failure on 
        the TEC module  <Help>  This alarm 
        indicates if the TEC of the line 
        transceiver is in fail condition 
        <Condtype> TEC_FAULT_1 <Probcause> 
        transmitterFailure (56) <Alarmtype> 
        equipmentAlarm (5) <Polarity> (2)
         
        "
	::= { pm1004AlmlineXfp1AlarmsEntry 16 }


pm1004AlmWavelengthUnlockedPortn OBJECT-TYPE
	SYNTAX  EkiOnOff
	MAX-ACCESS read-only
	STATUS current
	DESCRIPTION
        "
        Line Optical Tx Wavelength Unlocked 
        :This OID indicates that the wavelength 
        error is exceeding the manufacturer 
        tolerance  <Help>  This alarm indicates 
        if the wavelenght of the line transceiver 
        is locked <Condtype> WAVELENGTH_UNLOCKED_1 
        <Probcause> transmitterFailure
         (56) <Alarmtype> equipmentAlarm 
        (5) <Polarity> (2) 
        "
	::= { pm1004AlmlineXfp1AlarmsEntry 15 }


pm1004AlmChannelNotAcquiredPortn OBJECT-TYPE
	SYNTAX  EkiOnOff
	MAX-ACCESS read-only
	STATUS current
	DESCRIPTION
        "
        Line DWDM Channel Not Acquired 
        :This OID indicates the transceiver 
        didn't tune the DWDM Channel succesfully. 
         <Help>  This status indicates
         the transceiver has not tuned
         the DWDM Channel succesfully.
         <Condtype> CHANNEL_NOT_ACQUIRED_1 
        <Probcause> transmitterFailure
         (56) <Alarmtype> equipmentAlarm 
        (5) <Polarity> (2) 
        "
	::= { pm1004AlmlineXfp1AlarmsEntry 11 }


pm1004AlmTxNrPortn OBJECT-TYPE
	SYNTAX  EkiOnOff
	MAX-ACCESS read-only
	STATUS current
	DESCRIPTION
        "
        Line Optical Tx Not Ready :This 
        OID indicates a condition has arisen 
        leading to invalid data on the
         transmitting side  <Help>  This 
        alarm indicates if the Tx part
         of the line transceiver is ready 
        <Condtype> TX_NR_1 <Probcause>
         transmitterFailure (56) <Alarmtype> 
        equipmentAlarm (5) <Polarity> (2)
         
        "
	::= { pm1004AlmlineXfp1AlarmsEntry 9 }


pm1004AlmTxFaultPortn OBJECT-TYPE
	SYNTAX  EkiOnOff
	MAX-ACCESS read-only
	STATUS current
	DESCRIPTION
        "
        Line Optical Tx Failure :This
         OID indicates a fault condition 
        on the laser detected by the safety 
        syste  <Help>  This alarm indicates 
        if the laser of the line transceiver 
        is in fail condition <Condtype> 
        TX_FAULT_1 <Probcause> transmitterFailure 
        (56) <Alarmtype> equipmentAlarm 
        (5) <Polarity> (2) 
        "
	::= { pm1004AlmlineXfp1AlarmsEntry 8 }


pm1004AlmTxCdrNotLockedPortn OBJECT-TYPE
	SYNTAX  EkiOnOff
	MAX-ACCESS read-only
	STATUS current
	DESCRIPTION
        "
        Line Optical Tx CDR Unlocked :This 
        OID indicates a loss of lock on 
        the transmitting side CDR has been 
        detected.  <Help>  This alarm indicates 
        if the Tx CDR is locked in the
         line transceiver <Condtype> TX_CDR_NOT_LOCKED1_1 
        <Probcause> transmitterFailure
         (56) <Alarmtype> equipmentAlarm 
        (5) <Polarity> (2) 
        "
	::= { pm1004AlmlineXfp1AlarmsEntry 7 }


pm1004AlmRxNrPortn OBJECT-TYPE
	SYNTAX  EkiOnOff
	MAX-ACCESS read-only
	STATUS current
	DESCRIPTION
        "
        Line Optical Rx Not Ready :This 
        OID indicates that a condition
         has arisen leading to invalid
         data on the receiving side.  <Help> 
         This alarm indicates if the Rx 
        part of the line transceiver is 
        ready <Condtype> RX_NR_1 <Probcause> 
        receiveFailure (41) <Alarmtype> 
        equipmentAlarm (5) <Polarity> (2)
         
        "
	::= { pm1004AlmlineXfp1AlarmsEntry 6 }


pm1004AlmRxCdrNotLockedPortn OBJECT-TYPE
	SYNTAX  EkiOnOff
	MAX-ACCESS read-only
	STATUS current
	DESCRIPTION
        "
        Line Optical Rx CDR Unlocked :This 
        OID indicates that a loss of lock 
        on the receiving side CDR has been 
        detected  <Help>  This alarm indicates 
        if the Rx CDR is locked in the
         line transceiver <Condtype> RX_CDR_NOT_LOCKED1_1 
        <Probcause> receiveFailure (41) 
        <Alarmtype> equipmentAlarm (5)
         <Polarity> (2) 
        "
	::= { pm1004AlmlineXfp1AlarmsEntry 4 }


pm1004AlmModNrPortn OBJECT-TYPE
	SYNTAX  EkiOnOff
	MAX-ACCESS read-only
	STATUS current
	DESCRIPTION
        "
        Line Optical Module Not Ready
         :This OID indicates that the module 
        is unable to determine correct
         data.  <Help>  This alarm indicates 
        if the line transceiver is ready 
        <Condtype> MOD_NR_1 <Probcause> 
        receiveFailure (41) <Alarmtype> 
        equipmentAlarm (5) <Polarity> (2)
         
        "
	::= { pm1004AlmlineXfp1AlarmsEntry 3 }


--- *********************************************************
---     TABLE for the pm1004AlmlineXfp1SupplyAlarm articles
--- *********************************************************

pm1004AlmlineXfp1SupplyAlarmTable OBJECT-TYPE
	SYNTAX  SEQUENCE OF Pm1004AlmlineXfp1SupplyAlarmEntry
	MAX-ACCESS not-accessible
	STATUS current
	DESCRIPTION
        "
        List of pm1004AlmlineXfp1SupplyAlarm 
        Article
        "
	::= { pm1004AlmLineUrg 212 }


pm1004AlmlineXfp1SupplyAlarmEntry OBJECT-TYPE
	SYNTAX Pm1004AlmlineXfp1SupplyAlarmEntry
	MAX-ACCESS not-accessible
	STATUS current
	DESCRIPTION
        "
        Row definition for the pm1004AlmlineXfp1SupplyAlarm 
        table
        "
	INDEX   { pm1004AlmlineXfp1SupplyAlarmIndex }
	::= { pm1004AlmlineXfp1SupplyAlarmTable 1 }


Pm1004AlmlineXfp1SupplyAlarmEntry ::=
	SEQUENCE {
	pm1004AlmlineXfp1SupplyAlarmIndex
		INTEGER,
	pm1004AlmVcc5HighWarningPortn
		EkiOnOff,
	pm1004AlmVcc5LowWarningPortn
		EkiOnOff,
	pm1004AlmVcc3HighWarningPortn
		EkiOnOff,
	pm1004AlmVcc3LowWarningPortn
		EkiOnOff,
	pm1004AlmVcc2HighWarningPortn
		EkiOnOff,
	pm1004AlmVcc2LowWarningPortn
		EkiOnOff,
	pm1004AlmVee5HighWarningPortn
		EkiOnOff,
	pm1004AlmVee5LowWarningPortn
		EkiOnOff,
	pm1004AlmVcc5HighAlarmPortn
		EkiOnOff,
	pm1004AlmVcc5LowAlarmPortn
		EkiOnOff,
	pm1004AlmVcc3HighAlarmPortn
		EkiOnOff,
	pm1004AlmVcc3LowAlarmPortn
		EkiOnOff,
	pm1004AlmVcc2HighAlarmPortn
		EkiOnOff,
	pm1004AlmVcc2LowAlarmPortn
		EkiOnOff,
	pm1004AlmVee5HighAlarmPortn
		EkiOnOff,
	pm1004AlmVee5LowAlarmPortn
		EkiOnOff
	}


pm1004AlmlineXfp1SupplyAlarmIndex OBJECT-TYPE
	SYNTAX  INTEGER(0..128)
	MAX-ACCESS  read-only
	STATUS current
	DESCRIPTION
        "
        Index definition for the pm1004AlmlineXfp1SupplyAlarm 
        table
        "
	::= { pm1004AlmlineXfp1SupplyAlarmEntry 1 }


pm1004AlmVcc5HighWarningPortn OBJECT-TYPE
	SYNTAX  EkiOnOff
	MAX-ACCESS read-only
	STATUS current
	DESCRIPTION
        "
        VCC5 Power Supply High Warning 
        :Warning indicating the XFP/OTX 
        VCC5 power supply is higher than 
        the threshold written in the EEPROM 
        <Condtype> VCC5_HIGH_WARNING_1
         <Probcause> powerProblem (36)
         <Alarmtype> equipmentAlarm (5) 
        <Polarity> (2) 
        "
	::= { pm1004AlmlineXfp1SupplyAlarmEntry 17 }


pm1004AlmVcc5LowWarningPortn OBJECT-TYPE
	SYNTAX  EkiOnOff
	MAX-ACCESS read-only
	STATUS current
	DESCRIPTION
        "
        VCC5 Power Supply Low Warning
         :Warning indicating the XFP/OTX 
        VCC5 power supply is lower than 
        the threshold written in the EEPROM 
        <Condtype> VCC5_LOW_WARNING_1 <Probcause> 
        powerProblem (36) <Alarmtype> equipmentAlarm 
        (5) <Polarity> (2) 
        "
	::= { pm1004AlmlineXfp1SupplyAlarmEntry 16 }


pm1004AlmVcc3HighWarningPortn OBJECT-TYPE
	SYNTAX  EkiOnOff
	MAX-ACCESS read-only
	STATUS current
	DESCRIPTION
        "
        VCC3 Power Supply High Warning 
        :Warning indicating the XFP/OTX 
        VCC3 power supply is higher than 
        the threshold written in the EEPROM 
        <Condtype> VCC3_HIGH_WARNING_1
         <Probcause> powerProblem (36)
         <Alarmtype> equipmentAlarm (5) 
        <Polarity> (2) 
        "
	::= { pm1004AlmlineXfp1SupplyAlarmEntry 15 }


pm1004AlmVcc3LowWarningPortn OBJECT-TYPE
	SYNTAX  EkiOnOff
	MAX-ACCESS read-only
	STATUS current
	DESCRIPTION
        "
        VCC3 Power Supply Low Warning
         :Warning indicating the XFP/OTX 
        VCC3 power supply is lower than 
        the threshold written in the EEPROM 
        <Condtype> VCC3_LOW_WARNING_1 <Probcause> 
        powerProblem (36) <Alarmtype> equipmentAlarm 
        (5) <Polarity> (2) 
        "
	::= { pm1004AlmlineXfp1SupplyAlarmEntry 14 }


pm1004AlmVcc2HighWarningPortn OBJECT-TYPE
	SYNTAX  EkiOnOff
	MAX-ACCESS read-only
	STATUS current
	DESCRIPTION
        "
        VCC2 Power Supply High Warning 
        :Warning indicating the XFP/OTX 
        VCC2 power supply is higher than 
        the threshold written in the EEPROM 
        <Condtype> VCC2_HIGH_WARNING_1
         <Probcause> powerProblem (36)
         <Alarmtype> equipmentAlarm (5) 
        <Polarity> (2) 
        "
	::= { pm1004AlmlineXfp1SupplyAlarmEntry 13 }


pm1004AlmVcc2LowWarningPortn OBJECT-TYPE
	SYNTAX  EkiOnOff
	MAX-ACCESS read-only
	STATUS current
	DESCRIPTION
        "
        VCC2 Power Supply Low Warning
         :Warning indicating the XFP/OTX 
        VCC2 power supply is lower than 
        the threshold written in the EEPROM 
        <Condtype> VCC2_LOW_WARNING_1 <Probcause> 
        powerProblem (36) <Alarmtype> equipmentAlarm 
        (5) <Polarity> (2) 
        "
	::= { pm1004AlmlineXfp1SupplyAlarmEntry 12 }


pm1004AlmVee5HighWarningPortn OBJECT-TYPE
	SYNTAX  EkiOnOff
	MAX-ACCESS read-only
	STATUS current
	DESCRIPTION
        "
        VEE5 Power Supply High Warning 
        :Warning indicating the XFP/OTX 
        VEE5 power supply is higher than 
        the threshold written in the EEPROM 
        <Condtype> VEE5_HIGH_WARNING_1
         <Probcause> powerProblem (36)
         <Alarmtype> equipmentAlarm (5) 
        <Polarity> (2) 
        "
	::= { pm1004AlmlineXfp1SupplyAlarmEntry 11 }


pm1004AlmVee5LowWarningPortn OBJECT-TYPE
	SYNTAX  EkiOnOff
	MAX-ACCESS read-only
	STATUS current
	DESCRIPTION
        "
        VEE5 Power Supply Low Warning
         :Warning indicating the XFP/OTX 
        VEE5 power supply is lower than 
        the threshold written in the EEPROM 
        <Condtype> VEE5_LOW_WARNING_1 <Probcause> 
        powerProblem (36) <Alarmtype> equipmentAlarm 
        (5) <Polarity> (2) 
        "
	::= { pm1004AlmlineXfp1SupplyAlarmEntry 10 }


pm1004AlmVcc5HighAlarmPortn OBJECT-TYPE
	SYNTAX  EkiOnOff
	MAX-ACCESS read-only
	STATUS current
	DESCRIPTION
        "
        VCC5 Power Supply High :Alarm
         indicating the XFP/OTX VCC5 power 
        supply is higher than the threshold 
        written in the EEPROM <Condtype> 
        VCC5_HIGH_ALARM_1 <Probcause> powerProblem 
        (36) <Alarmtype> equipmentAlarm 
        (5) <Polarity> (2) 
        "
	::= { pm1004AlmlineXfp1SupplyAlarmEntry 9 }


pm1004AlmVcc5LowAlarmPortn OBJECT-TYPE
	SYNTAX  EkiOnOff
	MAX-ACCESS read-only
	STATUS current
	DESCRIPTION
        "
        VCC5 Power Supply Low :Alarm indicating 
        the XFP/OTX VCC5 power supply is 
        lower than the threshold written 
        in the EEPROM <Condtype> VCC5_LOW_ALARM_1 
        <Probcause> powerProblem (36) <Alarmtype> 
        equipmentAlarm (5) <Polarity> (2)
         
        "
	::= { pm1004AlmlineXfp1SupplyAlarmEntry 8 }


pm1004AlmVcc3HighAlarmPortn OBJECT-TYPE
	SYNTAX  EkiOnOff
	MAX-ACCESS read-only
	STATUS current
	DESCRIPTION
        "
        VCC3 Power Supply High :Alarm
         indicating the XFP/OTX VCC3 power 
        supply is higher than the threshold 
        written in the EEPROM <Condtype> 
        VCC3_HIGH_ALARM_1 <Probcause> powerProblem 
        (36) <Alarmtype> equipmentAlarm 
        (5) <Polarity> (2) 
        "
	::= { pm1004AlmlineXfp1SupplyAlarmEntry 7 }


pm1004AlmVcc3LowAlarmPortn OBJECT-TYPE
	SYNTAX  EkiOnOff
	MAX-ACCESS read-only
	STATUS current
	DESCRIPTION
        "
        VCC3 Power Supply Low :Alarm indicating 
        the XFP/OTX VCC3 power supply is 
        lower than the threshold written 
        in the EEPROM <Condtype> VCC3_LOW_ALARM_1 
        <Probcause> powerProblem (36) <Alarmtype> 
        equipmentAlarm (5) <Polarity> (2)
         
        "
	::= { pm1004AlmlineXfp1SupplyAlarmEntry 6 }


pm1004AlmVcc2HighAlarmPortn OBJECT-TYPE
	SYNTAX  EkiOnOff
	MAX-ACCESS read-only
	STATUS current
	DESCRIPTION
        "
        VCC2 Power Supply High :Alarm
         indicating the XFP/OTX VCC2 power 
        supply is higher than the threshold 
        written in the EEPROM <Condtype> 
        VCC2_HIGH_ALARM_1 <Probcause> powerProblem 
        (36) <Alarmtype> equipmentAlarm 
        (5) <Polarity> (2) 
        "
	::= { pm1004AlmlineXfp1SupplyAlarmEntry 5 }


pm1004AlmVcc2LowAlarmPortn OBJECT-TYPE
	SYNTAX  EkiOnOff
	MAX-ACCESS read-only
	STATUS current
	DESCRIPTION
        "
        VCC2 Power Supply Low :Alarm indicating 
        the XFP/OTX VCC2 power supply is 
        lower than the threshold written 
        in the EEPROM <Condtype> VCC2_LOW_ALARM_1 
        <Probcause> powerProblem (36) <Alarmtype> 
        equipmentAlarm (5) <Polarity> (2)
         
        "
	::= { pm1004AlmlineXfp1SupplyAlarmEntry 4 }


pm1004AlmVee5HighAlarmPortn OBJECT-TYPE
	SYNTAX  EkiOnOff
	MAX-ACCESS read-only
	STATUS current
	DESCRIPTION
        "
        VEE5 Power Supply High :Alarm
         indicating the XFP/OTX VEE5 power 
        supply is higher than the threshold 
        written in the EEPROM <Condtype> 
        VEE5_HIGH_ALARM_1 <Probcause> powerProblem 
        (36) <Alarmtype> equipmentAlarm 
        (5) <Polarity> (2) 
        "
	::= { pm1004AlmlineXfp1SupplyAlarmEntry 3 }


pm1004AlmVee5LowAlarmPortn OBJECT-TYPE
	SYNTAX  EkiOnOff
	MAX-ACCESS read-only
	STATUS current
	DESCRIPTION
        "
        VEE5 Power Supply Low :Alarm indicating 
        the XFP/OTX VEE5 power supply is 
        lower than the threshold written 
        in the EEPROM <Condtype> VEE5_LOW_ALARM_1 
        <Probcause> powerProblem (36) <Alarmtype> 
        equipmentAlarm (5) <Polarity> (2)
         
        "
	::= { pm1004AlmlineXfp1SupplyAlarmEntry 2 }


--- *********************************************************
---     TABLE for the pm1004AlmlineOtx1TlhAlarms articles
--- *********************************************************

pm1004AlmlineOtx1TlhAlarmsTable OBJECT-TYPE
	SYNTAX  SEQUENCE OF Pm1004AlmlineOtx1TlhAlarmsEntry
	MAX-ACCESS not-accessible
	STATUS current
	DESCRIPTION
        "
        List of pm1004AlmlineOtx1TlhAlarms 
        Article
        "
	::= { pm1004AlmLineUrg 224 }


pm1004AlmlineOtx1TlhAlarmsEntry OBJECT-TYPE
	SYNTAX Pm1004AlmlineOtx1TlhAlarmsEntry
	MAX-ACCESS not-accessible
	STATUS current
	DESCRIPTION
        "
        Row definition for the pm1004AlmlineOtx1TlhAlarms 
        table
        "
	INDEX   { pm1004AlmlineOtx1TlhAlarmsIndex }
	::= { pm1004AlmlineOtx1TlhAlarmsTable 1 }


Pm1004AlmlineOtx1TlhAlarmsEntry ::=
	SEQUENCE {
	pm1004AlmlineOtx1TlhAlarmsIndex
		INTEGER,
	pm1004AlmLineLaserTempHighAlaPortn
		EkiOnOff,
	pm1004AlmLineFreqDevHighAlaPortn
		EkiOnOff,
	pm1004AlmLineCdrNotReadyPortn
		EkiOnOff,
	pm1004AlmLineAgingHighAlaPortn
		EkiOnOff,
	pm1004AlmLineModulatorAgingHighAlaPortn
		EkiOnOff
	}


pm1004AlmlineOtx1TlhAlarmsIndex OBJECT-TYPE
	SYNTAX  INTEGER(0..128)
	MAX-ACCESS  read-only
	STATUS current
	DESCRIPTION
        "
        Index definition for the pm1004AlmlineOtx1TlhAlarms 
        table
        "
	::= { pm1004AlmlineOtx1TlhAlarmsEntry 1 }


pm1004AlmLineLaserTempHighAlaPortn OBJECT-TYPE
	SYNTAX  EkiOnOff
	MAX-ACCESS read-only
	STATUS current
	DESCRIPTION
        "
        Line Laser Temp. High Alarm :Alarm 
        indicating the Line OTX TLH laser 
        temperature is higher than the
         threshold written in the EEPROM 
        <Condtype> LINE_LASER_TEMP_HIGH_ALA_1 
        <Probcause> temperatureUnacceptable 
        (51) <Alarmtype> equipmentAlarm 
        (5) <Polarity> (2) 
        "
	::= { pm1004AlmlineOtx1TlhAlarmsEntry 15 }


pm1004AlmLineFreqDevHighAlaPortn OBJECT-TYPE
	SYNTAX  EkiOnOff
	MAX-ACCESS read-only
	STATUS current
	DESCRIPTION
        "
        Line Freq. Deviation High Alarm 
        :Alarm indicating the Line OTX
         TLH frequency deviation is higher 
        than the threshold written in the 
        EEPROM <Condtype> LINE_FREQ_DEV_HIGH_ALA_1 
        <Probcause> transmitterFailure
         (56) <Alarmtype> equipmentAlarm 
        (5) <Polarity> (2) 
        "
	::= { pm1004AlmlineOtx1TlhAlarmsEntry 13 }


pm1004AlmLineCdrNotReadyPortn OBJECT-TYPE
	SYNTAX  EkiOnOff
	MAX-ACCESS read-only
	STATUS current
	DESCRIPTION
        "
        CDR Not Ready :This OID indicates 
        the Clock Data Recovery unit is 
        not yet initialized.   <Help> 
         This alarm indicates the Clock 
        Data Recovery unit is not yet initialized. 
        <Condtype> LINE_CDR_NOT_READY_1 
        <Probcause> receiveFailure (41) 
        <Alarmtype> equipmentAlarm (5)
         <Polarity> (2) 
        "
	::= { pm1004AlmlineOtx1TlhAlarmsEntry 10 }


pm1004AlmLineAgingHighAlaPortn OBJECT-TYPE
	SYNTAX  EkiOnOff
	MAX-ACCESS read-only
	STATUS current
	DESCRIPTION
        "
        Line OTX TLH Aging High Alarm
         :Alarm indicating the Line OTX 
        TLH aging is higher than the threshold 
        written in the EEPROM <Condtype> 
        LINE_AGING_HIGH_ALA_1 <Probcause> 
        transmitterFailure (56) <Alarmtype> 
        equipmentAlarm (5) <Polarity> (2)
         
        "
	::= { pm1004AlmlineOtx1TlhAlarmsEntry 7 }


pm1004AlmLineModulatorAgingHighAlaPortn OBJECT-TYPE
	SYNTAX  EkiOnOff
	MAX-ACCESS read-only
	STATUS current
	DESCRIPTION
        "
        Line Modulator Aging High Alarm 
        :Alarm indicating the Line OTX
         TLH modulator aging is higher
         than the threshold written in
         the EEPROM <Condtype> LINE_MODULATOR_AGING_HIGH_ALA_1 
        <Probcause> transmitterFailure
         (56) <Alarmtype> equipmentAlarm 
        (5) <Polarity> (2) 
        "
	::= { pm1004AlmlineOtx1TlhAlarmsEntry 6 }


--- *********************************************************
---     TABLE for the pm1004AlmlineOtx1TlhWarnings articles
--- *********************************************************

pm1004AlmlineOtx1TlhWarningsTable OBJECT-TYPE
	SYNTAX  SEQUENCE OF Pm1004AlmlineOtx1TlhWarningsEntry
	MAX-ACCESS not-accessible
	STATUS current
	DESCRIPTION
        "
        List of pm1004AlmlineOtx1TlhWarnings 
        Article
        "
	::= { pm1004AlmLineNurg 225 }


pm1004AlmlineOtx1TlhWarningsEntry OBJECT-TYPE
	SYNTAX Pm1004AlmlineOtx1TlhWarningsEntry
	MAX-ACCESS not-accessible
	STATUS current
	DESCRIPTION
        "
        Row definition for the pm1004AlmlineOtx1TlhWarnings 
        table
        "
	INDEX   { pm1004AlmlineOtx1TlhWarningsIndex }
	::= { pm1004AlmlineOtx1TlhWarningsTable 1 }


Pm1004AlmlineOtx1TlhWarningsEntry ::=
	SEQUENCE {
	pm1004AlmlineOtx1TlhWarningsIndex
		INTEGER,
	pm1004AlmLineLaserTempHighWarningPortn
		EkiOnOff,
	pm1004AlmLineFreqDevHighWarningPortn
		EkiOnOff,
	pm1004AlmLineAgingHighWarningPortn
		EkiOnOff,
	pm1004AlmLineModulatorAgingHighWarningPortn
		EkiOnOff
	}


pm1004AlmlineOtx1TlhWarningsIndex OBJECT-TYPE
	SYNTAX  INTEGER(0..128)
	MAX-ACCESS  read-only
	STATUS current
	DESCRIPTION
        "
        Index definition for the pm1004AlmlineOtx1TlhWarnings 
        table
        "
	::= { pm1004AlmlineOtx1TlhWarningsEntry 1 }


pm1004AlmLineLaserTempHighWarningPortn OBJECT-TYPE
	SYNTAX  EkiOnOff
	MAX-ACCESS read-only
	STATUS current
	DESCRIPTION
        "
        Line Laser Temp. High Warning
         :Warning indicating the Line OTX 
        TLH laser temperature is higher 
        than the threshold written in the 
        EEPROM <Condtype> LINE_LASER_TEMP_HIGH_WARNING_1 
        <Probcause> temperatureUnacceptable 
        (51) <Alarmtype> equipmentAlarm 
        (5) <Polarity> (2) 
        "
	::= { pm1004AlmlineOtx1TlhWarningsEntry 15 }


pm1004AlmLineFreqDevHighWarningPortn OBJECT-TYPE
	SYNTAX  EkiOnOff
	MAX-ACCESS read-only
	STATUS current
	DESCRIPTION
        "
        Line Freq. Deviation High Warning 
        :Warning indicating the Line OTX 
        TLH frequency deviation is higher 
        than the threshold written in the 
        EEPROM <Condtype> LINE_FREQ_DEV_HIGH_WARNING_1 
        <Probcause> transmitterFailure
         (56) <Alarmtype> equipmentAlarm 
        (5) <Polarity> (2) 
        "
	::= { pm1004AlmlineOtx1TlhWarningsEntry 13 }


pm1004AlmLineAgingHighWarningPortn OBJECT-TYPE
	SYNTAX  EkiOnOff
	MAX-ACCESS read-only
	STATUS current
	DESCRIPTION
        "
        Line OTX TLH Aging High Warning 
        :Warning indicating the Line OTX 
        TLH aging is higher than the threshold 
        written in the EEPROM <Condtype> 
        LINE_AGING_HIGH_WARNING_1 <Probcause> 
        transmitterFailure (56) <Alarmtype> 
        equipmentAlarm (5) <Polarity> (2)
         
        "
	::= { pm1004AlmlineOtx1TlhWarningsEntry 7 }


pm1004AlmLineModulatorAgingHighWarningPortn OBJECT-TYPE
	SYNTAX  EkiOnOff
	MAX-ACCESS read-only
	STATUS current
	DESCRIPTION
        "
        Line Modulator Aging High Warning 
        :Warning indicating the Line OTX 
        TLH modulator aging is higher than 
        the threshold written in the EEPROM 
        <Condtype> LINE_MODULATOR_AGING_HIGH_WARNING_1 
        <Probcause> transmitterFailure
         (56) <Alarmtype> equipmentAlarm 
        (5) <Polarity> (2) 
        "
	::= { pm1004AlmlineOtx1TlhWarningsEntry 6 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm1004CtrlconfMgnt1 OBJECT IDENTIFIER ::= { pm1004CtrlOther 1 }




pm1004CtrlConf2Clear1 OBJECT-TYPE
	  SYNTAX EkiOnOff
	  MAX-ACCESS read-write
	  STATUS current
	  DESCRIPTION
        "
        Clear Configuration Tables :This 
        OID clears the configuration tables 
        from configuration2 in the flash. 
         <Help>  This control restores
         the default configuration of the 
        module
        "
	  ::= { pm1004CtrlconfMgnt1 14 }



pm1004CtrlConf2Flash1 OBJECT-TYPE
	  SYNTAX EkiOnOff
	  MAX-ACCESS read-write
	  STATUS current
	  DESCRIPTION
        "
        Write Configuration Tables :This 
        OID saves the current configuration 
        of the PM as configuration2 in
         the flash.  <Help>  This control 
        saves the customer configuration 
        on the module
        "
	  ::= { pm1004CtrlconfMgnt1 10 }



pm1004CtrlConf2Load1 OBJECT-TYPE
	  SYNTAX EkiOnOff
	  MAX-ACCESS read-write
	  STATUS current
	  DESCRIPTION
        "
        Load Configuration Tables Set
         Nb 2 :When set this OID enables 
        loading from flash configuration2 
        into the PM.
        "
	  ::= { pm1004CtrlconfMgnt1 2 }



pm1004CtrlConf1Load1 OBJECT-TYPE
	  SYNTAX EkiOnOff
	  MAX-ACCESS read-write
	  STATUS current
	  DESCRIPTION
        "
        Load Configuration Tables Set
         Nb 1 :When set this OID enables 
        loading from flash configuration1 
        into the PM.
        "
	  ::= { pm1004CtrlconfMgnt1 1 }



--- *****************************************************
---     LEAF for the synth4 article
--- *****************************************************
pm1004Ctrlsynth4 OBJECT IDENTIFIER ::= { pm1004CtrlOther 4 }




pm1004CtrlCorrelatOff OBJECT-TYPE
	  SYNTAX EkiOnOff
	  MAX-ACCESS read-write
	  STATUS current
	  DESCRIPTION
        "
        Disable Alarm Correlation :This 
        OID disables the alarm correlation 
        in the PM.
        "
	  ::= { pm1004Ctrlsynth4 2 }



pm1004CtrlCorrelatOn OBJECT-TYPE
	  SYNTAX EkiOnOff
	  MAX-ACCESS read-write
	  STATUS current
	  DESCRIPTION
        "
        Enable Alarm Correlation :This 
        OID enables the alarm correlation 
        in the PM.
        "
	  ::= { pm1004Ctrlsynth4 1 }



--- *****************************************************
---     LEAF for the swMgnt article
--- *****************************************************
pm1004CtrlswMgnt OBJECT IDENTIFIER ::= { pm1004CtrlOther 5 }




pm1004CtrlLoadSwBank2 OBJECT-TYPE
	  SYNTAX EkiOnOff
	  MAX-ACCESS read-write
	  STATUS current
	  DESCRIPTION
        "
        Set Software Nb 2 As Active :This 
        OID, when set, loads the SW from 
        bank2 into the PM. It must be followed 
        by a reset.  <Help>  This controls 
        selects the second SW bank as the 
        active bank for the next module 
        reset
        "
	  ::= { pm1004CtrlswMgnt 6 }



pm1004CtrlLoadSwBank1 OBJECT-TYPE
	  SYNTAX EkiOnOff
	  MAX-ACCESS read-write
	  STATUS current
	  DESCRIPTION
        "
        Set Software Nb 1 As Active :This 
        OID, when set, loads the SW from 
        bank1 into the PM. It must be followed 
        by a reset.  <Help>  This controls 
        selects the first SW bank as the 
        active bank for the next module 
        reset
        "
	  ::= { pm1004CtrlswMgnt 5 }



pm1004CtrlWarmReset OBJECT-TYPE
	  SYNTAX EkiOnOff
	  MAX-ACCESS read-write
	  STATUS current
	  DESCRIPTION
        "
        PM Warm Reset :This OID, when
         set, causes a warm reset of the 
        PM. This reset is not traffic affecting, 
        and the configuration of PM remains 
        unchanged.  <Help>  This control 
        initiates a warm reset of the module.
         
        "
	  ::= { pm1004CtrlswMgnt 3 }



pm1004CtrlColdReset OBJECT-TYPE
	  SYNTAX EkiOnOff
	  MAX-ACCESS read-write
	  STATUS current
	  DESCRIPTION
        "
        PM Cold Reset :This OID, when
         set, causes a cold reset of the 
        PM. This reset is traffic affecting, 
        and the configuration of PM is
         reloaded on start-up.  <Help>
          This control initiates a cold 
        reset of the module. 
        "
	  ::= { pm1004CtrlswMgnt 2 }



--- *****************************************************
---     LEAF for the gwMgnt article
--- *****************************************************
pm1004CtrlgwMgnt OBJECT IDENTIFIER ::= { pm1004CtrlOther 6 }




pm1004CtrlLoadGwBank4 OBJECT-TYPE
	  SYNTAX EkiOnOff
	  MAX-ACCESS read-write
	  STATUS current
	  DESCRIPTION
        "
        Set Gateware Nb 4 As Active :This 
        OID, when set, loads the GW from 
        bank4 (Flash) into the PM. It is 
        followed by an automatic gateware 
        cold reset.
        "
	  ::= { pm1004CtrlgwMgnt 8 }



pm1004CtrlLoadGwBank3 OBJECT-TYPE
	  SYNTAX EkiOnOff
	  MAX-ACCESS read-write
	  STATUS current
	  DESCRIPTION
        "
        Set Gateware Nb 3 As Active :This 
        OID, when set, loads the GW from 
        bank3 (Flash) into the PM. It is 
        followed by an automatic gateware 
        cold reset.  <Help>  This controls 
        initiates a cold reset of the module 
        and select the third GW bank as 
        the active bank
        "
	  ::= { pm1004CtrlgwMgnt 7 }



pm1004CtrlLoadGwBank2 OBJECT-TYPE
	  SYNTAX EkiOnOff
	  MAX-ACCESS read-write
	  STATUS current
	  DESCRIPTION
        "
        Set Gateware Nb 2 As Active :This 
        OID, when set, loads the GW from 
        bank2 (Flash) into the PM. It is 
        followed by an automatic gateware 
        cold reset.
        "
	  ::= { pm1004CtrlgwMgnt 6 }



pm1004CtrlLoadGwBank1 OBJECT-TYPE
	  SYNTAX EkiOnOff
	  MAX-ACCESS read-write
	  STATUS current
	  DESCRIPTION
        "
        Set Gateware Nb 1 As Active :This 
        OID, when set, loads the GW from 
        bank1 (Flash) into the PM. It is 
        followed by an automatic gateware 
        cold reset.  <Help>  This controls 
        initiates a cold reset of the module 
        and select the first GW bank as 
        the active bank
        "
	  ::= { pm1004CtrlgwMgnt 5 }



pm1004CtrlCurrentGwReset OBJECT-TYPE
	  SYNTAX EkiOnOff
	  MAX-ACCESS read-write
	  STATUS current
	  DESCRIPTION
        "
        Active Gateware Reset :This OID, 
        when set, resets the active gateware. 
        It is traffic affecting.
        "
	  ::= { pm1004CtrlgwMgnt 1 }



--- *********************************************************
---     TABLE for the pm1004CtrlaccessLoop articles
--- *********************************************************

pm1004CtrlaccessLoopTable OBJECT-TYPE
	SYNTAX  SEQUENCE OF Pm1004CtrlaccessLoopEntry
	MAX-ACCESS not-accessible
	STATUS current
	DESCRIPTION
        "
        List of pm1004CtrlaccessLoop Articl
        e
        "
	::= { pm1004CtrlClient 16 }


pm1004CtrlaccessLoopEntry OBJECT-TYPE
	SYNTAX Pm1004CtrlaccessLoopEntry
	MAX-ACCESS not-accessible
	STATUS current
	DESCRIPTION
        "
        Row definition for the pm1004CtrlaccessLoop 
        table
        "
	INDEX   { pm1004CtrlaccessLoopIndex }
	::= { pm1004CtrlaccessLoopTable 1 }


Pm1004CtrlaccessLoopEntry ::=
	SEQUENCE {
	pm1004CtrlaccessLoopIndex
		INTEGER,
	pm1004CtrlaccessLoopPortn
		EkiState
	}


pm1004CtrlaccessLoopIndex OBJECT-TYPE
	SYNTAX  INTEGER(0..128)
	MAX-ACCESS  read-only
	STATUS current
	DESCRIPTION
        "
        Index definition for the pm1004CtrlaccessLoop 
        table
        "
	::= { pm1004CtrlaccessLoopEntry 1 }


pm1004CtrlaccessLoopPortn OBJECT-TYPE
	SYNTAX  EkiState
	MAX-ACCESS read-write
	STATUS current
	DESCRIPTION
        "
        Client Facility Loopback :This 
        OID operates a Client Facility
         Loopback, looping client input 
        signal on the client output port. 
        The loop is located on the client 
        transceiver  <Help> This maintenance 
        parameter operates a Client Facility 
        Loopback, looping client input
         signal on the client output port. 
        The loop is located on the client 
        transceiver
        "
	::= { pm1004CtrlaccessLoopEntry 2 }


--- *********************************************************
---     TABLE for the pm1004CtrlportOosMode articles
--- *********************************************************

pm1004CtrlportOosModeTable OBJECT-TYPE
	SYNTAX  SEQUENCE OF Pm1004CtrlportOosModeEntry
	MAX-ACCESS not-accessible
	STATUS current
	DESCRIPTION
        "
        List of pm1004CtrlportOosMode
         Article
        "
	::= { pm1004CtrlClient 18 }


pm1004CtrlportOosModeEntry OBJECT-TYPE
	SYNTAX Pm1004CtrlportOosModeEntry
	MAX-ACCESS not-accessible
	STATUS current
	DESCRIPTION
        "
        Row definition for the pm1004CtrlportOosMode 
        table
        "
	INDEX   { pm1004CtrlportOosModeIndex }
	::= { pm1004CtrlportOosModeTable 1 }


Pm1004CtrlportOosModeEntry ::=
	SEQUENCE {
	pm1004CtrlportOosModeIndex
		INTEGER,
	pm1004CtrlportOosModePortn
		EkiState
	}


pm1004CtrlportOosModeIndex OBJECT-TYPE
	SYNTAX  INTEGER(0..128)
	MAX-ACCESS  read-only
	STATUS current
	DESCRIPTION
        "
        Index definition for the pm1004CtrlportOosMode 
        table
        "
	::= { pm1004CtrlportOosModeEntry 1 }


pm1004CtrlportOosModePortn OBJECT-TYPE
	SYNTAX  EkiState
	MAX-ACCESS read-write
	STATUS current
	DESCRIPTION
        "
        Client Port Out Of Service :This 
        OID sets the client port Out Of 
        Service  <Help>  This controls
         defines the service state of the 
        client port
        "
	::= { pm1004CtrlportOosModeEntry 2 }


--- *********************************************************
---     TABLE for the pm1004CtrlsfpOnCtrl articles
--- *********************************************************

pm1004CtrlsfpOnCtrlTable OBJECT-TYPE
	SYNTAX  SEQUENCE OF Pm1004CtrlsfpOnCtrlEntry
	MAX-ACCESS not-accessible
	STATUS current
	DESCRIPTION
        "
        List of pm1004CtrlsfpOnCtrl Articl
        e
        "
	::= { pm1004CtrlClient 19 }


pm1004CtrlsfpOnCtrlEntry OBJECT-TYPE
	SYNTAX Pm1004CtrlsfpOnCtrlEntry
	MAX-ACCESS not-accessible
	STATUS current
	DESCRIPTION
        "
        Row definition for the pm1004CtrlsfpOnCtrl 
        table
        "
	INDEX   { pm1004CtrlsfpOnCtrlIndex }
	::= { pm1004CtrlsfpOnCtrlTable 1 }


Pm1004CtrlsfpOnCtrlEntry ::=
	SEQUENCE {
	pm1004CtrlsfpOnCtrlIndex
		INTEGER,
	pm1004CtrlsfpOnCtrlPortn
		EkiState
	}


pm1004CtrlsfpOnCtrlIndex OBJECT-TYPE
	SYNTAX  INTEGER(0..128)
	MAX-ACCESS  read-only
	STATUS current
	DESCRIPTION
        "
        Index definition for the pm1004CtrlsfpOnCtrl 
        table
        "
	::= { pm1004CtrlsfpOnCtrlEntry 1 }


pm1004CtrlsfpOnCtrlPortn OBJECT-TYPE
	SYNTAX  EkiState
	MAX-ACCESS read-write
	STATUS current
	DESCRIPTION
        "
        Client SFP Optical Laser ON :This 
        OID switches on the SFP.
        "
	::= { pm1004CtrlsfpOnCtrlEntry 2 }


--- *********************************************************
---     TABLE for the pm1004CtrlsfpOffCtrl articles
--- *********************************************************

pm1004CtrlsfpOffCtrlTable OBJECT-TYPE
	SYNTAX  SEQUENCE OF Pm1004CtrlsfpOffCtrlEntry
	MAX-ACCESS not-accessible
	STATUS current
	DESCRIPTION
        "
        List of pm1004CtrlsfpOffCtrl Articl
        e
        "
	::= { pm1004CtrlClient 20 }


pm1004CtrlsfpOffCtrlEntry OBJECT-TYPE
	SYNTAX Pm1004CtrlsfpOffCtrlEntry
	MAX-ACCESS not-accessible
	STATUS current
	DESCRIPTION
        "
        Row definition for the pm1004CtrlsfpOffCtrl 
        table
        "
	INDEX   { pm1004CtrlsfpOffCtrlIndex }
	::= { pm1004CtrlsfpOffCtrlTable 1 }


Pm1004CtrlsfpOffCtrlEntry ::=
	SEQUENCE {
	pm1004CtrlsfpOffCtrlIndex
		INTEGER,
	pm1004CtrlsfpOffCtrlPortn
		EkiState
	}


pm1004CtrlsfpOffCtrlIndex OBJECT-TYPE
	SYNTAX  INTEGER(0..128)
	MAX-ACCESS  read-only
	STATUS current
	DESCRIPTION
        "
        Index definition for the pm1004CtrlsfpOffCtrl 
        table
        "
	::= { pm1004CtrlsfpOffCtrlEntry 1 }


pm1004CtrlsfpOffCtrlPortn OBJECT-TYPE
	SYNTAX  EkiState
	MAX-ACCESS read-write
	STATUS current
	DESCRIPTION
        "
        Client SFP Laser Shutdown :This 
        OID switches off the SFP.  <Help> 
         This control defines the laser 
        state of the client transceive
        r
        "
	::= { pm1004CtrlsfpOffCtrlEntry 2 }


--- *********************************************************
---     TABLE for the pm1004CtrlcsfUpIns articles
--- *********************************************************

pm1004CtrlcsfUpInsTable OBJECT-TYPE
	SYNTAX  SEQUENCE OF Pm1004CtrlcsfUpInsEntry
	MAX-ACCESS not-accessible
	STATUS current
	DESCRIPTION
        "
        List of pm1004CtrlcsfUpIns Articl
        e
        "
	::= { pm1004CtrlClient 21 }


pm1004CtrlcsfUpInsEntry OBJECT-TYPE
	SYNTAX Pm1004CtrlcsfUpInsEntry
	MAX-ACCESS not-accessible
	STATUS current
	DESCRIPTION
        "
        Row definition for the pm1004CtrlcsfUpIns 
        table
        "
	INDEX   { pm1004CtrlcsfUpInsIndex }
	::= { pm1004CtrlcsfUpInsTable 1 }


Pm1004CtrlcsfUpInsEntry ::=
	SEQUENCE {
	pm1004CtrlcsfUpInsIndex
		INTEGER,
	pm1004CtrlcsfUpInsPortn
		EkiState
	}


pm1004CtrlcsfUpInsIndex OBJECT-TYPE
	SYNTAX  INTEGER(0..128)
	MAX-ACCESS  read-only
	STATUS current
	DESCRIPTION
        "
        Index definition for the pm1004CtrlcsfUpIns 
        table
        "
	::= { pm1004CtrlcsfUpInsEntry 1 }


pm1004CtrlcsfUpInsPortn OBJECT-TYPE
	SYNTAX  EkiState
	MAX-ACCESS read-write
	STATUS current
	DESCRIPTION
        "
        Client Signal Fail Insertion :This 
        OID, when set, inserts  a client 
        signal fail in the upstream client 
        Port.  <Help>  This control inserts 
        a Client Signal Fail for the client 
        port
        "
	::= { pm1004CtrlcsfUpInsEntry 2 }


--- *********************************************************
---     TABLE for the pm1004CtrlcaisDwIns articles
--- *********************************************************

pm1004CtrlcaisDwInsTable OBJECT-TYPE
	SYNTAX  SEQUENCE OF Pm1004CtrlcaisDwInsEntry
	MAX-ACCESS not-accessible
	STATUS current
	DESCRIPTION
        "
        List of pm1004CtrlcaisDwIns Articl
        e
        "
	::= { pm1004CtrlClient 22 }


pm1004CtrlcaisDwInsEntry OBJECT-TYPE
	SYNTAX Pm1004CtrlcaisDwInsEntry
	MAX-ACCESS not-accessible
	STATUS current
	DESCRIPTION
        "
        Row definition for the pm1004CtrlcaisDwIns 
        table
        "
	INDEX   { pm1004CtrlcaisDwInsIndex }
	::= { pm1004CtrlcaisDwInsTable 1 }


Pm1004CtrlcaisDwInsEntry ::=
	SEQUENCE {
	pm1004CtrlcaisDwInsIndex
		INTEGER,
	pm1004CtrlcaisDwInsPortn
		EkiState
	}


pm1004CtrlcaisDwInsIndex OBJECT-TYPE
	SYNTAX  INTEGER(0..128)
	MAX-ACCESS  read-only
	STATUS current
	DESCRIPTION
        "
        Index definition for the pm1004CtrlcaisDwIns 
        table
        "
	::= { pm1004CtrlcaisDwInsEntry 1 }


pm1004CtrlcaisDwInsPortn OBJECT-TYPE
	SYNTAX  EkiState
	MAX-ACCESS read-write
	STATUS current
	DESCRIPTION
        "
        Client AIS Insertion :This OID, 
        when set, inserts a client AIS
         on the downstream client Port. 
         <Help>  This control inserts a 
        Client AIS for the client port
        "
	::= { pm1004CtrlcaisDwInsEntry 2 }


--- *********************************************************
---     TABLE for the pm1004CtrlclientAccessTermLoop articles
--- *********************************************************

pm1004CtrlclientAccessTermLoopTable OBJECT-TYPE
	SYNTAX  SEQUENCE OF Pm1004CtrlclientAccessTermLoopEntry
	MAX-ACCESS not-accessible
	STATUS current
	DESCRIPTION
        "
        List of pm1004CtrlclientAccessTermLoop 
        Article
        "
	::= { pm1004CtrlClient 26 }


pm1004CtrlclientAccessTermLoopEntry OBJECT-TYPE
	SYNTAX Pm1004CtrlclientAccessTermLoopEntry
	MAX-ACCESS not-accessible
	STATUS current
	DESCRIPTION
        "
        Row definition for the pm1004CtrlclientAccessTermLoop 
        table
        "
	INDEX   { pm1004CtrlclientAccessTermLoopIndex }
	::= { pm1004CtrlclientAccessTermLoopTable 1 }


Pm1004CtrlclientAccessTermLoopEntry ::=
	SEQUENCE {
	pm1004CtrlclientAccessTermLoopIndex
		INTEGER,
	pm1004CtrlclientAccessTermLoopPortn
		EkiState
	}


pm1004CtrlclientAccessTermLoopIndex OBJECT-TYPE
	SYNTAX  INTEGER(0..128)
	MAX-ACCESS  read-only
	STATUS current
	DESCRIPTION
        "
        Index definition for the pm1004CtrlclientAccessTermLoop 
        table
        "
	::= { pm1004CtrlclientAccessTermLoopEntry 1 }


pm1004CtrlclientAccessTermLoopPortn OBJECT-TYPE
	SYNTAX  EkiState
	MAX-ACCESS read-write
	STATUS current
	DESCRIPTION
        "
        Client Terminal Loopback :This 
        OID operates a Client Terminal
         Loopback, looping client input 
        signal on the client output port. 
        The loop is located on the line 
        transceiver  <Help> This maintenance 
        parameter operates a Client Terminal 
        Loopback, looping client input
         signal on the client output port. 
        The loop is located on the line 
        transceiver
        "
	::= { pm1004CtrlclientAccessTermLoopEntry 2 }


--- *********************************************************
---     TABLE for the pm1004CtrlresetCount15Port articles
--- *********************************************************

pm1004CtrlresetCount15PortTable OBJECT-TYPE
	SYNTAX  SEQUENCE OF Pm1004CtrlresetCount15PortEntry
	MAX-ACCESS not-accessible
	STATUS current
	DESCRIPTION
        "
        List of pm1004CtrlresetCount15Port 
        Article
        "
	::= { pm1004CtrlClient 35 }


pm1004CtrlresetCount15PortEntry OBJECT-TYPE
	SYNTAX Pm1004CtrlresetCount15PortEntry
	MAX-ACCESS not-accessible
	STATUS current
	DESCRIPTION
        "
        Row definition for the pm1004CtrlresetCount15Port 
        table
        "
	INDEX   { pm1004CtrlresetCount15PortIndex }
	::= { pm1004CtrlresetCount15PortTable 1 }


Pm1004CtrlresetCount15PortEntry ::=
	SEQUENCE {
	pm1004CtrlresetCount15PortIndex
		INTEGER,
	pm1004CtrlclientResetAllPerfCount15Portn
		EkiState
	}


pm1004CtrlresetCount15PortIndex OBJECT-TYPE
	SYNTAX  INTEGER(0..128)
	MAX-ACCESS  read-only
	STATUS current
	DESCRIPTION
        "
        Index definition for the pm1004CtrlresetCount15Port 
        table
        "
	::= { pm1004CtrlresetCount15PortEntry 1 }


pm1004CtrlclientResetAllPerfCount15Portn OBJECT-TYPE
	SYNTAX  EkiState
	MAX-ACCESS read-write
	STATUS current
	DESCRIPTION
        "
        Client 15-min Counters Reset :This 
        OID resets all the current 15-min 
        Counters on the client port
        "
	::= { pm1004CtrlresetCount15PortEntry 2 }


--- *********************************************************
---     TABLE for the pm1004CtrlresetCount24Port articles
--- *********************************************************

pm1004CtrlresetCount24PortTable OBJECT-TYPE
	SYNTAX  SEQUENCE OF Pm1004CtrlresetCount24PortEntry
	MAX-ACCESS not-accessible
	STATUS current
	DESCRIPTION
        "
        List of pm1004CtrlresetCount24Port 
        Article
        "
	::= { pm1004CtrlClient 36 }


pm1004CtrlresetCount24PortEntry OBJECT-TYPE
	SYNTAX Pm1004CtrlresetCount24PortEntry
	MAX-ACCESS not-accessible
	STATUS current
	DESCRIPTION
        "
        Row definition for the pm1004CtrlresetCount24Port 
        table
        "
	INDEX   { pm1004CtrlresetCount24PortIndex }
	::= { pm1004CtrlresetCount24PortTable 1 }


Pm1004CtrlresetCount24PortEntry ::=
	SEQUENCE {
	pm1004CtrlresetCount24PortIndex
		INTEGER,
	pm1004CtrlclientResetAllPerfCount24Portn
		EkiState
	}


pm1004CtrlresetCount24PortIndex OBJECT-TYPE
	SYNTAX  INTEGER(0..128)
	MAX-ACCESS  read-only
	STATUS current
	DESCRIPTION
        "
        Index definition for the pm1004CtrlresetCount24Port 
        table
        "
	::= { pm1004CtrlresetCount24PortEntry 1 }


pm1004CtrlclientResetAllPerfCount24Portn OBJECT-TYPE
	SYNTAX  EkiState
	MAX-ACCESS read-write
	STATUS current
	DESCRIPTION
        "
        Client 24-hours Counters Reset 
        :This OID resets all the current 
        24-hours Counters on the client 
        port
        "
	::= { pm1004CtrlresetCount24PortEntry 2 }


--- *********************************************************
---     TABLE for the pm1004Ctrlprotocol articles
--- *********************************************************

pm1004CtrlprotocolTable OBJECT-TYPE
	SYNTAX  SEQUENCE OF Pm1004CtrlprotocolEntry
	MAX-ACCESS not-accessible
	STATUS current
	DESCRIPTION
        "
        List of pm1004Ctrlprotocol Articl
        e
        "
	::= { pm1004CtrlClient 51 }


pm1004CtrlprotocolEntry OBJECT-TYPE
	SYNTAX Pm1004CtrlprotocolEntry
	MAX-ACCESS not-accessible
	STATUS current
	DESCRIPTION
        "
        Row definition for the pm1004Ctrlprotocol 
        table
        "
	INDEX   { pm1004CtrlprotocolIndex }
	::= { pm1004CtrlprotocolTable 1 }


Pm1004CtrlprotocolEntry ::=
	SEQUENCE {
	pm1004CtrlprotocolIndex
		INTEGER,
	pm1004CtrlprotocolPortn
		EkiProtocol
	}


pm1004CtrlprotocolIndex OBJECT-TYPE
	SYNTAX  INTEGER(0..128)
	MAX-ACCESS  read-only
	STATUS current
	DESCRIPTION
        "
        Index definition for the pm1004Ctrlprotocol 
        table
        "
	::= { pm1004CtrlprotocolEntry 1 }


pm1004CtrlprotocolPortn OBJECT-TYPE
	SYNTAX  EkiProtocol
	MAX-ACCESS read-write
	STATUS current
	DESCRIPTION
        "
        Client Protocol : This OID sets 
        the protocol of the Client port
        .
        "
	::= { pm1004CtrlprotocolEntry 2 }


--- *****************************************************
---     LEAF for the commAccessLoop article
--- *****************************************************
pm1004CtrlcommAccessLoop OBJECT IDENTIFIER ::= { pm1004CtrlLine 64 }




pm1004CtrlCommAccessloop OBJECT-TYPE
	  SYNTAX EkiOnOff
	  MAX-ACCESS read-write
	  STATUS deprecated
	  DESCRIPTION
        "
        PM Full Access Loop Mode :This 
        OID, when set, puts the module
         in common access loop back, looping 
        the 10 Gb/s output signal on the 
        10 Gb/s input.
        "
	  ::= { pm1004CtrlcommAccessLoop 1 }



--- *****************************************************
---     LEAF for the lineLoop article
--- *****************************************************
pm1004CtrllineLoop OBJECT IDENTIFIER ::= { pm1004CtrlLine 66 }




pm1004CtrlLineLoop OBJECT-TYPE
	  SYNTAX EkiOnOff
	  MAX-ACCESS read-write
	  STATUS deprecated
	  DESCRIPTION
        "
        PM Line Loop Mode :This OID, when 
        set at '1' puts the module in line 
        loopback mode, looping the received 
        10 Gb/s signal on the transmit
         10 Gb/s output. The Upstream part 
        of the module is timed on the 10 
        Gb/s recovered clock in that case
        .
        "
	  ::= { pm1004CtrllineLoop 1 }



--- *****************************************************
---     LEAF for the msAis article
--- *****************************************************
pm1004CtrlmsAis OBJECT IDENTIFIER ::= { pm1004CtrlLine 67 }




pm1004CtrlMsAis OBJECT-TYPE
	  SYNTAX EkiOnOff
	  MAX-ACCESS read-write
	  STATUS current
	  DESCRIPTION
        "
        Insert MS-AIS/L-AIS On Line Output 
        :This OID, when set, inserts an 
        MS-AIS/L-AIS in the outgoing STM-64/OC-192 
        signal.
        "
	  ::= { pm1004CtrlmsAis 1 }



--- *********************************************************
---     TABLE for the pm1004CtrlfecDisable articles
--- *********************************************************

pm1004CtrlfecDisableTable OBJECT-TYPE
	SYNTAX  SEQUENCE OF Pm1004CtrlfecDisableEntry
	MAX-ACCESS not-accessible
	STATUS current
	DESCRIPTION
        "
        List of pm1004CtrlfecDisable Articl
        e
        "
	::= { pm1004CtrlLine 69 }


pm1004CtrlfecDisableEntry OBJECT-TYPE
	SYNTAX Pm1004CtrlfecDisableEntry
	MAX-ACCESS not-accessible
	STATUS current
	DESCRIPTION
        "
        Row definition for the pm1004CtrlfecDisable 
        table
        "
	INDEX   { pm1004CtrlfecDisableIndex }
	::= { pm1004CtrlfecDisableTable 1 }


Pm1004CtrlfecDisableEntry ::=
	SEQUENCE {
	pm1004CtrlfecDisableIndex
		INTEGER,
	pm1004CtrlfecDisablePortn
		EkiState
	}


pm1004CtrlfecDisableIndex OBJECT-TYPE
	SYNTAX  INTEGER(0..128)
	MAX-ACCESS  read-only
	STATUS current
	DESCRIPTION
        "
        Index definition for the pm1004CtrlfecDisable 
        table
        "
	::= { pm1004CtrlfecDisableEntry 1 }


pm1004CtrlfecDisablePortn OBJECT-TYPE
	SYNTAX  EkiState
	MAX-ACCESS read-write
	STATUS current
	DESCRIPTION
        "
        Forward Error Correction Inhibition 
        :This OID, when set, inhibits the 
        Forward Error Correction feature 
        on the line input  <Help>  This 
        control enables/disables the Forward 
        Error Correction on the line interfac
        e
        "
	::= { pm1004CtrlfecDisableEntry 2 }


--- *****************************************************
---     LEAF for the protMgnt article
--- *****************************************************
pm1004CtrlProtMgnt OBJECT IDENTIFIER ::= { pm1004CtrlLine 73 }




pm1004CtrlLineNumber OBJECT-TYPE
	  SYNTAX Unsigned32 (0..3)
	  MAX-ACCESS read-write
	  STATUS current
	  DESCRIPTION
        "
        Active Line Number : This OID
         sets the active line number
        "
	  ::= { pm1004CtrlProtMgnt 1 }



pm1004CtrlProtMode OBJECT-TYPE
	  SYNTAX EkiMode
	  MAX-ACCESS read-write
	  STATUS current
	  DESCRIPTION
        "
        Line Switch Mode (Auto Or Manual) 
        :This bit selects the manual (1) 
        or automatic (0) switch method
          <Help>  This control defines
         the protection switch mode on
         the line interface
        "
	  ::= { pm1004CtrlProtMgnt 2 }



--- *********************************************************
---     TABLE for the pm1004CtrllineOosMode articles
--- *********************************************************

pm1004CtrllineOosModeTable OBJECT-TYPE
	SYNTAX  SEQUENCE OF Pm1004CtrllineOosModeEntry
	MAX-ACCESS not-accessible
	STATUS current
	DESCRIPTION
        "
        List of pm1004CtrllineOosMode
         Article
        "
	::= { pm1004CtrlLine 74 }


pm1004CtrllineOosModeEntry OBJECT-TYPE
	SYNTAX Pm1004CtrllineOosModeEntry
	MAX-ACCESS not-accessible
	STATUS current
	DESCRIPTION
        "
        Row definition for the pm1004CtrllineOosMode 
        table
        "
	INDEX   { pm1004CtrllineOosModeIndex }
	::= { pm1004CtrllineOosModeTable 1 }


Pm1004CtrllineOosModeEntry ::=
	SEQUENCE {
	pm1004CtrllineOosModeIndex
		INTEGER,
	pm1004CtrllineOosModePortn
		EkiState
	}


pm1004CtrllineOosModeIndex OBJECT-TYPE
	SYNTAX  INTEGER(0..128)
	MAX-ACCESS  read-only
	STATUS current
	DESCRIPTION
        "
        Index definition for the pm1004CtrllineOosMode 
        table
        "
	::= { pm1004CtrllineOosModeEntry 1 }


pm1004CtrllineOosModePortn OBJECT-TYPE
	SYNTAX  EkiState
	MAX-ACCESS read-write
	STATUS current
	DESCRIPTION
        "
        Line Port Out Of Service :This 
        OID sets the line port Out Of Service 
         <Help>  This control defines the 
        service state of the line port
        "
	::= { pm1004CtrllineOosModeEntry 2 }


--- *********************************************************
---     TABLE for the pm1004CtrllineResetCount15Line articles
--- *********************************************************

pm1004CtrllineResetCount15LineTable OBJECT-TYPE
	SYNTAX  SEQUENCE OF Pm1004CtrllineResetCount15LineEntry
	MAX-ACCESS not-accessible
	STATUS current
	DESCRIPTION
        "
        List of pm1004CtrllineResetCount15Line 
        Article
        "
	::= { pm1004CtrlLine 86 }


pm1004CtrllineResetCount15LineEntry OBJECT-TYPE
	SYNTAX Pm1004CtrllineResetCount15LineEntry
	MAX-ACCESS not-accessible
	STATUS current
	DESCRIPTION
        "
        Row definition for the pm1004CtrllineResetCount15Line 
        table
        "
	INDEX   { pm1004CtrllineResetCount15LineIndex }
	::= { pm1004CtrllineResetCount15LineTable 1 }


Pm1004CtrllineResetCount15LineEntry ::=
	SEQUENCE {
	pm1004CtrllineResetCount15LineIndex
		INTEGER,
	pm1004CtrlresetAllPerfCount15Portn
		EkiState
	}


pm1004CtrllineResetCount15LineIndex OBJECT-TYPE
	SYNTAX  INTEGER(0..128)
	MAX-ACCESS  read-only
	STATUS current
	DESCRIPTION
        "
        Index definition for the pm1004CtrllineResetCount15Line 
        table
        "
	::= { pm1004CtrllineResetCount15LineEntry 1 }


pm1004CtrlresetAllPerfCount15Portn OBJECT-TYPE
	SYNTAX  EkiState
	MAX-ACCESS read-write
	STATUS current
	DESCRIPTION
        "
        Line 15-min Counters Reset :This 
        OID resets all the current 15-min 
        Counters on the client port
        "
	::= { pm1004CtrllineResetCount15LineEntry 2 }


--- *********************************************************
---     TABLE for the pm1004CtrllineResetCount24Line articles
--- *********************************************************

pm1004CtrllineResetCount24LineTable OBJECT-TYPE
	SYNTAX  SEQUENCE OF Pm1004CtrllineResetCount24LineEntry
	MAX-ACCESS not-accessible
	STATUS current
	DESCRIPTION
        "
        List of pm1004CtrllineResetCount24Line 
        Article
        "
	::= { pm1004CtrlLine 87 }


pm1004CtrllineResetCount24LineEntry OBJECT-TYPE
	SYNTAX Pm1004CtrllineResetCount24LineEntry
	MAX-ACCESS not-accessible
	STATUS current
	DESCRIPTION
        "
        Row definition for the pm1004CtrllineResetCount24Line 
        table
        "
	INDEX   { pm1004CtrllineResetCount24LineIndex }
	::= { pm1004CtrllineResetCount24LineTable 1 }


Pm1004CtrllineResetCount24LineEntry ::=
	SEQUENCE {
	pm1004CtrllineResetCount24LineIndex
		INTEGER,
	pm1004CtrlresetAllPerfCount24Portn
		EkiState
	}


pm1004CtrllineResetCount24LineIndex OBJECT-TYPE
	SYNTAX  INTEGER(0..128)
	MAX-ACCESS  read-only
	STATUS current
	DESCRIPTION
        "
        Index definition for the pm1004CtrllineResetCount24Line 
        table
        "
	::= { pm1004CtrllineResetCount24LineEntry 1 }


pm1004CtrlresetAllPerfCount24Portn OBJECT-TYPE
	SYNTAX  EkiState
	MAX-ACCESS read-write
	STATUS current
	DESCRIPTION
        "
        Line 24-hours Counters Reset :This 
        OID resets all the current 24-hours 
        Counters on the client port
        "
	::= { pm1004CtrllineResetCount24LineEntry 2 }


--- *****************************************************
---     LEAF for the ledTest article
--- *****************************************************
pm1004CtrlledTest OBJECT IDENTIFIER ::= { pm1004CtrlOther 192 }




pm1004CtrlLedOff OBJECT-TYPE
	  SYNTAX EkiOnOff
	  MAX-ACCESS read-write
	  STATUS current
	  DESCRIPTION
        "
        Leds Off :This OID switches off 
        all the Leds as a test feature. 
         <Help>  This control initiates 
        a test leds turning all the LEDs 
        to OFF
        "
	  ::= { pm1004CtrlledTest 3 }



pm1004CtrlRedLed OBJECT-TYPE
	  SYNTAX EkiOnOff
	  MAX-ACCESS read-write
	  STATUS current
	  DESCRIPTION
        "
        Red Leds Test :This OID switches 
        on all the red Leds as a test feature. 
         <Help>  This control initiates 
        a test leds turning all the LEDs 
        to red
        "
	  ::= { pm1004CtrlledTest 2 }



pm1004CtrlGreenLed OBJECT-TYPE
	  SYNTAX EkiOnOff
	  MAX-ACCESS read-write
	  STATUS current
	  DESCRIPTION
        "
        Green Leds Test :This OID switches 
        on all the green Leds as a test 
        feature.  <Help>  This control
         initiates a test leds turning
         all the LEDs to green
        "
	  ::= { pm1004CtrlledTest 1 }



--- *****************************************************
---     LEAF for the moduleOosMode article
--- *****************************************************
pm1004CtrlmoduleOosMode OBJECT IDENTIFIER ::= { pm1004CtrlOther 193 }




pm1004CtrlModuleOosMode OBJECT-TYPE
	  SYNTAX EkiOnOff
	  MAX-ACCESS read-write
	  STATUS current
	  DESCRIPTION
        "
        PM Out Of Service :This OID sets 
        the PM Out Of Service  <Help> 
         This control defines the service 
        state of the complete module
        "
	  ::= { pm1004CtrlmoduleOosMode 1 }



--- *****************************************************
---     LEAF for the maintenanceMode article
--- *****************************************************
pm1004CtrlmaintenanceMode OBJECT IDENTIFIER ::= { pm1004CtrlOther 197 }




pm1004CtrlMaintenanceMode OBJECT-TYPE
	  SYNTAX EkiOnOff
	  MAX-ACCESS read-write
	  STATUS current
	  DESCRIPTION
        "
        Module Maintenance Mode :This
         OID enables the maintenance mode 
        on the PM.  <Help>   This control 
        enables the maintenance mode on 
        the PM.
        "
	  ::= { pm1004CtrlmaintenanceMode 1 }



--- *****************************************************
---     LEAF for the dccEnable article
--- *****************************************************
pm1004CtrldccEnable OBJECT IDENTIFIER ::= { pm1004CtrlOther 198 }




pm1004CtrlDccEnable OBJECT-TYPE
	  SYNTAX EkiOnOff
	  MAX-ACCESS read-write
	  STATUS current
	  DESCRIPTION
        "
        DCC Enable :This OID enables the 
        DCC mode on the PM   <Help>   This 
        control enables the DCC mode on 
        the PM
        "
	  ::= { pm1004CtrldccEnable 1 }



--- *********************************************************
---     TABLE for the pm1004CtrlxfpOnoff articles
--- *********************************************************

pm1004CtrlxfpOnoffTable OBJECT-TYPE
	SYNTAX  SEQUENCE OF Pm1004CtrlxfpOnoffEntry
	MAX-ACCESS not-accessible
	STATUS current
	DESCRIPTION
        "
        List of pm1004CtrlxfpOnoff Articl
        e
        "
	::= { pm1004CtrlLine 208 }


pm1004CtrlxfpOnoffEntry OBJECT-TYPE
	SYNTAX Pm1004CtrlxfpOnoffEntry
	MAX-ACCESS not-accessible
	STATUS current
	DESCRIPTION
        "
        Row definition for the pm1004CtrlxfpOnoff 
        table
        "
	INDEX   { pm1004CtrlxfpOnoffIndex }
	::= { pm1004CtrlxfpOnoffTable 1 }


Pm1004CtrlxfpOnoffEntry ::=
	SEQUENCE {
	pm1004CtrlxfpOnoffIndex
		INTEGER,
	pm1004CtrlxfpOnoffPortn
		EkiState
	}


pm1004CtrlxfpOnoffIndex OBJECT-TYPE
	SYNTAX  INTEGER(0..128)
	MAX-ACCESS  read-only
	STATUS current
	DESCRIPTION
        "
        Index definition for the pm1004CtrlxfpOnoff 
        table
        "
	::= { pm1004CtrlxfpOnoffEntry 1 }


pm1004CtrlxfpOnoffPortn OBJECT-TYPE
	SYNTAX  EkiState
	MAX-ACCESS read-write
	STATUS current
	DESCRIPTION
        "
        Line Optical Laser Shutdown :This 
        OID switches off the XFP or the 
        OTX  <Help>  This control defines 
        the laser state of the line transceive
        r
        "
	::= { pm1004CtrlxfpOnoffEntry 2 }


--- *********************************************************
---     TABLE for the pm1004CtrlxfpLineLoop articles
--- *********************************************************

pm1004CtrlxfpLineLoopTable OBJECT-TYPE
	SYNTAX  SEQUENCE OF Pm1004CtrlxfpLineLoopEntry
	MAX-ACCESS not-accessible
	STATUS current
	DESCRIPTION
        "
        List of pm1004CtrlxfpLineLoop
         Article
        "
	::= { pm1004CtrlLine 209 }


pm1004CtrlxfpLineLoopEntry OBJECT-TYPE
	SYNTAX Pm1004CtrlxfpLineLoopEntry
	MAX-ACCESS not-accessible
	STATUS current
	DESCRIPTION
        "
        Row definition for the pm1004CtrlxfpLineLoop 
        table
        "
	INDEX   { pm1004CtrlxfpLineLoopIndex }
	::= { pm1004CtrlxfpLineLoopTable 1 }


Pm1004CtrlxfpLineLoopEntry ::=
	SEQUENCE {
	pm1004CtrlxfpLineLoopIndex
		INTEGER,
	pm1004CtrlxfpLineLoopPortn
		EkiState
	}


pm1004CtrlxfpLineLoopIndex OBJECT-TYPE
	SYNTAX  INTEGER(0..128)
	MAX-ACCESS  read-only
	STATUS current
	DESCRIPTION
        "
        Index definition for the pm1004CtrlxfpLineLoop 
        table
        "
	::= { pm1004CtrlxfpLineLoopEntry 1 }


pm1004CtrlxfpLineLoopPortn OBJECT-TYPE
	SYNTAX  EkiState
	MAX-ACCESS read-write
	STATUS current
	DESCRIPTION
        "
        Line Facility Loopback :This OID 
        operates a Line Facility Loopback, 
        looping line input signal on the 
        line output port. The loop is located 
        on the line transceiver. If the 
        Line signal carries DCC, the management 
        network is impacted  <Help> This 
        maintenance parameter operates
         a Line Facility Loopback, looping 
        line input signal on the line output 
        port. The loop is located on the 
        line transceiver. If the Line signal 
        carries DCC, the management network 
        is impacted
        "
	::= { pm1004CtrlxfpLineLoopEntry 2 }


--- *********************************************************
---     TABLE for the pm1004CtrlxfpXfiLoop articles
--- *********************************************************

pm1004CtrlxfpXfiLoopTable OBJECT-TYPE
	SYNTAX  SEQUENCE OF Pm1004CtrlxfpXfiLoopEntry
	MAX-ACCESS not-accessible
	STATUS current
	DESCRIPTION
        "
        List of pm1004CtrlxfpXfiLoop Articl
        e
        "
	::= { pm1004CtrlLine 210 }


pm1004CtrlxfpXfiLoopEntry OBJECT-TYPE
	SYNTAX Pm1004CtrlxfpXfiLoopEntry
	MAX-ACCESS not-accessible
	STATUS current
	DESCRIPTION
        "
        Row definition for the pm1004CtrlxfpXfiLoop 
        table
        "
	INDEX   { pm1004CtrlxfpXfiLoopIndex }
	::= { pm1004CtrlxfpXfiLoopTable 1 }


Pm1004CtrlxfpXfiLoopEntry ::=
	SEQUENCE {
	pm1004CtrlxfpXfiLoopIndex
		INTEGER,
	pm1004CtrlxfpXfiLoopPortn
		EkiState
	}


pm1004CtrlxfpXfiLoopIndex OBJECT-TYPE
	SYNTAX  INTEGER(0..128)
	MAX-ACCESS  read-only
	STATUS current
	DESCRIPTION
        "
        Index definition for the pm1004CtrlxfpXfiLoop 
        table
        "
	::= { pm1004CtrlxfpXfiLoopEntry 1 }


pm1004CtrlxfpXfiLoopPortn OBJECT-TYPE
	SYNTAX  EkiState
	MAX-ACCESS read-write
	STATUS current
	DESCRIPTION
        "
        Line Terminal Loopback :This OID 
        operates a Line Terminal Loopback, 
        looping line input signal on the 
        line output port. The loop is located 
        on all client transceivers  <Help> 
        This maintenance parameter operates 
        a Line Terminal Loopback, looping 
        line input signal on the line output 
        port. The loop is located on all 
        client transceivers.
        "
	::= { pm1004CtrlxfpXfiLoopEntry 2 }


--- *********************************************************
---     TABLE for the pm1004CtrllineTunableChannel articles
--- *********************************************************

pm1004CtrllineTunableChannelTable OBJECT-TYPE
	SYNTAX  SEQUENCE OF Pm1004CtrllineTunableChannelEntry
	MAX-ACCESS not-accessible
	STATUS current
	DESCRIPTION
        "
        List of pm1004CtrllineTunableChannel 
        Article
        "
	::= { pm1004CtrlLine 212 }


pm1004CtrllineTunableChannelEntry OBJECT-TYPE
	SYNTAX Pm1004CtrllineTunableChannelEntry
	MAX-ACCESS not-accessible
	STATUS current
	DESCRIPTION
        "
        Row definition for the pm1004CtrllineTunableChannel 
        table
        "
	INDEX   { pm1004CtrllineTunableChannelIndex }
	::= { pm1004CtrllineTunableChannelTable 1 }


Pm1004CtrllineTunableChannelEntry ::=
	SEQUENCE {
	pm1004CtrllineTunableChannelIndex
		INTEGER,
	pm1004CtrllineTunableChannelPortn
		Pm1004OtxChannel
	}


pm1004CtrllineTunableChannelIndex OBJECT-TYPE
	SYNTAX  INTEGER(0..128)
	MAX-ACCESS  read-only
	STATUS current
	DESCRIPTION
        "
        Index definition for the pm1004CtrllineTunableChannel 
        table
        "
	::= { pm1004CtrllineTunableChannelEntry 1 }


pm1004CtrllineTunableChannelPortn OBJECT-TYPE
	SYNTAX  Pm1004OtxChannel
	MAX-ACCESS read-write
	STATUS current
	DESCRIPTION
        "
        ITU Channel :This OID selects
         the ITU channel of the Line OTX 
        TLH Laser  <Help>   This control 
        defines the ITU channel of the
         Line OTX TLH Laser
        "
	::= { pm1004CtrllineTunableChannelEntry 2 }


--- *********************************************************
---     TABLE for the pm1004CtrllinePhotodiodeMode articles
--- *********************************************************

pm1004CtrllinePhotodiodeModeTable OBJECT-TYPE
	SYNTAX  SEQUENCE OF Pm1004CtrllinePhotodiodeModeEntry
	MAX-ACCESS not-accessible
	STATUS current
	DESCRIPTION
        "
        List of pm1004CtrllinePhotodiodeMode 
        Article
        "
	::= { pm1004CtrlLine 213 }


pm1004CtrllinePhotodiodeModeEntry OBJECT-TYPE
	SYNTAX Pm1004CtrllinePhotodiodeModeEntry
	MAX-ACCESS not-accessible
	STATUS current
	DESCRIPTION
        "
        Row definition for the pm1004CtrllinePhotodiodeMode 
        table
        "
	INDEX   { pm1004CtrllinePhotodiodeModeIndex }
	::= { pm1004CtrllinePhotodiodeModeTable 1 }


Pm1004CtrllinePhotodiodeModeEntry ::=
	SEQUENCE {
	pm1004CtrllinePhotodiodeModeIndex
		INTEGER,
	pm1004CtrllinePhotodiodeModePortn
		Pm1004OtxMode
	}


pm1004CtrllinePhotodiodeModeIndex OBJECT-TYPE
	SYNTAX  INTEGER(0..128)
	MAX-ACCESS  read-only
	STATUS current
	DESCRIPTION
        "
        Index definition for the pm1004CtrllinePhotodiodeMode 
        table
        "
	::= { pm1004CtrllinePhotodiodeModeEntry 1 }


pm1004CtrllinePhotodiodeModePortn OBJECT-TYPE
	SYNTAX  Pm1004OtxMode
	MAX-ACCESS read-write
	STATUS current
	DESCRIPTION
        "
        OTX TLH Rx Sens. Mode :This OID 
        defines the Rx sensiblity mode
         of the Line OTX TLH  <Help>  
         This control defines the receiver 
        sensibility mode of the Line OTX 
        TLH Laser (OTX60, OTX80 or Custom
        )
        "
	::= { pm1004CtrllinePhotodiodeModeEntry 2 }


--- *********************************************************
---     TABLE for the pm1004CtrllinePhotodiodeValue articles
--- *********************************************************

pm1004CtrllinePhotodiodeValueTable OBJECT-TYPE
	SYNTAX  SEQUENCE OF Pm1004CtrllinePhotodiodeValueEntry
	MAX-ACCESS not-accessible
	STATUS current
	DESCRIPTION
        "
        List of pm1004CtrllinePhotodiodeValue 
        Article
        "
	::= { pm1004CtrlLine 214 }


pm1004CtrllinePhotodiodeValueEntry OBJECT-TYPE
	SYNTAX Pm1004CtrllinePhotodiodeValueEntry
	MAX-ACCESS not-accessible
	STATUS current
	DESCRIPTION
        "
        Row definition for the pm1004CtrllinePhotodiodeValue 
        table
        "
	INDEX   { pm1004CtrllinePhotodiodeValueIndex }
	::= { pm1004CtrllinePhotodiodeValueTable 1 }


Pm1004CtrllinePhotodiodeValueEntry ::=
	SEQUENCE {
	pm1004CtrllinePhotodiodeValueIndex
		INTEGER,
	pm1004CtrllinePhotodiodeValuePortn
		Pm1004AdjustValue
	}


pm1004CtrllinePhotodiodeValueIndex OBJECT-TYPE
	SYNTAX  INTEGER(0..128)
	MAX-ACCESS  read-only
	STATUS current
	DESCRIPTION
        "
        Index definition for the pm1004CtrllinePhotodiodeValue 
        table
        "
	::= { pm1004CtrllinePhotodiodeValueEntry 1 }


pm1004CtrllinePhotodiodeValuePortn OBJECT-TYPE
	SYNTAX  Pm1004AdjustValue
	MAX-ACCESS read-write
	STATUS current
	DESCRIPTION
        "
        OTX TLH Rx Sensibility :This OID 
        sets the Rx sensibility of the
         Line OTX TLH (custom mode only) 
         <Help>   This control defines
         the receiver sensibility value 
        (only in Custom mode) of the Line 
        OTX TLH Laser
        "
	::= { pm1004CtrllinePhotodiodeValueEntry 2 }


--- *********************************************************
---     TABLE for the pm1004CtrllinePowerLaser articles
--- *********************************************************

pm1004CtrllinePowerLaserTable OBJECT-TYPE
	SYNTAX  SEQUENCE OF Pm1004CtrllinePowerLaserEntry
	MAX-ACCESS not-accessible
	STATUS current
	DESCRIPTION
        "
        List of pm1004CtrllinePowerLaser 
        Article
        "
	::= { pm1004CtrlLine 215 }


pm1004CtrllinePowerLaserEntry OBJECT-TYPE
	SYNTAX Pm1004CtrllinePowerLaserEntry
	MAX-ACCESS not-accessible
	STATUS current
	DESCRIPTION
        "
        Row definition for the pm1004CtrllinePowerLaser 
        table
        "
	INDEX   { pm1004CtrllinePowerLaserIndex }
	::= { pm1004CtrllinePowerLaserTable 1 }


Pm1004CtrllinePowerLaserEntry ::=
	SEQUENCE {
	pm1004CtrllinePowerLaserIndex
		INTEGER,
	pm1004CtrllinePowerLaserPortn
		INTEGER 
	}


pm1004CtrllinePowerLaserIndex OBJECT-TYPE
	SYNTAX  INTEGER(0..128)
	MAX-ACCESS  read-only
	STATUS current
	DESCRIPTION
        "
        Index definition for the pm1004CtrllinePowerLaser 
        table
        "
	::= { pm1004CtrllinePowerLaserEntry 1 }


pm1004CtrllinePowerLaserPortn OBJECT-TYPE
	SYNTAX  INTEGER (0..65535)
	MAX-ACCESS read-write
	STATUS current
	DESCRIPTION
        "
        Line Laser Output Power [3-5]
         :This OID sets the output power 
        value on the laser of the Line
         OTX TLH (AV=Power*10+158) (Unit 
        = dBm)  <Help>   This control defines 
        the start-up output power of the 
        Line OTX TLH
        "
	::= { pm1004CtrllinePowerLaserEntry 2 }


--- *****************************************************
---     LEAF for the otxVlhReset article
--- *****************************************************
pm1004CtrlotxVlhReset OBJECT IDENTIFIER ::= { pm1004CtrlLine 216 }




pm1004CtrlOtxVlhReset OBJECT-TYPE
	  SYNTAX EkiOnOff
	  MAX-ACCESS read-write
	  STATUS current
	  DESCRIPTION
        "
        OTX-VLH Reset :This OID resets 
        the OTX-VLH module  <Help>  This 
        control resets the OTX-VLH and
         its parameters  
        "
	  ::= { pm1004CtrlotxVlhReset 1 }








--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm1004CntupRaRemCnt articles
--- *********************************************************

pm1004CntupRaRemCntTable OBJECT-TYPE
	SYNTAX  SEQUENCE OF Pm1004CntupRaRemCntEntry
	MAX-ACCESS not-accessible
	STATUS current
	DESCRIPTION
        "
        List of pm1004CntupRaRemCnt Articl
        e
        "
	::= { pm1004CntClient 16 }


pm1004CntupRaRemCntEntry OBJECT-TYPE
	SYNTAX Pm1004CntupRaRemCntEntry
	MAX-ACCESS not-accessible
	STATUS current
	DESCRIPTION
        "
        Row definition for the pm1004CntupRaRemCnt 
        table
        "
	INDEX   { pm1004CntupRaRemCntIndex }
	::= { pm1004CntupRaRemCntTable 1 }


Pm1004CntupRaRemCntEntry ::=
	SEQUENCE {
	pm1004CntupRaRemCntIndex
		INTEGER,
	pm1004CntupRaRemCntValuePortn
		Counter32,
	pm1004CntupRaRemCntErrorPortn
		EkiOnOff,
	pm1004CntupRaRemCntOverloadPortn
		EkiOnOff
	}


pm1004CntupRaRemCntIndex OBJECT-TYPE
	SYNTAX  INTEGER(0..128)
	MAX-ACCESS  read-only
	STATUS current
	DESCRIPTION
        "
        Index definition for the pm1004CntupRaRemCnt 
        table
        "
	::= { pm1004CntupRaRemCntEntry 1 }


pm1004CntupRaRemCntValuePortn OBJECT-TYPE
	SYNTAX  Counter32
	MAX-ACCESS read-only
	STATUS current
	DESCRIPTION
        "
        Client Rate Adapt. Words Removal 
        :This counter is incremented each 
        time a rate adaptation 10B word 
        is removed from the Client input 
        stream
        "
	::= { pm1004CntupRaRemCntEntry 2 }


pm1004CntupRaRemCntErrorPortn OBJECT-TYPE
	SYNTAX  EkiOnOff
	MAX-ACCESS read-only
	STATUS current
	DESCRIPTION
        "
        Client Counter Error :This OID 
        when set indicates the rate adaptation 
        removal counter value is invalid 
        on Port
        "
	::= { pm1004CntupRaRemCntEntry 3 }


pm1004CntupRaRemCntOverloadPortn OBJECT-TYPE
	SYNTAX  EkiOnOff
	MAX-ACCESS read-only
	STATUS current
	DESCRIPTION
        "
        Client Counter Overload :This
         OID when set indicates a rate
         adaptation removal counter overload 
        on Port
        "
	::= { pm1004CntupRaRemCntEntry 4 }


--- *********************************************************
---     TABLE for the pm1004CntupRaInsCnt articles
--- *********************************************************

pm1004CntupRaInsCntTable OBJECT-TYPE
	SYNTAX  SEQUENCE OF Pm1004CntupRaInsCntEntry
	MAX-ACCESS not-accessible
	STATUS current
	DESCRIPTION
        "
        List of pm1004CntupRaInsCnt Articl
        e
        "
	::= { pm1004CntClient 24 }


pm1004CntupRaInsCntEntry OBJECT-TYPE
	SYNTAX Pm1004CntupRaInsCntEntry
	MAX-ACCESS not-accessible
	STATUS current
	DESCRIPTION
        "
        Row definition for the pm1004CntupRaInsCnt 
        table
        "
	INDEX   { pm1004CntupRaInsCntIndex }
	::= { pm1004CntupRaInsCntTable 1 }


Pm1004CntupRaInsCntEntry ::=
	SEQUENCE {
	pm1004CntupRaInsCntIndex
		INTEGER,
	pm1004CntupRaInsCntValuePortn
		Counter32,
	pm1004CntupRaInsCntErrorPortn
		EkiOnOff,
	pm1004CntupRaInsCntOverloadPortn
		EkiOnOff
	}


pm1004CntupRaInsCntIndex OBJECT-TYPE
	SYNTAX  INTEGER(0..128)
	MAX-ACCESS  read-only
	STATUS current
	DESCRIPTION
        "
        Index definition for the pm1004CntupRaInsCnt 
        table
        "
	::= { pm1004CntupRaInsCntEntry 1 }


pm1004CntupRaInsCntValuePortn OBJECT-TYPE
	SYNTAX  Counter32
	MAX-ACCESS read-only
	STATUS current
	DESCRIPTION
        "
        Client Rate Adapt. Words Insertion 
        :This counter is incremented each 
        time a rate adaptation 10B word 
        is inserted in the Client input 
        stream
        "
	::= { pm1004CntupRaInsCntEntry 2 }


pm1004CntupRaInsCntErrorPortn OBJECT-TYPE
	SYNTAX  EkiOnOff
	MAX-ACCESS read-only
	STATUS current
	DESCRIPTION
        "
        Client Counter Error :This OID 
        when set indicates the rate adaptation 
        insertion counter value is invalid 
        on Port
        "
	::= { pm1004CntupRaInsCntEntry 3 }


pm1004CntupRaInsCntOverloadPortn OBJECT-TYPE
	SYNTAX  EkiOnOff
	MAX-ACCESS read-only
	STATUS current
	DESCRIPTION
        "
        Client Counter Overload :This
         OID when set indicates a rate
         adaptation insertion counter overload 
        on Port
        "
	::= { pm1004CntupRaInsCntEntry 4 }


--- *********************************************************
---     TABLE for the pm1004CntupRdErrCnt articles
--- *********************************************************

pm1004CntupRdErrCntTable OBJECT-TYPE
	SYNTAX  SEQUENCE OF Pm1004CntupRdErrCntEntry
	MAX-ACCESS not-accessible
	STATUS current
	DESCRIPTION
        "
        List of pm1004CntupRdErrCnt Articl
        e
        "
	::= { pm1004CntClient 32 }


pm1004CntupRdErrCntEntry OBJECT-TYPE
	SYNTAX Pm1004CntupRdErrCntEntry
	MAX-ACCESS not-accessible
	STATUS current
	DESCRIPTION
        "
        Row definition for the pm1004CntupRdErrCnt 
        table
        "
	INDEX   { pm1004CntupRdErrCntIndex }
	::= { pm1004CntupRdErrCntTable 1 }


Pm1004CntupRdErrCntEntry ::=
	SEQUENCE {
	pm1004CntupRdErrCntIndex
		INTEGER,
	pm1004CntupRdErrCntValuePortn
		Counter32,
	pm1004CntupRdErrCntErrorPortn
		EkiOnOff,
	pm1004CntupRdErrCntOverloadPortn
		EkiOnOff
	}


pm1004CntupRdErrCntIndex OBJECT-TYPE
	SYNTAX  INTEGER(0..128)
	MAX-ACCESS  read-only
	STATUS current
	DESCRIPTION
        "
        Index definition for the pm1004CntupRdErrCnt 
        table
        "
	::= { pm1004CntupRdErrCntEntry 1 }


pm1004CntupRdErrCntValuePortn OBJECT-TYPE
	SYNTAX  Counter32
	MAX-ACCESS read-only
	STATUS current
	DESCRIPTION
        "
        Client Input Errors :This counter 
        is increased each time a 10b/8b 
        running disparity error is detected 
        on the Client input stream  <Help> 
         This counter gives the number
         of B1 errors on the client input 
        port
        "
	::= { pm1004CntupRdErrCntEntry 2 }


pm1004CntupRdErrCntErrorPortn OBJECT-TYPE
	SYNTAX  EkiOnOff
	MAX-ACCESS read-only
	STATUS current
	DESCRIPTION
        "
        Client Counter Error :This OID 
        when set indicates the client error 
        counter value is invalid on Por
        t
        "
	::= { pm1004CntupRdErrCntEntry 3 }


pm1004CntupRdErrCntOverloadPortn OBJECT-TYPE
	SYNTAX  EkiOnOff
	MAX-ACCESS read-only
	STATUS current
	DESCRIPTION
        "
        Client Counter Overload :This
         OID when set indicates a client 
        input error counter overload on 
        Port
        "
	::= { pm1004CntupRdErrCntEntry 4 }


--- *********************************************************
---     TABLE for the pm1004CntupTimCnt articles
--- *********************************************************

pm1004CntupTimCntTable OBJECT-TYPE
	SYNTAX  SEQUENCE OF Pm1004CntupTimCntEntry
	MAX-ACCESS not-accessible
	STATUS current
	DESCRIPTION
        "
        List of pm1004CntupTimCnt Articl
        e
        "
	::= { pm1004CntClient 40 }


pm1004CntupTimCntEntry OBJECT-TYPE
	SYNTAX Pm1004CntupTimCntEntry
	MAX-ACCESS not-accessible
	STATUS current
	DESCRIPTION
        "
        Row definition for the pm1004CntupTimCnt 
        table
        "
	INDEX   { pm1004CntupTimCntIndex }
	::= { pm1004CntupTimCntTable 1 }


Pm1004CntupTimCntEntry ::=
	SEQUENCE {
	pm1004CntupTimCntIndex
		INTEGER,
	pm1004CntupTimCntValuePortn
		Counter32,
	pm1004CntupTimCntErrorPortn
		EkiOnOff,
	pm1004CntupTimCntOverloadPortn
		EkiOnOff
	}


pm1004CntupTimCntIndex OBJECT-TYPE
	SYNTAX  INTEGER(0..128)
	MAX-ACCESS  read-only
	STATUS current
	DESCRIPTION
        "
        Index definition for the pm1004CntupTimCnt 
        table
        "
	::= { pm1004CntupTimCntEntry 1 }


pm1004CntupTimCntValuePortn OBJECT-TYPE
	SYNTAX  Counter32
	MAX-ACCESS read-only
	STATUS current
	DESCRIPTION
        "
        Client Upstream Timer Counter
         :This is the timing counter dedicated 
        to the upstream access counters. 
        It is incremented every 125 us
        .
        "
	::= { pm1004CntupTimCntEntry 2 }


pm1004CntupTimCntErrorPortn OBJECT-TYPE
	SYNTAX  EkiOnOff
	MAX-ACCESS read-only
	STATUS current
	DESCRIPTION
        "
        Client Counter Error :This OID 
        when set indicates the upstream 
        timing counter value is invalid 
        on Port
        "
	::= { pm1004CntupTimCntEntry 3 }


pm1004CntupTimCntOverloadPortn OBJECT-TYPE
	SYNTAX  EkiOnOff
	MAX-ACCESS read-only
	STATUS current
	DESCRIPTION
        "
        Client Counter Overload :This
         OID when set indicates a upstream 
        timing counter overload on Por
        t
        "
	::= { pm1004CntupTimCntEntry 4 }


--- *********************************************************
---     TABLE for the pm1004CntupCvErrCnt articles
--- *********************************************************

pm1004CntupCvErrCntTable OBJECT-TYPE
	SYNTAX  SEQUENCE OF Pm1004CntupCvErrCntEntry
	MAX-ACCESS not-accessible
	STATUS current
	DESCRIPTION
        "
        List of pm1004CntupCvErrCnt Articl
        e
        "
	::= { pm1004CntClient 48 }


pm1004CntupCvErrCntEntry OBJECT-TYPE
	SYNTAX Pm1004CntupCvErrCntEntry
	MAX-ACCESS not-accessible
	STATUS current
	DESCRIPTION
        "
        Row definition for the pm1004CntupCvErrCnt 
        table
        "
	INDEX   { pm1004CntupCvErrCntIndex }
	::= { pm1004CntupCvErrCntTable 1 }


Pm1004CntupCvErrCntEntry ::=
	SEQUENCE {
	pm1004CntupCvErrCntIndex
		INTEGER,
	pm1004CntupCvErrCntValuePortn
		Counter32,
	pm1004CntupCvErrCntErrorPortn
		EkiOnOff,
	pm1004CntupCvErrCntOverloadPortn
		EkiOnOff
	}


pm1004CntupCvErrCntIndex OBJECT-TYPE
	SYNTAX  INTEGER(0..128)
	MAX-ACCESS  read-only
	STATUS current
	DESCRIPTION
        "
        Index definition for the pm1004CntupCvErrCnt 
        table
        "
	::= { pm1004CntupCvErrCntEntry 1 }


pm1004CntupCvErrCntValuePortn OBJECT-TYPE
	SYNTAX  Counter32
	MAX-ACCESS read-only
	STATUS current
	DESCRIPTION
        "
        Client Coding Violation Counter 
        :This counter is increased each 
        time a 10b/8b coding violation
         is detected on the Client input 
        stream
        "
	::= { pm1004CntupCvErrCntEntry 2 }


pm1004CntupCvErrCntErrorPortn OBJECT-TYPE
	SYNTAX  EkiOnOff
	MAX-ACCESS read-only
	STATUS current
	DESCRIPTION
        "
        Client Counter Error :This OID 
        when set indicates the coding violation 
        counter value is invalid on Por
        t
        "
	::= { pm1004CntupCvErrCntEntry 3 }


pm1004CntupCvErrCntOverloadPortn OBJECT-TYPE
	SYNTAX  EkiOnOff
	MAX-ACCESS read-only
	STATUS current
	DESCRIPTION
        "
        Client Counter Overload :This
         OID when set indicates a coding 
        violation counter overload on Por
        t
        "
	::= { pm1004CntupCvErrCntEntry 4 }


--- *********************************************************
---     TABLE for the pm1004CntdwCbipCnt articles
--- *********************************************************

pm1004CntdwCbipCntTable OBJECT-TYPE
	SYNTAX  SEQUENCE OF Pm1004CntdwCbipCntEntry
	MAX-ACCESS not-accessible
	STATUS current
	DESCRIPTION
        "
        List of pm1004CntdwCbipCnt Articl
        e
        "
	::= { pm1004CntClient 64 }


pm1004CntdwCbipCntEntry OBJECT-TYPE
	SYNTAX Pm1004CntdwCbipCntEntry
	MAX-ACCESS not-accessible
	STATUS current
	DESCRIPTION
        "
        Row definition for the pm1004CntdwCbipCnt 
        table
        "
	INDEX   { pm1004CntdwCbipCntIndex }
	::= { pm1004CntdwCbipCntTable 1 }


Pm1004CntdwCbipCntEntry ::=
	SEQUENCE {
	pm1004CntdwCbipCntIndex
		INTEGER,
	pm1004CntdwCbipCntValuePortn
		Counter32,
	pm1004CntdwCbipCntErrorPortn
		EkiOnOff,
	pm1004CntdwCbipCntOverloadPortn
		EkiOnOff
	}


pm1004CntdwCbipCntIndex OBJECT-TYPE
	SYNTAX  INTEGER(0..128)
	MAX-ACCESS  read-only
	STATUS current
	DESCRIPTION
        "
        Index definition for the pm1004CntdwCbipCnt 
        table
        "
	::= { pm1004CntdwCbipCntEntry 1 }


pm1004CntdwCbipCntValuePortn OBJECT-TYPE
	SYNTAX  Counter32
	MAX-ACCESS read-only
	STATUS current
	DESCRIPTION
        "
        Client Output Errors :This counter 
        is incremented each time a CBIP 
        parity error is detected on the 
        Client output stream  <Help>  This 
        counter gives the number of B1
         errors on the client output por
        t
        "
	::= { pm1004CntdwCbipCntEntry 2 }


pm1004CntdwCbipCntErrorPortn OBJECT-TYPE
	SYNTAX  EkiOnOff
	MAX-ACCESS read-only
	STATUS current
	DESCRIPTION
        "
        Client Counter Error :This OID 
        when set indicates the CBIP error 
        counter value is invalid on Por
        t
        "
	::= { pm1004CntdwCbipCntEntry 3 }


pm1004CntdwCbipCntOverloadPortn OBJECT-TYPE
	SYNTAX  EkiOnOff
	MAX-ACCESS read-only
	STATUS current
	DESCRIPTION
        "
        Client CBIP Counter Overload :This 
        OID when set indicates a CBIP error 
        counter overload on Port
        "
	::= { pm1004CntdwCbipCntEntry 4 }


--- *********************************************************
---     TABLE for the pm1004CntdwTimCnt articles
--- *********************************************************

pm1004CntdwTimCntTable OBJECT-TYPE
	SYNTAX  SEQUENCE OF Pm1004CntdwTimCntEntry
	MAX-ACCESS not-accessible
	STATUS current
	DESCRIPTION
        "
        List of pm1004CntdwTimCnt Articl
        e
        "
	::= { pm1004CntClient 72 }


pm1004CntdwTimCntEntry OBJECT-TYPE
	SYNTAX Pm1004CntdwTimCntEntry
	MAX-ACCESS not-accessible
	STATUS current
	DESCRIPTION
        "
        Row definition for the pm1004CntdwTimCnt 
        table
        "
	INDEX   { pm1004CntdwTimCntIndex }
	::= { pm1004CntdwTimCntTable 1 }


Pm1004CntdwTimCntEntry ::=
	SEQUENCE {
	pm1004CntdwTimCntIndex
		INTEGER,
	pm1004CntdwTimCntValuePortn
		Counter32,
	pm1004CntdwTimCntErrorPortn
		EkiOnOff,
	pm1004CntdwTimCntOverloadPortn
		EkiOnOff
	}


pm1004CntdwTimCntIndex OBJECT-TYPE
	SYNTAX  INTEGER(0..128)
	MAX-ACCESS  read-only
	STATUS current
	DESCRIPTION
        "
        Index definition for the pm1004CntdwTimCnt 
        table
        "
	::= { pm1004CntdwTimCntEntry 1 }


pm1004CntdwTimCntValuePortn OBJECT-TYPE
	SYNTAX  Counter32
	MAX-ACCESS read-only
	STATUS current
	DESCRIPTION
        "
        Client Downstream Timer Counter 
        :This is the timing counter dedicated 
        to the downstream access counters. 
        It is incremented every 125 us
        .
        "
	::= { pm1004CntdwTimCntEntry 2 }


pm1004CntdwTimCntErrorPortn OBJECT-TYPE
	SYNTAX  EkiOnOff
	MAX-ACCESS read-only
	STATUS current
	DESCRIPTION
        "
        Client Counter Error :This OID 
        when set indicates the downstream 
        timer counter value is invalid
         on Port
        "
	::= { pm1004CntdwTimCntEntry 3 }


pm1004CntdwTimCntOverloadPortn OBJECT-TYPE
	SYNTAX  EkiOnOff
	MAX-ACCESS read-only
	STATUS current
	DESCRIPTION
        "
        Client Counter Overload :This
         OID when set indicates a downstream 
        timer counter overload on Port
        "
	::= { pm1004CntdwTimCntEntry 4 }


--- *********************************************************
---     TABLE for the pm1004CntdfrmB1ErrCnt articles
--- *********************************************************

pm1004CntdfrmB1ErrCntTable OBJECT-TYPE
	SYNTAX  SEQUENCE OF Pm1004CntdfrmB1ErrCntEntry
	MAX-ACCESS not-accessible
	STATUS current
	DESCRIPTION
        "
        List of pm1004CntdfrmB1ErrCnt
         Article
        "
	::= { pm1004CntLine 152 }


pm1004CntdfrmB1ErrCntEntry OBJECT-TYPE
	SYNTAX Pm1004CntdfrmB1ErrCntEntry
	MAX-ACCESS not-accessible
	STATUS current
	DESCRIPTION
        "
        Row definition for the pm1004CntdfrmB1ErrCnt 
        table
        "
	INDEX   { pm1004CntdfrmB1ErrCntIndex }
	::= { pm1004CntdfrmB1ErrCntTable 1 }


Pm1004CntdfrmB1ErrCntEntry ::=
	SEQUENCE {
	pm1004CntdfrmB1ErrCntIndex
		INTEGER,
	pm1004CntdfrmB1ErrCntValuePortn
		Counter32,
	pm1004CntdfrmB1ErrCntErrorPortn
		EkiOnOff,
	pm1004CntdfrmB1ErrCntOverloadPortn
		EkiOnOff
	}


pm1004CntdfrmB1ErrCntIndex OBJECT-TYPE
	SYNTAX  INTEGER(0..128)
	MAX-ACCESS  read-only
	STATUS current
	DESCRIPTION
        "
        Index definition for the pm1004CntdfrmB1ErrCnt 
        table
        "
	::= { pm1004CntdfrmB1ErrCntEntry 1 }


pm1004CntdfrmB1ErrCntValuePortn OBJECT-TYPE
	SYNTAX  Counter32
	MAX-ACCESS read-only
	STATUS current
	DESCRIPTION
        "
        Line Input SM-BIP8 Errors :This 
        counter is incremented each time 
        a SM BIP error is detected on the 
        Deframer input stream.  <Help>
          This counter gives the number 
        of SM-BIP8 errors on the line por
        t
        "
	::= { pm1004CntdfrmB1ErrCntEntry 2 }


pm1004CntdfrmB1ErrCntErrorPortn OBJECT-TYPE
	SYNTAX  EkiOnOff
	MAX-ACCESS read-only
	STATUS current
	DESCRIPTION
        "
        Line Counter Error :This OID when 
        set indicates the SM BIP error
         counter value is invalid on Por
        t
        "
	::= { pm1004CntdfrmB1ErrCntEntry 3 }


pm1004CntdfrmB1ErrCntOverloadPortn OBJECT-TYPE
	SYNTAX  EkiOnOff
	MAX-ACCESS read-only
	STATUS current
	DESCRIPTION
        "
        Line Counter Overload :This OID 
        when set indicates a SM BIP error 
        counter overload on Port
        "
	::= { pm1004CntdfrmB1ErrCntEntry 4 }


--- *********************************************************
---     TABLE for the pm1004CntdfrmTimCnt articles
--- *********************************************************

pm1004CntdfrmTimCntTable OBJECT-TYPE
	SYNTAX  SEQUENCE OF Pm1004CntdfrmTimCntEntry
	MAX-ACCESS not-accessible
	STATUS current
	DESCRIPTION
        "
        List of pm1004CntdfrmTimCnt Articl
        e
        "
	::= { pm1004CntLine 153 }


pm1004CntdfrmTimCntEntry OBJECT-TYPE
	SYNTAX Pm1004CntdfrmTimCntEntry
	MAX-ACCESS not-accessible
	STATUS current
	DESCRIPTION
        "
        Row definition for the pm1004CntdfrmTimCnt 
        table
        "
	INDEX   { pm1004CntdfrmTimCntIndex }
	::= { pm1004CntdfrmTimCntTable 1 }


Pm1004CntdfrmTimCntEntry ::=
	SEQUENCE {
	pm1004CntdfrmTimCntIndex
		INTEGER,
	pm1004CntdfrmTimCntValuePortn
		Counter32,
	pm1004CntdfrmTimCntErrorPortn
		EkiOnOff,
	pm1004CntdfrmTimCntOverloadPortn
		EkiOnOff
	}


pm1004CntdfrmTimCntIndex OBJECT-TYPE
	SYNTAX  INTEGER(0..128)
	MAX-ACCESS  read-only
	STATUS current
	DESCRIPTION
        "
        Index definition for the pm1004CntdfrmTimCnt 
        table
        "
	::= { pm1004CntdfrmTimCntEntry 1 }


pm1004CntdfrmTimCntValuePortn OBJECT-TYPE
	SYNTAX  Counter32
	MAX-ACCESS read-only
	STATUS current
	DESCRIPTION
        "
        Line Timer Counter :This is the 
        timing counter dedicated to the 
        downstream deframer counters. It 
        is incremented every 125 us.
        "
	::= { pm1004CntdfrmTimCntEntry 2 }


pm1004CntdfrmTimCntErrorPortn OBJECT-TYPE
	SYNTAX  EkiOnOff
	MAX-ACCESS read-only
	STATUS current
	DESCRIPTION
        "
        Line Counter Error :This OID when 
        set indicates the deframer timer 
        counter value is invalid on Por
        t
        "
	::= { pm1004CntdfrmTimCntEntry 3 }


pm1004CntdfrmTimCntOverloadPortn OBJECT-TYPE
	SYNTAX  EkiOnOff
	MAX-ACCESS read-only
	STATUS current
	DESCRIPTION
        "
        Line Counter Overload :This OID 
        when set indicates a deframer timer 
        counter overload on Port
        "
	::= { pm1004CntdfrmTimCntEntry 4 }


--- *********************************************************
---     TABLE for the pm1004CntdfrmPrimLineErrCnt articles
--- *********************************************************

pm1004CntdfrmPrimLineErrCntTable OBJECT-TYPE
	SYNTAX  SEQUENCE OF Pm1004CntdfrmPrimLineErrCntEntry
	MAX-ACCESS not-accessible
	STATUS current
	DESCRIPTION
        "
        List of pm1004CntdfrmPrimLineErrCnt 
        Article
        "
	::= { pm1004CntLine 154 }


pm1004CntdfrmPrimLineErrCntEntry OBJECT-TYPE
	SYNTAX Pm1004CntdfrmPrimLineErrCntEntry
	MAX-ACCESS not-accessible
	STATUS current
	DESCRIPTION
        "
        Row definition for the pm1004CntdfrmPrimLineErrCnt 
        table
        "
	INDEX   { pm1004CntdfrmPrimLineErrCntIndex }
	::= { pm1004CntdfrmPrimLineErrCntTable 1 }


Pm1004CntdfrmPrimLineErrCntEntry ::=
	SEQUENCE {
	pm1004CntdfrmPrimLineErrCntIndex
		INTEGER,
	pm1004CntdfrmPrimLineErrCntValuePortn
		Counter32,
	pm1004CntdfrmPrimLineErrCntErrorPortn
		EkiOnOff,
	pm1004CntdfrmPrimLineErrCntOverloadPortn
		EkiOnOff
	}


pm1004CntdfrmPrimLineErrCntIndex OBJECT-TYPE
	SYNTAX  INTEGER(0..128)
	MAX-ACCESS  read-only
	STATUS current
	DESCRIPTION
        "
        Index definition for the pm1004CntdfrmPrimLineErrCnt 
        table
        "
	::= { pm1004CntdfrmPrimLineErrCntEntry 1 }


pm1004CntdfrmPrimLineErrCntValuePortn OBJECT-TYPE
	SYNTAX  Counter32
	MAX-ACCESS read-only
	STATUS current
	DESCRIPTION
        "
        Line Input FEC Corrected Errors 
        :This counter is incremented each 
        time the FEC is correcting an error 
        on the line input stream.  <Help> 
         This counter gives the number
         of errors corrected by the FEC 
        on the line port
        "
	::= { pm1004CntdfrmPrimLineErrCntEntry 2 }


pm1004CntdfrmPrimLineErrCntErrorPortn OBJECT-TYPE
	SYNTAX  EkiOnOff
	MAX-ACCESS read-only
	STATUS current
	DESCRIPTION
        "
        FEC Counter Error :This bit when 
        set indicates the FEC corrected 
        errors counter value is invalid 
        on Line
        "
	::= { pm1004CntdfrmPrimLineErrCntEntry 3 }


pm1004CntdfrmPrimLineErrCntOverloadPortn OBJECT-TYPE
	SYNTAX  EkiOnOff
	MAX-ACCESS read-only
	STATUS current
	DESCRIPTION
        "
        FEC Counter Overload :This bit 
        when set indicates a FEC corrected 
        errors counter overload on Lin
        e
        "
	::= { pm1004CntdfrmPrimLineErrCntEntry 4 }


pm1004CntCountersReset  OBJECT-TYPE
	SYNTAX EkiOnOff
	MAX-ACCESS read-write
	STATUS current
	DESCRIPTION
	"Counters Reset:This OID resets and restarts all the counters"
	::= { pm1004counters  259 }

pm1004CntCountersStop  OBJECT-TYPE
	SYNTAX EkiOnOff
	MAX-ACCESS read-write
	STATUS current
	DESCRIPTION
	"Counters stop:This OID stops all the counters"
	::= { pm1004counters 260 }






--- *****************************************************
--- $$$$$$$$$$$$$$$$$$$$$$$$$$$$$$$$$$$$$$$$$$$$$$$$$$$$$
---     J0
--- $$$$$$$$$$$$$$$$$$$$$$$$$$$$$$$$$$$$$$$$$$$$$$$$$$$$$
--- *****************************************************








--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm1004Mesrsynth0 OBJECT-TYPE
	  SYNTAX EkiMeasureType
	  MAX-ACCESS read-only
	  STATUS deprecated
	  DESCRIPTION
        "
        Not Used :This OID gives the unit 
        used on AUX1 measurement of XFP#1 
         (Unit = )
        "
	  ::= { pm1004MesrOther 0 }



pm1004Mesrsynth1 OBJECT-TYPE
	  SYNTAX EkiMeasureType
	  MAX-ACCESS read-only
	  STATUS deprecated
	  DESCRIPTION
        "
        Not Used :This OID gives the unit 
        used on AUX2 measurement of XFP#1 
         (Unit = )
        "
	  ::= { pm1004MesrOther 1 }



--- *********************************************************
---     TABLE for the pm1004MesrtempMeas articles
--- *********************************************************

pm1004MesrtempMeasTable OBJECT-TYPE
	SYNTAX  SEQUENCE OF Pm1004MesrtempMeasEntry
	MAX-ACCESS not-accessible
	STATUS current
	DESCRIPTION
        "
        List of pm1004MesrtempMeas Articl
        e
        "
	::= { pm1004MesrClient 16 }


pm1004MesrtempMeasEntry OBJECT-TYPE
	SYNTAX Pm1004MesrtempMeasEntry
	MAX-ACCESS not-accessible
	STATUS current
	DESCRIPTION
        "
        Row definition for the pm1004MesrtempMeas 
        table
        "
	INDEX   { pm1004MesrtempMeasIndex }
	::= { pm1004MesrtempMeasTable 1 }


Pm1004MesrtempMeasEntry ::=
	SEQUENCE {
	pm1004MesrtempMeasIndex
		INTEGER,
	pm1004MesrtempMeasPortn
		INTEGER 
	}


pm1004MesrtempMeasIndex OBJECT-TYPE
	SYNTAX  INTEGER(0..128)
	MAX-ACCESS  read-only
	STATUS current
	DESCRIPTION
        "
        Index definition for the pm1004MesrtempMeas 
        table
        "
	::= { pm1004MesrtempMeasEntry 1 }


pm1004MesrtempMeasPortn OBJECT-TYPE
	SYNTAX  INTEGER (0..65535)
	MAX-ACCESS read-only
	STATUS current
	DESCRIPTION
        "
        Client SFP Temperature :This OID 
        gives the temperature value of
         the SFP plugged in port, read
         from the DDM (Digital Diagnostic 
        Monitoring) (Temperature = AV/256) 
        (Unit = C)  <Help>  This measure 
        gives the temperature of the client 
        transceiver
        "
	::= { pm1004MesrtempMeasEntry 2 }


--- *********************************************************
---     TABLE for the pm1004MesrvoltMeas articles
--- *********************************************************

pm1004MesrvoltMeasTable OBJECT-TYPE
	SYNTAX  SEQUENCE OF Pm1004MesrvoltMeasEntry
	MAX-ACCESS not-accessible
	STATUS current
	DESCRIPTION
        "
        List of pm1004MesrvoltMeas Articl
        e
        "
	::= { pm1004MesrClient 24 }


pm1004MesrvoltMeasEntry OBJECT-TYPE
	SYNTAX Pm1004MesrvoltMeasEntry
	MAX-ACCESS not-accessible
	STATUS current
	DESCRIPTION
        "
        Row definition for the pm1004MesrvoltMeas 
        table
        "
	INDEX   { pm1004MesrvoltMeasIndex }
	::= { pm1004MesrvoltMeasTable 1 }


Pm1004MesrvoltMeasEntry ::=
	SEQUENCE {
	pm1004MesrvoltMeasIndex
		INTEGER,
	pm1004MesrvoltMeasPortn
		INTEGER 
	}


pm1004MesrvoltMeasIndex OBJECT-TYPE
	SYNTAX  INTEGER(0..128)
	MAX-ACCESS  read-only
	STATUS current
	DESCRIPTION
        "
        Index definition for the pm1004MesrvoltMeas 
        table
        "
	::= { pm1004MesrvoltMeasEntry 1 }


pm1004MesrvoltMeasPortn OBJECT-TYPE
	SYNTAX  INTEGER (0..65535)
	MAX-ACCESS read-only
	STATUS current
	DESCRIPTION
        "
        Client SFP Power Supply :This
         OID gives the 3V3 voltage value 
        of the SFP plugged into port, read 
        from the DDM (Digital Diagnostic 
        Monitoring) (Voltage = AV/10000) 
        (Unit = V)  <Help>  This measure 
        gives the 3V3 voltage of the client 
        transceiver
        "
	::= { pm1004MesrvoltMeasEntry 2 }


--- *********************************************************
---     TABLE for the pm1004MesrbiasMeas articles
--- *********************************************************

pm1004MesrbiasMeasTable OBJECT-TYPE
	SYNTAX  SEQUENCE OF Pm1004MesrbiasMeasEntry
	MAX-ACCESS not-accessible
	STATUS current
	DESCRIPTION
        "
        List of pm1004MesrbiasMeas Articl
        e
        "
	::= { pm1004MesrClient 32 }


pm1004MesrbiasMeasEntry OBJECT-TYPE
	SYNTAX Pm1004MesrbiasMeasEntry
	MAX-ACCESS not-accessible
	STATUS current
	DESCRIPTION
        "
        Row definition for the pm1004MesrbiasMeas 
        table
        "
	INDEX   { pm1004MesrbiasMeasIndex }
	::= { pm1004MesrbiasMeasTable 1 }


Pm1004MesrbiasMeasEntry ::=
	SEQUENCE {
	pm1004MesrbiasMeasIndex
		INTEGER,
	pm1004MesrbiasMeasPortn
		INTEGER 
	}


pm1004MesrbiasMeasIndex OBJECT-TYPE
	SYNTAX  INTEGER(0..128)
	MAX-ACCESS  read-only
	STATUS current
	DESCRIPTION
        "
        Index definition for the pm1004MesrbiasMeas 
        table
        "
	::= { pm1004MesrbiasMeasEntry 1 }


pm1004MesrbiasMeasPortn OBJECT-TYPE
	SYNTAX  INTEGER (0..65535)
	MAX-ACCESS read-only
	STATUS current
	DESCRIPTION
        "
        Client SFP Laser Bias :This OID 
        gives the bias value of the SFP 
        plugged into port, read from the 
        DDM (Digital Diagnostic Monitoring) 
        (Bias = AV/500)  (Unit = mA)  <Help> 
         This measure gives the bias of 
        the client transceiver
        "
	::= { pm1004MesrbiasMeasEntry 2 }


--- *********************************************************
---     TABLE for the pm1004MesrtxpwrMeas articles
--- *********************************************************

pm1004MesrtxpwrMeasTable OBJECT-TYPE
	SYNTAX  SEQUENCE OF Pm1004MesrtxpwrMeasEntry
	MAX-ACCESS not-accessible
	STATUS current
	DESCRIPTION
        "
        List of pm1004MesrtxpwrMeas Articl
        e
        "
	::= { pm1004MesrClient 40 }


pm1004MesrtxpwrMeasEntry OBJECT-TYPE
	SYNTAX Pm1004MesrtxpwrMeasEntry
	MAX-ACCESS not-accessible
	STATUS current
	DESCRIPTION
        "
        Row definition for the pm1004MesrtxpwrMeas 
        table
        "
	INDEX   { pm1004MesrtxpwrMeasIndex }
	::= { pm1004MesrtxpwrMeasTable 1 }


Pm1004MesrtxpwrMeasEntry ::=
	SEQUENCE {
	pm1004MesrtxpwrMeasIndex
		INTEGER,
	pm1004MesrtxpwrMeasPortn
		INTEGER 
	}


pm1004MesrtxpwrMeasIndex OBJECT-TYPE
	SYNTAX  INTEGER(0..128)
	MAX-ACCESS  read-only
	STATUS current
	DESCRIPTION
        "
        Index definition for the pm1004MesrtxpwrMeas 
        table
        "
	::= { pm1004MesrtxpwrMeasEntry 1 }


pm1004MesrtxpwrMeasPortn OBJECT-TYPE
	SYNTAX  INTEGER (0..65535)
	MAX-ACCESS read-only
	STATUS current
	DESCRIPTION
        "
        Client SFP Tx Power :This OID
         gives the transmit power value 
        of the SFP plugged into port, read 
        from the DDM (Digital Diagnostic 
        Monitoring) (Power = 10*log(AV)-40) 
        (Unit = dBm)  <Help>  This measure 
        gives the Tx optical power of the 
        client transceiver
        "
	::= { pm1004MesrtxpwrMeasEntry 2 }


--- *********************************************************
---     TABLE for the pm1004MesrrxpwrMeas articles
--- *********************************************************

pm1004MesrrxpwrMeasTable OBJECT-TYPE
	SYNTAX  SEQUENCE OF Pm1004MesrrxpwrMeasEntry
	MAX-ACCESS not-accessible
	STATUS current
	DESCRIPTION
        "
        List of pm1004MesrrxpwrMeas Articl
        e
        "
	::= { pm1004MesrClient 48 }


pm1004MesrrxpwrMeasEntry OBJECT-TYPE
	SYNTAX Pm1004MesrrxpwrMeasEntry
	MAX-ACCESS not-accessible
	STATUS current
	DESCRIPTION
        "
        Row definition for the pm1004MesrrxpwrMeas 
        table
        "
	INDEX   { pm1004MesrrxpwrMeasIndex }
	::= { pm1004MesrrxpwrMeasTable 1 }


Pm1004MesrrxpwrMeasEntry ::=
	SEQUENCE {
	pm1004MesrrxpwrMeasIndex
		INTEGER,
	pm1004MesrrxpwrMeasPortn
		INTEGER 
	}


pm1004MesrrxpwrMeasIndex OBJECT-TYPE
	SYNTAX  INTEGER(0..128)
	MAX-ACCESS  read-only
	STATUS current
	DESCRIPTION
        "
        Index definition for the pm1004MesrrxpwrMeas 
        table
        "
	::= { pm1004MesrrxpwrMeasEntry 1 }


pm1004MesrrxpwrMeasPortn OBJECT-TYPE
	SYNTAX  INTEGER (0..65535)
	MAX-ACCESS read-only
	STATUS current
	DESCRIPTION
        "
        Client SFP Rx Power :This OID
         gives the receive power value
         of the SFP plugged into port,
         read in the DDM (Digital Diagnostic 
        Monitoring) (Power = 10*log(AV)-40) 
        (Unit = dBm)  <Help>  This measure 
        gives the Rx optical power of the 
        client transceiver
        "
	::= { pm1004MesrrxpwrMeasEntry 2 }


--- *********************************************************
---     TABLE for the pm1004Mesrxfp1LxModTempMeas articles
--- *********************************************************

pm1004Mesrxfp1LxModTempMeasTable OBJECT-TYPE
	SYNTAX  SEQUENCE OF Pm1004Mesrxfp1LxModTempMeasEntry
	MAX-ACCESS not-accessible
	STATUS current
	DESCRIPTION
        "
        List of pm1004Mesrxfp1LxModTempMeas 
        Article
        "
	::= { pm1004MesrLine 208 }


pm1004Mesrxfp1LxModTempMeasEntry OBJECT-TYPE
	SYNTAX Pm1004Mesrxfp1LxModTempMeasEntry
	MAX-ACCESS not-accessible
	STATUS current
	DESCRIPTION
        "
        Row definition for the pm1004Mesrxfp1LxModTempMeas 
        table
        "
	INDEX   { pm1004Mesrxfp1LxModTempMeasIndex }
	::= { pm1004Mesrxfp1LxModTempMeasTable 1 }


Pm1004Mesrxfp1LxModTempMeasEntry ::=
	SEQUENCE {
	pm1004Mesrxfp1LxModTempMeasIndex
		INTEGER,
	pm1004Mesrxfp1LxModTempMeasPortn
		INTEGER 
	}


pm1004Mesrxfp1LxModTempMeasIndex OBJECT-TYPE
	SYNTAX  INTEGER(0..128)
	MAX-ACCESS  read-only
	STATUS current
	DESCRIPTION
        "
        Index definition for the pm1004Mesrxfp1LxModTempMeas 
        table
        "
	::= { pm1004Mesrxfp1LxModTempMeasEntry 1 }


pm1004Mesrxfp1LxModTempMeasPortn OBJECT-TYPE
	SYNTAX  INTEGER (0..65535)
	MAX-ACCESS read-only
	STATUS current
	DESCRIPTION
        "
        Line Optical Module Temperature 
        :This OID gives the temperature 
        of the XFP or OTX plugged in line, 
        read from the DDM (Digital Diagnostic 
        Monitoring) (Temperature = AV/256) 
        (Unit = C)  <Help>  This measure 
        gives the temperature of the line 
        transceiver
        "
	::= { pm1004Mesrxfp1LxModTempMeasEntry 2 }


--- *********************************************************
---     TABLE for the pm1004Mesrxfp1Reserved articles
--- *********************************************************

pm1004Mesrxfp1ReservedTable OBJECT-TYPE
	SYNTAX  SEQUENCE OF Pm1004Mesrxfp1ReservedEntry
	MAX-ACCESS not-accessible
	STATUS deprecated
	DESCRIPTION
        "
        List of pm1004Mesrxfp1Reserved 
        Article
        "
	::= { pm1004MesrLine 209 }


pm1004Mesrxfp1ReservedEntry OBJECT-TYPE
	SYNTAX Pm1004Mesrxfp1ReservedEntry
	MAX-ACCESS not-accessible
	STATUS deprecated
	DESCRIPTION
        "
        Row definition for the pm1004Mesrxfp1Reserved 
        table
        "
	INDEX   { pm1004Mesrxfp1ReservedIndex }
	::= { pm1004Mesrxfp1ReservedTable 1 }


Pm1004Mesrxfp1ReservedEntry ::=
	SEQUENCE {
	pm1004Mesrxfp1ReservedIndex
		INTEGER,
	pm1004Mesrxfp1ReservedPortn
		INTEGER 
	}


pm1004Mesrxfp1ReservedIndex OBJECT-TYPE
	SYNTAX  INTEGER(0..128)
	MAX-ACCESS  read-only
	STATUS deprecated
	DESCRIPTION
        "
        Index definition for the pm1004Mesrxfp1Reserved 
        table
        "
	::= { pm1004Mesrxfp1ReservedEntry 1 }


pm1004Mesrxfp1ReservedPortn OBJECT-TYPE
	SYNTAX  INTEGER (0..65535)
	MAX-ACCESS read-only
	STATUS deprecated
	DESCRIPTION
        "
        Not Used :Reserved
        "
	::= { pm1004Mesrxfp1ReservedEntry 2 }


--- *********************************************************
---     TABLE for the pm1004Mesrxfp1LoBiasCurrentMeas articles
--- *********************************************************

pm1004Mesrxfp1LoBiasCurrentMeasTable OBJECT-TYPE
	SYNTAX  SEQUENCE OF Pm1004Mesrxfp1LoBiasCurrentMeasEntry
	MAX-ACCESS not-accessible
	STATUS current
	DESCRIPTION
        "
        List of pm1004Mesrxfp1LoBiasCurrentMeas 
        Article
        "
	::= { pm1004MesrLine 210 }


pm1004Mesrxfp1LoBiasCurrentMeasEntry OBJECT-TYPE
	SYNTAX Pm1004Mesrxfp1LoBiasCurrentMeasEntry
	MAX-ACCESS not-accessible
	STATUS current
	DESCRIPTION
        "
        Row definition for the pm1004Mesrxfp1LoBiasCurrentMeas 
        table
        "
	INDEX   { pm1004Mesrxfp1LoBiasCurrentMeasIndex }
	::= { pm1004Mesrxfp1LoBiasCurrentMeasTable 1 }


Pm1004Mesrxfp1LoBiasCurrentMeasEntry ::=
	SEQUENCE {
	pm1004Mesrxfp1LoBiasCurrentMeasIndex
		INTEGER,
	pm1004Mesrxfp1LoBiasCurrentMeasPortn
		INTEGER 
	}


pm1004Mesrxfp1LoBiasCurrentMeasIndex OBJECT-TYPE
	SYNTAX  INTEGER(0..128)
	MAX-ACCESS  read-only
	STATUS current
	DESCRIPTION
        "
        Index definition for the pm1004Mesrxfp1LoBiasCurrentMeas 
        table
        "
	::= { pm1004Mesrxfp1LoBiasCurrentMeasEntry 1 }


pm1004Mesrxfp1LoBiasCurrentMeasPortn OBJECT-TYPE
	SYNTAX  INTEGER (0..65535)
	MAX-ACCESS read-only
	STATUS current
	DESCRIPTION
        "
        Line Optical Module Laser Bias 
        :This OID gives the bias value
         of the XFP or OTX plugged in line 
        , read from the DDM (Digital Diagnostic 
        Monitoring) (Bias = AV/500) (Unit 
        = mA)  <Help>  This measure gives 
        the bias of the line transceive
        r
        "
	::= { pm1004Mesrxfp1LoBiasCurrentMeasEntry 2 }


--- *********************************************************
---     TABLE for the pm1004Mesrxfp1LoTxPowerMeas articles
--- *********************************************************

pm1004Mesrxfp1LoTxPowerMeasTable OBJECT-TYPE
	SYNTAX  SEQUENCE OF Pm1004Mesrxfp1LoTxPowerMeasEntry
	MAX-ACCESS not-accessible
	STATUS current
	DESCRIPTION
        "
        List of pm1004Mesrxfp1LoTxPowerMeas 
        Article
        "
	::= { pm1004MesrLine 211 }


pm1004Mesrxfp1LoTxPowerMeasEntry OBJECT-TYPE
	SYNTAX Pm1004Mesrxfp1LoTxPowerMeasEntry
	MAX-ACCESS not-accessible
	STATUS current
	DESCRIPTION
        "
        Row definition for the pm1004Mesrxfp1LoTxPowerMeas 
        table
        "
	INDEX   { pm1004Mesrxfp1LoTxPowerMeasIndex }
	::= { pm1004Mesrxfp1LoTxPowerMeasTable 1 }


Pm1004Mesrxfp1LoTxPowerMeasEntry ::=
	SEQUENCE {
	pm1004Mesrxfp1LoTxPowerMeasIndex
		INTEGER,
	pm1004Mesrxfp1LoTxPowerMeasPortn
		INTEGER 
	}


pm1004Mesrxfp1LoTxPowerMeasIndex OBJECT-TYPE
	SYNTAX  INTEGER(0..128)
	MAX-ACCESS  read-only
	STATUS current
	DESCRIPTION
        "
        Index definition for the pm1004Mesrxfp1LoTxPowerMeas 
        table
        "
	::= { pm1004Mesrxfp1LoTxPowerMeasEntry 1 }


pm1004Mesrxfp1LoTxPowerMeasPortn OBJECT-TYPE
	SYNTAX  INTEGER (0..65535)
	MAX-ACCESS read-only
	STATUS current
	DESCRIPTION
        "
        Line Optical Module Tx Power :This 
        OID gives the transmit power value 
        of the XFP or OTX plugged in line 
        , read from the DDM (Digital  
         Diagnostic Monitoring) (Power
         = 10*log(AV)-40) (Unit = dBm)
          <Help>  This measure gives the 
        Tx optical power of the line transceive
        r
        "
	::= { pm1004Mesrxfp1LoTxPowerMeasEntry 2 }


--- *********************************************************
---     TABLE for the pm1004Mesrxfp1LiRxPowerMeas articles
--- *********************************************************

pm1004Mesrxfp1LiRxPowerMeasTable OBJECT-TYPE
	SYNTAX  SEQUENCE OF Pm1004Mesrxfp1LiRxPowerMeasEntry
	MAX-ACCESS not-accessible
	STATUS current
	DESCRIPTION
        "
        List of pm1004Mesrxfp1LiRxPowerMeas 
        Article
        "
	::= { pm1004MesrLine 212 }


pm1004Mesrxfp1LiRxPowerMeasEntry OBJECT-TYPE
	SYNTAX Pm1004Mesrxfp1LiRxPowerMeasEntry
	MAX-ACCESS not-accessible
	STATUS current
	DESCRIPTION
        "
        Row definition for the pm1004Mesrxfp1LiRxPowerMeas 
        table
        "
	INDEX   { pm1004Mesrxfp1LiRxPowerMeasIndex }
	::= { pm1004Mesrxfp1LiRxPowerMeasTable 1 }


Pm1004Mesrxfp1LiRxPowerMeasEntry ::=
	SEQUENCE {
	pm1004Mesrxfp1LiRxPowerMeasIndex
		INTEGER,
	pm1004Mesrxfp1LiRxPowerMeasPortn
		INTEGER 
	}


pm1004Mesrxfp1LiRxPowerMeasIndex OBJECT-TYPE
	SYNTAX  INTEGER(0..128)
	MAX-ACCESS  read-only
	STATUS current
	DESCRIPTION
        "
        Index definition for the pm1004Mesrxfp1LiRxPowerMeas 
        table
        "
	::= { pm1004Mesrxfp1LiRxPowerMeasEntry 1 }


pm1004Mesrxfp1LiRxPowerMeasPortn OBJECT-TYPE
	SYNTAX  INTEGER (0..65535)
	MAX-ACCESS read-only
	STATUS current
	DESCRIPTION
        "
        Line Optical Module Rx Power :This 
        OID gives the receive power value 
        of the XFP or OTX plugged in line 
        , read from the DDM (Digital Diagnostic 
        Monitoring) (Power = 10*log(AV)-40) 
        (Unit = dBm)  <Help>  This measure 
        gives the Rx optical power of the 
        line transceiver
        "
	::= { pm1004Mesrxfp1LiRxPowerMeasEntry 2 }


--- *********************************************************
---     TABLE for the pm1004Mesrxfp1LxAux1Meas articles
--- *********************************************************

pm1004Mesrxfp1LxAux1MeasTable OBJECT-TYPE
	SYNTAX  SEQUENCE OF Pm1004Mesrxfp1LxAux1MeasEntry
	MAX-ACCESS not-accessible
	STATUS deprecated
	DESCRIPTION
        "
        List of pm1004Mesrxfp1LxAux1Meas 
        Article
        "
	::= { pm1004MesrLine 213 }


pm1004Mesrxfp1LxAux1MeasEntry OBJECT-TYPE
	SYNTAX Pm1004Mesrxfp1LxAux1MeasEntry
	MAX-ACCESS not-accessible
	STATUS deprecated
	DESCRIPTION
        "
        Row definition for the pm1004Mesrxfp1LxAux1Meas 
        table
        "
	INDEX   { pm1004Mesrxfp1LxAux1MeasIndex }
	::= { pm1004Mesrxfp1LxAux1MeasTable 1 }


Pm1004Mesrxfp1LxAux1MeasEntry ::=
	SEQUENCE {
	pm1004Mesrxfp1LxAux1MeasIndex
		INTEGER,
	pm1004Mesrxfp1LxAux1MeasPortn
		INTEGER 
	}


pm1004Mesrxfp1LxAux1MeasIndex OBJECT-TYPE
	SYNTAX  INTEGER(0..128)
	MAX-ACCESS  read-only
	STATUS deprecated
	DESCRIPTION
        "
        Index definition for the pm1004Mesrxfp1LxAux1Meas 
        table
        "
	::= { pm1004Mesrxfp1LxAux1MeasEntry 1 }


pm1004Mesrxfp1LxAux1MeasPortn OBJECT-TYPE
	SYNTAX  INTEGER (0..65535)
	MAX-ACCESS read-only
	STATUS deprecated
	DESCRIPTION
        "
        Not Used :This OID gives the receive 
        power value read in the DDM (Digital 
        Diagnostic Monitoring) of the XFP 
        or OTX plugged in line  (Unit = 
        ?)
        "
	::= { pm1004Mesrxfp1LxAux1MeasEntry 2 }


--- *********************************************************
---     TABLE for the pm1004Mesrxfp1LxAux2Meas articles
--- *********************************************************

pm1004Mesrxfp1LxAux2MeasTable OBJECT-TYPE
	SYNTAX  SEQUENCE OF Pm1004Mesrxfp1LxAux2MeasEntry
	MAX-ACCESS not-accessible
	STATUS deprecated
	DESCRIPTION
        "
        List of pm1004Mesrxfp1LxAux2Meas 
        Article
        "
	::= { pm1004MesrLine 214 }


pm1004Mesrxfp1LxAux2MeasEntry OBJECT-TYPE
	SYNTAX Pm1004Mesrxfp1LxAux2MeasEntry
	MAX-ACCESS not-accessible
	STATUS deprecated
	DESCRIPTION
        "
        Row definition for the pm1004Mesrxfp1LxAux2Meas 
        table
        "
	INDEX   { pm1004Mesrxfp1LxAux2MeasIndex }
	::= { pm1004Mesrxfp1LxAux2MeasTable 1 }


Pm1004Mesrxfp1LxAux2MeasEntry ::=
	SEQUENCE {
	pm1004Mesrxfp1LxAux2MeasIndex
		INTEGER,
	pm1004Mesrxfp1LxAux2MeasPortn
		INTEGER 
	}


pm1004Mesrxfp1LxAux2MeasIndex OBJECT-TYPE
	SYNTAX  INTEGER(0..128)
	MAX-ACCESS  read-only
	STATUS deprecated
	DESCRIPTION
        "
        Index definition for the pm1004Mesrxfp1LxAux2Meas 
        table
        "
	::= { pm1004Mesrxfp1LxAux2MeasEntry 1 }


pm1004Mesrxfp1LxAux2MeasPortn OBJECT-TYPE
	SYNTAX  INTEGER (0..65535)
	MAX-ACCESS read-only
	STATUS deprecated
	DESCRIPTION
        "
        Not Used :This OID gives the receive 
        power value read in the DDM (Digital 
        Diagnostic Monitoring) of the XFP 
        or OTX plugged in line  (Unit = 
        ?)
        "
	::= { pm1004Mesrxfp1LxAux2MeasEntry 2 }


--- *********************************************************
---     TABLE for the pm1004Mesrotx1Aging articles
--- *********************************************************

pm1004Mesrotx1AgingTable OBJECT-TYPE
	SYNTAX  SEQUENCE OF Pm1004Mesrotx1AgingEntry
	MAX-ACCESS not-accessible
	STATUS current
	DESCRIPTION
        "
        List of pm1004Mesrotx1Aging Articl
        e
        "
	::= { pm1004MesrLine 224 }


pm1004Mesrotx1AgingEntry OBJECT-TYPE
	SYNTAX Pm1004Mesrotx1AgingEntry
	MAX-ACCESS not-accessible
	STATUS current
	DESCRIPTION
        "
        Row definition for the pm1004Mesrotx1Aging 
        table
        "
	INDEX   { pm1004Mesrotx1AgingIndex }
	::= { pm1004Mesrotx1AgingTable 1 }


Pm1004Mesrotx1AgingEntry ::=
	SEQUENCE {
	pm1004Mesrotx1AgingIndex
		INTEGER,
	pm1004Mesrotx1AgingPortn
		INTEGER 
	}


pm1004Mesrotx1AgingIndex OBJECT-TYPE
	SYNTAX  INTEGER(0..128)
	MAX-ACCESS  read-only
	STATUS current
	DESCRIPTION
        "
        Index definition for the pm1004Mesrotx1Aging 
        table
        "
	::= { pm1004Mesrotx1AgingEntry 1 }


pm1004Mesrotx1AgingPortn OBJECT-TYPE
	SYNTAX  INTEGER (0..65535)
	MAX-ACCESS read-only
	STATUS current
	DESCRIPTION
        "
        Line OTX TLH Aging :This OID gives 
        the aging of the Line OTX TLH,
         read from the DDM (Digital Diagnostic 
        Monitoring)  (Aging = AV) (Unit 
        = %)  <Help>  This measure gives 
        the aging of the Line OTX TLH
        "
	::= { pm1004Mesrotx1AgingEntry 2 }


--- *********************************************************
---     TABLE for the pm1004Mesrotx1LaserTemperature articles
--- *********************************************************

pm1004Mesrotx1LaserTemperatureTable OBJECT-TYPE
	SYNTAX  SEQUENCE OF Pm1004Mesrotx1LaserTemperatureEntry
	MAX-ACCESS not-accessible
	STATUS deprecated
	DESCRIPTION
        "
        List of pm1004Mesrotx1LaserTemperature 
        Article
        "
	::= { pm1004MesrLine 225 }


pm1004Mesrotx1LaserTemperatureEntry OBJECT-TYPE
	SYNTAX Pm1004Mesrotx1LaserTemperatureEntry
	MAX-ACCESS not-accessible
	STATUS deprecated
	DESCRIPTION
        "
        Row definition for the pm1004Mesrotx1LaserTemperature 
        table
        "
	INDEX   { pm1004Mesrotx1LaserTemperatureIndex }
	::= { pm1004Mesrotx1LaserTemperatureTable 1 }


Pm1004Mesrotx1LaserTemperatureEntry ::=
	SEQUENCE {
	pm1004Mesrotx1LaserTemperatureIndex
		INTEGER,
	pm1004Mesrotx1LaserTemperaturePortn
		INTEGER 
	}


pm1004Mesrotx1LaserTemperatureIndex OBJECT-TYPE
	SYNTAX  INTEGER(0..128)
	MAX-ACCESS  read-only
	STATUS deprecated
	DESCRIPTION
        "
        Index definition for the pm1004Mesrotx1LaserTemperature 
        table
        "
	::= { pm1004Mesrotx1LaserTemperatureEntry 1 }


pm1004Mesrotx1LaserTemperaturePortn OBJECT-TYPE
	SYNTAX  INTEGER (0..65535)
	MAX-ACCESS read-only
	STATUS deprecated
	DESCRIPTION
        "
        Line OTX TLH Laser Temperature 
        :This OID gives the laser temperature 
        of the Line OTX TLH, read from
         the DDM (Digital Diagnostic Monitoring) 
        (Temperature = AV/256) (Unit =
         C)  <Help>  This measure gives 
        the laser temperature of the Line 
        OTX TLH
        "
	::= { pm1004Mesrotx1LaserTemperatureEntry 2 }


--- *********************************************************
---     TABLE for the pm1004Mesrotx1FreqDeviation articles
--- *********************************************************

pm1004Mesrotx1FreqDeviationTable OBJECT-TYPE
	SYNTAX  SEQUENCE OF Pm1004Mesrotx1FreqDeviationEntry
	MAX-ACCESS not-accessible
	STATUS current
	DESCRIPTION
        "
        List of pm1004Mesrotx1FreqDeviation 
        Article
        "
	::= { pm1004MesrLine 226 }


pm1004Mesrotx1FreqDeviationEntry OBJECT-TYPE
	SYNTAX Pm1004Mesrotx1FreqDeviationEntry
	MAX-ACCESS not-accessible
	STATUS current
	DESCRIPTION
        "
        Row definition for the pm1004Mesrotx1FreqDeviation 
        table
        "
	INDEX   { pm1004Mesrotx1FreqDeviationIndex }
	::= { pm1004Mesrotx1FreqDeviationTable 1 }


Pm1004Mesrotx1FreqDeviationEntry ::=
	SEQUENCE {
	pm1004Mesrotx1FreqDeviationIndex
		INTEGER,
	pm1004Mesrotx1FreqDeviationPortn
		INTEGER 
	}


pm1004Mesrotx1FreqDeviationIndex OBJECT-TYPE
	SYNTAX  INTEGER(0..128)
	MAX-ACCESS  read-only
	STATUS current
	DESCRIPTION
        "
        Index definition for the pm1004Mesrotx1FreqDeviation 
        table
        "
	::= { pm1004Mesrotx1FreqDeviationEntry 1 }


pm1004Mesrotx1FreqDeviationPortn OBJECT-TYPE
	SYNTAX  INTEGER (0..65535)
	MAX-ACCESS read-only
	STATUS current
	DESCRIPTION
        "
        Line OTX TLH Frequency Deviation 
        :This OID gives the frequency deviation 
        of the Line OTX TLH, read from
         the DDM (Digital Diagnostic Monitoring) 
         (Deviation = (AV-32768)*100) (Unit 
        = MHz)  <Help>  This measure gives 
        the frequency deviation of the
         Line OTX TLH
        "
	::= { pm1004Mesrotx1FreqDeviationEntry 2 }


--- *********************************************************
---     TABLE for the pm1004Mesrotx1LaserWvlength articles
--- *********************************************************

pm1004Mesrotx1LaserWvlengthTable OBJECT-TYPE
	SYNTAX  SEQUENCE OF Pm1004Mesrotx1LaserWvlengthEntry
	MAX-ACCESS not-accessible
	STATUS current
	DESCRIPTION
        "
        List of pm1004Mesrotx1LaserWvlength 
        Article
        "
	::= { pm1004MesrLine 227 }


pm1004Mesrotx1LaserWvlengthEntry OBJECT-TYPE
	SYNTAX Pm1004Mesrotx1LaserWvlengthEntry
	MAX-ACCESS not-accessible
	STATUS current
	DESCRIPTION
        "
        Row definition for the pm1004Mesrotx1LaserWvlength 
        table
        "
	INDEX   { pm1004Mesrotx1LaserWvlengthIndex }
	::= { pm1004Mesrotx1LaserWvlengthTable 1 }


Pm1004Mesrotx1LaserWvlengthEntry ::=
	SEQUENCE {
	pm1004Mesrotx1LaserWvlengthIndex
		INTEGER,
	pm1004Mesrotx1LaserWvlengthPortn
		INTEGER 
	}


pm1004Mesrotx1LaserWvlengthIndex OBJECT-TYPE
	SYNTAX  INTEGER(0..128)
	MAX-ACCESS  read-only
	STATUS current
	DESCRIPTION
        "
        Index definition for the pm1004Mesrotx1LaserWvlength 
        table
        "
	::= { pm1004Mesrotx1LaserWvlengthEntry 1 }


pm1004Mesrotx1LaserWvlengthPortn OBJECT-TYPE
	SYNTAX  INTEGER (0..65535)
	MAX-ACCESS read-only
	STATUS current
	DESCRIPTION
        "
        Line Optical Module Wavelength 
        :This OID gives the laser wavelength 
        of the Line OTX TLH, read from
         the DDM (Digital Diagnostic Monitoring) 
         (Wavelength=299792458/((193,100+(AV-32768 
        )*12,5)*10 3)) (Unit = nm)  <Help> 
         This measure gives the laser wavelength 
        of the Line OTX TLH
        "
	::= { pm1004Mesrotx1LaserWvlengthEntry 2 }







--- *****************************************************
--- $$$$$$$$$$$$$$$$$$$$$$$$$$$$$$$$$$$$$$$$$$$$$$$$$$$$$
---     PERFORMANCE
--- $$$$$$$$$$$$$$$$$$$$$$$$$$$$$$$$$$$$$$$$$$$$$$$$$$$$$
--- *****************************************************



--- *********************************************************
---     TABLE for the pm1004PerfUpCurrent15Cnt articles
--- *********************************************************

pm1004PerfUpCurrent15CntTable OBJECT-TYPE
	SYNTAX  SEQUENCE OF Pm1004PerfUpCurrent15CntEntry
	MAX-ACCESS not-accessible
	STATUS current
	DESCRIPTION
        "
        List of pm1004PerfUpCurrent15Cnt 
        Article
        "
	::= { pm1004MonClientPerformance 16 }


pm1004PerfUpCurrent15CntEntry OBJECT-TYPE
	SYNTAX Pm1004PerfUpCurrent15CntEntry
	MAX-ACCESS not-accessible
	STATUS current
	DESCRIPTION
        "
        Row definition for the pm1004PerfUpCurrent15Cnt 
        table
        "
	INDEX   { pm1004PerfUpCurrent15CntIndex }
	::= { pm1004PerfUpCurrent15CntTable 1 }


Pm1004PerfUpCurrent15CntEntry ::=
	SEQUENCE {
	pm1004PerfUpCurrent15CntIndex
		INTEGER,
	pm1004PerfUpCurrent15CntInvCvPortn
		EkiOnOff,
	pm1004PerfUpCurrent15CntCvValuePortn
		Unsigned32,
	pm1004PerfUpCurrent15CntInvEsPortn
		EkiOnOff,
	pm1004PerfUpCurrent15CntEsValuePortn
		Unsigned32,
	pm1004PerfUpCurrent15CntInvSesPortn
		EkiOnOff,
	pm1004PerfUpCurrent15CntSesValuePortn
		Unsigned32,
	pm1004PerfUpCurrent15CntInvSefsPortn
		EkiOnOff,
	pm1004PerfUpCurrent15CntSefsValuePortn
		Unsigned32,
	pm1004PerfUpCurrent15CntInvUasPortn
		EkiOnOff,
	pm1004PerfUpCurrent15CntUasValuePortn
		Unsigned32
	}


pm1004PerfUpCurrent15CntIndex OBJECT-TYPE
	SYNTAX  INTEGER(0..128)
	MAX-ACCESS  read-only
	STATUS current
	DESCRIPTION
        "
        Index definition for the pm1004PerfUpCurrent15Cnt 
        table
        "
	::= { pm1004PerfUpCurrent15CntEntry 1 }


pm1004PerfUpCurrent15CntInvCvPortn OBJECT-TYPE
	SYNTAX  EkiOnOff
	MAX-ACCESS read-only
	STATUS current
	DESCRIPTION
        "
        Current 15-min CV counter inv. 
        :This OID indicates that the current 
        15-min Coding Violation counter 
        is invalid
        "
	::= { pm1004PerfUpCurrent15CntEntry 2 }


pm1004PerfUpCurrent15CntCvValuePortn OBJECT-TYPE
	SYNTAX  Unsigned32
	MAX-ACCESS read-only
	STATUS current
	DESCRIPTION
        "
        Current 15-min CV counter :This 
        OID gives the current 15-min Coding 
        Violation counter value
        "
	::= { pm1004PerfUpCurrent15CntEntry 3 }


pm1004PerfUpCurrent15CntInvEsPortn OBJECT-TYPE
	SYNTAX  EkiOnOff
	MAX-ACCESS read-only
	STATUS current
	DESCRIPTION
        "
        Current 15-min ES counter inv. 
        :This OID indicates that the current 
        15-min Errored Second counter is 
        invalid
        "
	::= { pm1004PerfUpCurrent15CntEntry 4 }


pm1004PerfUpCurrent15CntEsValuePortn OBJECT-TYPE
	SYNTAX  Unsigned32
	MAX-ACCESS read-only
	STATUS current
	DESCRIPTION
        "
        Current 15-min ES counter :This 
        OID gives the current 15-min Errored 
        Second counter value
        "
	::= { pm1004PerfUpCurrent15CntEntry 5 }


pm1004PerfUpCurrent15CntInvSesPortn OBJECT-TYPE
	SYNTAX  EkiOnOff
	MAX-ACCESS read-only
	STATUS current
	DESCRIPTION
        "
        Current 15-min SES counter inv. 
        :This OID indicates that the current 
        15-min severely Errored Second
         counter is invalid
        "
	::= { pm1004PerfUpCurrent15CntEntry 6 }


pm1004PerfUpCurrent15CntSesValuePortn OBJECT-TYPE
	SYNTAX  Unsigned32
	MAX-ACCESS read-only
	STATUS current
	DESCRIPTION
        "
        Current 15-min SES counter :This 
        OID gives the current 15-min severely 
        Errored Second counter value
        "
	::= { pm1004PerfUpCurrent15CntEntry 7 }


pm1004PerfUpCurrent15CntInvSefsPortn OBJECT-TYPE
	SYNTAX  EkiOnOff
	MAX-ACCESS read-only
	STATUS current
	DESCRIPTION
        "
        Current 15-min SEFS counter inv. 
        :This OID indicates that the current 
        15-min severely Errored Framing 
        Second counter is invalid
        "
	::= { pm1004PerfUpCurrent15CntEntry 8 }


pm1004PerfUpCurrent15CntSefsValuePortn OBJECT-TYPE
	SYNTAX  Unsigned32
	MAX-ACCESS read-only
	STATUS current
	DESCRIPTION
        "
        Current 15-min SEFS counter :This 
        OID gives the current 15-min severely 
        Errored Framing Second counter
         value
        "
	::= { pm1004PerfUpCurrent15CntEntry 9 }


pm1004PerfUpCurrent15CntInvUasPortn OBJECT-TYPE
	SYNTAX  EkiOnOff
	MAX-ACCESS read-only
	STATUS current
	DESCRIPTION
        "
        Current 15-min UAS counter inv. 
        :This OID indicates that the current 
        15-min UnAvailable Second counter 
        is invalid
        "
	::= { pm1004PerfUpCurrent15CntEntry 10 }


pm1004PerfUpCurrent15CntUasValuePortn OBJECT-TYPE
	SYNTAX  Unsigned32
	MAX-ACCESS read-only
	STATUS current
	DESCRIPTION
        "
        Current 15-min UAS counter :This 
        OID gives the current 15-min UnAvailable 
        Second counter value
        "
	::= { pm1004PerfUpCurrent15CntEntry 11 }


--- *********************************************************
---     TABLE for the pm1004PerfUpPast15Cnt articles
--- *********************************************************

pm1004PerfUpPast15CntTable OBJECT-TYPE
	SYNTAX  SEQUENCE OF Pm1004PerfUpPast15CntEntry
	MAX-ACCESS not-accessible
	STATUS current
	DESCRIPTION
        "
        List of pm1004PerfUpPast15Cnt
         Article
        "
	::= { pm1004MonClientPerformance 24 }


pm1004PerfUpPast15CntEntry OBJECT-TYPE
	SYNTAX Pm1004PerfUpPast15CntEntry
	MAX-ACCESS not-accessible
	STATUS current
	DESCRIPTION
        "
        Row definition for the pm1004PerfUpPast15Cnt 
        table
        "
	INDEX   { pm1004PerfUpPast15CntIndex }
	::= { pm1004PerfUpPast15CntTable 1 }


Pm1004PerfUpPast15CntEntry ::=
	SEQUENCE {
	pm1004PerfUpPast15CntIndex
		INTEGER,
	pm1004PerfUpPast15CntInvCvPortn
		EkiOnOff,
	pm1004PerfUpPast15CntCvValuePortn
		Unsigned32,
	pm1004PerfUpPast15CntInvEsPortn
		EkiOnOff,
	pm1004PerfUpPast15CntEsValuePortn
		Unsigned32,
	pm1004PerfUpPast15CntInvSesPortn
		EkiOnOff,
	pm1004PerfUpPast15CntSesValuePortn
		Unsigned32,
	pm1004PerfUpPast15CntInvSefsPortn
		EkiOnOff,
	pm1004PerfUpPast15CntSefsValuePortn
		Unsigned32,
	pm1004PerfUpPast15CntInvUasPortn
		EkiOnOff,
	pm1004PerfUpPast15CntUasValuePortn
		Unsigned32
	}


pm1004PerfUpPast15CntIndex OBJECT-TYPE
	SYNTAX  INTEGER(0..128)
	MAX-ACCESS  read-only
	STATUS current
	DESCRIPTION
        "
        Index definition for the pm1004PerfUpPast15Cnt 
        table
        "
	::= { pm1004PerfUpPast15CntEntry 1 }


pm1004PerfUpPast15CntInvCvPortn OBJECT-TYPE
	SYNTAX  EkiOnOff
	MAX-ACCESS read-only
	STATUS current
	DESCRIPTION
        "
        Previous 15-min CV counter inv. 
        :This OID indicates that the previous 
        15-min Coding Violation counter 
        is invalid
        "
	::= { pm1004PerfUpPast15CntEntry 2 }


pm1004PerfUpPast15CntCvValuePortn OBJECT-TYPE
	SYNTAX  Unsigned32
	MAX-ACCESS read-only
	STATUS current
	DESCRIPTION
        "
        Previous 15-min CV counter :This 
        OID gives the previous 15-min Coding 
        Violation counter value
        "
	::= { pm1004PerfUpPast15CntEntry 3 }


pm1004PerfUpPast15CntInvEsPortn OBJECT-TYPE
	SYNTAX  EkiOnOff
	MAX-ACCESS read-only
	STATUS current
	DESCRIPTION
        "
        Previous 15-min ES counter inv. 
        :This OID indicates that the previous 
        15-min Errored Second counter is 
        invalid
        "
	::= { pm1004PerfUpPast15CntEntry 4 }


pm1004PerfUpPast15CntEsValuePortn OBJECT-TYPE
	SYNTAX  Unsigned32
	MAX-ACCESS read-only
	STATUS current
	DESCRIPTION
        "
        Previous 15-min ES counter :This 
        OID gives the previous 15-min Errored 
        Second counter value
        "
	::= { pm1004PerfUpPast15CntEntry 5 }


pm1004PerfUpPast15CntInvSesPortn OBJECT-TYPE
	SYNTAX  EkiOnOff
	MAX-ACCESS read-only
	STATUS current
	DESCRIPTION
        "
        Previous 15-min SES counter inv. 
        :This OID indicates that the previous 
        15-min severely Errored Second
         counter is invalid
        "
	::= { pm1004PerfUpPast15CntEntry 6 }


pm1004PerfUpPast15CntSesValuePortn OBJECT-TYPE
	SYNTAX  Unsigned32
	MAX-ACCESS read-only
	STATUS current
	DESCRIPTION
        "
        Previous 15-min SES counter :This 
        OID gives the previous 15-min severely 
        Errored Second counter value
        "
	::= { pm1004PerfUpPast15CntEntry 7 }


pm1004PerfUpPast15CntInvSefsPortn OBJECT-TYPE
	SYNTAX  EkiOnOff
	MAX-ACCESS read-only
	STATUS current
	DESCRIPTION
        "
        Previous 15-min SEFS counter inv. 
        :This OID indicates that the previous 
        15-min severely Errored Framing 
        Second counter is invalid
        "
	::= { pm1004PerfUpPast15CntEntry 8 }


pm1004PerfUpPast15CntSefsValuePortn OBJECT-TYPE
	SYNTAX  Unsigned32
	MAX-ACCESS read-only
	STATUS current
	DESCRIPTION
        "
        Previous 15-min SEFS counter :This 
        OID gives the previous 15-min severely 
        Errored Framing Second counter
         value
        "
	::= { pm1004PerfUpPast15CntEntry 9 }


pm1004PerfUpPast15CntInvUasPortn OBJECT-TYPE
	SYNTAX  EkiOnOff
	MAX-ACCESS read-only
	STATUS current
	DESCRIPTION
        "
        Previous 15-min UAS counter inv. 
        :This OID indicates that the previous 
        15-min UnAvailable Second counter 
        is invalid
        "
	::= { pm1004PerfUpPast15CntEntry 10 }


pm1004PerfUpPast15CntUasValuePortn OBJECT-TYPE
	SYNTAX  Unsigned32
	MAX-ACCESS read-only
	STATUS current
	DESCRIPTION
        "
        Previous 15-min UAS counter :This 
        OID gives the previous 15-min UnAvailable 
        Second counter value
        "
	::= { pm1004PerfUpPast15CntEntry 11 }


--- *********************************************************
---     TABLE for the pm1004PerfUpCurrent24Cnt articles
--- *********************************************************

pm1004PerfUpCurrent24CntTable OBJECT-TYPE
	SYNTAX  SEQUENCE OF Pm1004PerfUpCurrent24CntEntry
	MAX-ACCESS not-accessible
	STATUS current
	DESCRIPTION
        "
        List of pm1004PerfUpCurrent24Cnt 
        Article
        "
	::= { pm1004MonClientPerformance 32 }


pm1004PerfUpCurrent24CntEntry OBJECT-TYPE
	SYNTAX Pm1004PerfUpCurrent24CntEntry
	MAX-ACCESS not-accessible
	STATUS current
	DESCRIPTION
        "
        Row definition for the pm1004PerfUpCurrent24Cnt 
        table
        "
	INDEX   { pm1004PerfUpCurrent24CntIndex }
	::= { pm1004PerfUpCurrent24CntTable 1 }


Pm1004PerfUpCurrent24CntEntry ::=
	SEQUENCE {
	pm1004PerfUpCurrent24CntIndex
		INTEGER,
	pm1004PerfUpCurrent24CntInvCvPortn
		EkiOnOff,
	pm1004PerfUpCurrent24CntCvValuePortn
		Unsigned32,
	pm1004PerfUpCurrent24CntInvEsPortn
		EkiOnOff,
	pm1004PerfUpCurrent24CntEsValuePortn
		Unsigned32,
	pm1004PerfUpCurrent24CntInvSesPortn
		EkiOnOff,
	pm1004PerfUpCurrent24CntSesValuePortn
		Unsigned32,
	pm1004PerfUpCurrent24CntInvSefsPortn
		EkiOnOff,
	pm1004PerfUpCurrent24CntSefsValuePortn
		Unsigned32,
	pm1004PerfUpCurrent24CntInvUasPortn
		EkiOnOff,
	pm1004PerfUpCurrent24CntUasValuePortn
		Unsigned32
	}


pm1004PerfUpCurrent24CntIndex OBJECT-TYPE
	SYNTAX  INTEGER(0..128)
	MAX-ACCESS  read-only
	STATUS current
	DESCRIPTION
        "
        Index definition for the pm1004PerfUpCurrent24Cnt 
        table
        "
	::= { pm1004PerfUpCurrent24CntEntry 1 }


pm1004PerfUpCurrent24CntInvCvPortn OBJECT-TYPE
	SYNTAX  EkiOnOff
	MAX-ACCESS read-only
	STATUS current
	DESCRIPTION
        "
        Current 24-hours CV counter inv. 
        :This OID indicates that the current 
        24-hours Coding Violation counter 
        is invalid
        "
	::= { pm1004PerfUpCurrent24CntEntry 2 }


pm1004PerfUpCurrent24CntCvValuePortn OBJECT-TYPE
	SYNTAX  Unsigned32
	MAX-ACCESS read-only
	STATUS current
	DESCRIPTION
        "
        Current 24-hours CV counter :This 
        OID gives the current 24-hours
         Coding Violation counter valu
        e
        "
	::= { pm1004PerfUpCurrent24CntEntry 3 }


pm1004PerfUpCurrent24CntInvEsPortn OBJECT-TYPE
	SYNTAX  EkiOnOff
	MAX-ACCESS read-only
	STATUS current
	DESCRIPTION
        "
        Current 24-hours ES counter inv. 
        :This OID indicates that the current 
        24-hours Errored Second counter 
        is invalid
        "
	::= { pm1004PerfUpCurrent24CntEntry 4 }


pm1004PerfUpCurrent24CntEsValuePortn OBJECT-TYPE
	SYNTAX  Unsigned32
	MAX-ACCESS read-only
	STATUS current
	DESCRIPTION
        "
        Current 24-hours ES counter :This 
        OID gives the current 24-hours
         Errored Second counter value
        "
	::= { pm1004PerfUpCurrent24CntEntry 5 }


pm1004PerfUpCurrent24CntInvSesPortn OBJECT-TYPE
	SYNTAX  EkiOnOff
	MAX-ACCESS read-only
	STATUS current
	DESCRIPTION
        "
        Current 24-hours SES counter inv. 
        :This OID indicates that the current 
        24-hours severely Errored Second 
        counter is invalid
        "
	::= { pm1004PerfUpCurrent24CntEntry 6 }


pm1004PerfUpCurrent24CntSesValuePortn OBJECT-TYPE
	SYNTAX  Unsigned32
	MAX-ACCESS read-only
	STATUS current
	DESCRIPTION
        "
        Current 24-hours SES counter :This 
        OID gives the current 24-hours
         severely Errored Second counter 
        value
        "
	::= { pm1004PerfUpCurrent24CntEntry 7 }


pm1004PerfUpCurrent24CntInvSefsPortn OBJECT-TYPE
	SYNTAX  EkiOnOff
	MAX-ACCESS read-only
	STATUS current
	DESCRIPTION
        "
        Current 24-hours SEFS counter
         inv. :This OID indicates that
         the current 24-hours severely
         Errored Framing Second counter 
        is invalid
        "
	::= { pm1004PerfUpCurrent24CntEntry 8 }


pm1004PerfUpCurrent24CntSefsValuePortn OBJECT-TYPE
	SYNTAX  Unsigned32
	MAX-ACCESS read-only
	STATUS current
	DESCRIPTION
        "
        Current 24-hours SEFS counter
         :This OID gives the current 24-hours 
        severely Errored Framing Second 
        counter value
        "
	::= { pm1004PerfUpCurrent24CntEntry 9 }


pm1004PerfUpCurrent24CntInvUasPortn OBJECT-TYPE
	SYNTAX  EkiOnOff
	MAX-ACCESS read-only
	STATUS current
	DESCRIPTION
        "
        Current 24-hours UAS counter inv. 
        :This OID indicates that the current 
        24-hours UnAvailable Second counter 
        is invalid
        "
	::= { pm1004PerfUpCurrent24CntEntry 10 }


pm1004PerfUpCurrent24CntUasValuePortn OBJECT-TYPE
	SYNTAX  Unsigned32
	MAX-ACCESS read-only
	STATUS current
	DESCRIPTION
        "
        Current 24-hours UAS counter :This 
        OID gives the current 24-hours
         UnAvailable Second counter valu
        e
        "
	::= { pm1004PerfUpCurrent24CntEntry 11 }


--- *********************************************************
---     TABLE for the pm1004PerfUpPast24Cnt articles
--- *********************************************************

pm1004PerfUpPast24CntTable OBJECT-TYPE
	SYNTAX  SEQUENCE OF Pm1004PerfUpPast24CntEntry
	MAX-ACCESS not-accessible
	STATUS current
	DESCRIPTION
        "
        List of pm1004PerfUpPast24Cnt
         Article
        "
	::= { pm1004MonClientPerformance 40 }


pm1004PerfUpPast24CntEntry OBJECT-TYPE
	SYNTAX Pm1004PerfUpPast24CntEntry
	MAX-ACCESS not-accessible
	STATUS current
	DESCRIPTION
        "
        Row definition for the pm1004PerfUpPast24Cnt 
        table
        "
	INDEX   { pm1004PerfUpPast24CntIndex }
	::= { pm1004PerfUpPast24CntTable 1 }


Pm1004PerfUpPast24CntEntry ::=
	SEQUENCE {
	pm1004PerfUpPast24CntIndex
		INTEGER,
	pm1004PerfUpPast24CntInvCvPortn
		EkiOnOff,
	pm1004PerfUpPast24CntCvValuePortn
		Unsigned32,
	pm1004PerfUpPast24CntInvEsPortn
		EkiOnOff,
	pm1004PerfUpPast24CntEsValuePortn
		Unsigned32,
	pm1004PerfUpPast24CntInvSesPortn
		EkiOnOff,
	pm1004PerfUpPast24CntSesValuePortn
		Unsigned32,
	pm1004PerfUpPast24CntInvSefsPortn
		EkiOnOff,
	pm1004PerfUpPast24CntSefsValuePortn
		Unsigned32,
	pm1004PerfUpPast24CntInvUasPortn
		EkiOnOff,
	pm1004PerfUpPast24CntUasValuePortn
		Unsigned32
	}


pm1004PerfUpPast24CntIndex OBJECT-TYPE
	SYNTAX  INTEGER(0..128)
	MAX-ACCESS  read-only
	STATUS current
	DESCRIPTION
        "
        Index definition for the pm1004PerfUpPast24Cnt 
        table
        "
	::= { pm1004PerfUpPast24CntEntry 1 }


pm1004PerfUpPast24CntInvCvPortn OBJECT-TYPE
	SYNTAX  EkiOnOff
	MAX-ACCESS read-only
	STATUS current
	DESCRIPTION
        "
        Previous 24-hours CV counter inv. 
        :This OID indicates that the previous 
        24-hours Coding Violation counter 
        is invalid
        "
	::= { pm1004PerfUpPast24CntEntry 2 }


pm1004PerfUpPast24CntCvValuePortn OBJECT-TYPE
	SYNTAX  Unsigned32
	MAX-ACCESS read-only
	STATUS current
	DESCRIPTION
        "
        Previous 24-hours CV counter :This 
        OID gives the previous 24-hours 
        Coding Violation counter value
        "
	::= { pm1004PerfUpPast24CntEntry 3 }


pm1004PerfUpPast24CntInvEsPortn OBJECT-TYPE
	SYNTAX  EkiOnOff
	MAX-ACCESS read-only
	STATUS current
	DESCRIPTION
        "
        Previous 24-hours ES counter inv. 
        :This OID indicates that the previous 
        24-hours Errored Second counter 
        is invalid
        "
	::= { pm1004PerfUpPast24CntEntry 4 }


pm1004PerfUpPast24CntEsValuePortn OBJECT-TYPE
	SYNTAX  Unsigned32
	MAX-ACCESS read-only
	STATUS current
	DESCRIPTION
        "
        Previous 24-hours ES counter :This 
        OID gives the previous 24-hours 
        Errored Second counter value
        "
	::= { pm1004PerfUpPast24CntEntry 5 }


pm1004PerfUpPast24CntInvSesPortn OBJECT-TYPE
	SYNTAX  EkiOnOff
	MAX-ACCESS read-only
	STATUS current
	DESCRIPTION
        "
        Previous 24-hours SES counter
         inv. :This OID indicates that
         the previous 24-hours severely 
        Errored Second counter is invali
        d
        "
	::= { pm1004PerfUpPast24CntEntry 6 }


pm1004PerfUpPast24CntSesValuePortn OBJECT-TYPE
	SYNTAX  Unsigned32
	MAX-ACCESS read-only
	STATUS current
	DESCRIPTION
        "
        Previous 24-hours SES counter
         :This OID gives the previous 24-hours 
        severely Errored Second counter 
        value
        "
	::= { pm1004PerfUpPast24CntEntry 7 }


pm1004PerfUpPast24CntInvSefsPortn OBJECT-TYPE
	SYNTAX  EkiOnOff
	MAX-ACCESS read-only
	STATUS current
	DESCRIPTION
        "
        Previous 24-hours SEFS counter 
        inv. :This OID indicates that the 
        previous 24-hours severely Errored 
        Framing Second counter is invali
        d
        "
	::= { pm1004PerfUpPast24CntEntry 8 }


pm1004PerfUpPast24CntSefsValuePortn OBJECT-TYPE
	SYNTAX  Unsigned32
	MAX-ACCESS read-only
	STATUS current
	DESCRIPTION
        "
        Previous 24-hours SEFS counter 
        :This OID gives the previous 24-hours 
        severely Errored Framing Second 
        counter value
        "
	::= { pm1004PerfUpPast24CntEntry 9 }


pm1004PerfUpPast24CntInvUasPortn OBJECT-TYPE
	SYNTAX  EkiOnOff
	MAX-ACCESS read-only
	STATUS current
	DESCRIPTION
        "
        Previous 24-hours UAS counter
         inv. :This OID indicates that
         the previous 24-hours UnAvailable 
        Second counter is invalid
        "
	::= { pm1004PerfUpPast24CntEntry 10 }


pm1004PerfUpPast24CntUasValuePortn OBJECT-TYPE
	SYNTAX  Unsigned32
	MAX-ACCESS read-only
	STATUS current
	DESCRIPTION
        "
        Previous 24-hours UAS counter
         :This OID gives the previous 24-hours 
        UnAvailable Second counter valu
        e
        "
	::= { pm1004PerfUpPast24CntEntry 11 }


--- *********************************************************
---     TABLE for the pm1004PerfLineCurrent15Cnt articles
--- *********************************************************

pm1004PerfLineCurrent15CntTable OBJECT-TYPE
	SYNTAX  SEQUENCE OF Pm1004PerfLineCurrent15CntEntry
	MAX-ACCESS not-accessible
	STATUS current
	DESCRIPTION
        "
        List of pm1004PerfLineCurrent15Cnt 
        Article
        "
	::= { pm1004MonLinePerformance 128 }


pm1004PerfLineCurrent15CntEntry OBJECT-TYPE
	SYNTAX Pm1004PerfLineCurrent15CntEntry
	MAX-ACCESS not-accessible
	STATUS current
	DESCRIPTION
        "
        Row definition for the pm1004PerfLineCurrent15Cnt 
        table
        "
	INDEX   { pm1004PerfLineCurrent15CntIndex }
	::= { pm1004PerfLineCurrent15CntTable 1 }


Pm1004PerfLineCurrent15CntEntry ::=
	SEQUENCE {
	pm1004PerfLineCurrent15CntIndex
		INTEGER,
	pm1004PerfLineCurrent15CntInvCvPortn
		EkiOnOff,
	pm1004PerfLineCurrent15CntCvValuePortn
		Unsigned32,
	pm1004PerfLineCurrent15CntInvEsPortn
		EkiOnOff,
	pm1004PerfLineCurrent15CntEsValuePortn
		Unsigned32,
	pm1004PerfLineCurrent15CntInvSesPortn
		EkiOnOff,
	pm1004PerfLineCurrent15CntSesValuePortn
		Unsigned32,
	pm1004PerfLineCurrent15CntInvSefsPortn
		EkiOnOff,
	pm1004PerfLineCurrent15CntSefsValuePortn
		Unsigned32,
	pm1004PerfLineCurrent15CntInvUasPortn
		EkiOnOff,
	pm1004PerfLineCurrent15CntUasValuePortn
		Unsigned32
	}


pm1004PerfLineCurrent15CntIndex OBJECT-TYPE
	SYNTAX  INTEGER(0..128)
	MAX-ACCESS  read-only
	STATUS current
	DESCRIPTION
        "
        Index definition for the pm1004PerfLineCurrent15Cnt 
        table
        "
	::= { pm1004PerfLineCurrent15CntEntry 1 }


pm1004PerfLineCurrent15CntInvCvPortn OBJECT-TYPE
	SYNTAX  EkiOnOff
	MAX-ACCESS read-only
	STATUS current
	DESCRIPTION
        "
        Current 15-min CV counter inv. 
        :This OID indicates that the current 
        15-min Coding Violation counter 
        is invalid
        "
	::= { pm1004PerfLineCurrent15CntEntry 2 }


pm1004PerfLineCurrent15CntCvValuePortn OBJECT-TYPE
	SYNTAX  Unsigned32
	MAX-ACCESS read-only
	STATUS current
	DESCRIPTION
        "
        Current 15-min CV counter :This 
        OID gives the current 15-min Coding 
        Violation counter value
        "
	::= { pm1004PerfLineCurrent15CntEntry 3 }


pm1004PerfLineCurrent15CntInvEsPortn OBJECT-TYPE
	SYNTAX  EkiOnOff
	MAX-ACCESS read-only
	STATUS current
	DESCRIPTION
        "
        Current 15-min ES counter inv. 
        :This OID indicates that the current 
        15-min Errored Second counter is 
        invalid
        "
	::= { pm1004PerfLineCurrent15CntEntry 4 }


pm1004PerfLineCurrent15CntEsValuePortn OBJECT-TYPE
	SYNTAX  Unsigned32
	MAX-ACCESS read-only
	STATUS current
	DESCRIPTION
        "
        Current 15-min ES counter :This 
        OID gives the current 15-min Errored 
        Second counter value
        "
	::= { pm1004PerfLineCurrent15CntEntry 5 }


pm1004PerfLineCurrent15CntInvSesPortn OBJECT-TYPE
	SYNTAX  EkiOnOff
	MAX-ACCESS read-only
	STATUS current
	DESCRIPTION
        "
        Current 15-min SES counter inv. 
        :This OID indicates that the current 
        15-min severely Errored Second
         counter is invalid
        "
	::= { pm1004PerfLineCurrent15CntEntry 6 }


pm1004PerfLineCurrent15CntSesValuePortn OBJECT-TYPE
	SYNTAX  Unsigned32
	MAX-ACCESS read-only
	STATUS current
	DESCRIPTION
        "
        Current 15-min SES counter :This 
        OID gives the current 15-min severely 
        Errored Second counter value
        "
	::= { pm1004PerfLineCurrent15CntEntry 7 }


pm1004PerfLineCurrent15CntInvSefsPortn OBJECT-TYPE
	SYNTAX  EkiOnOff
	MAX-ACCESS read-only
	STATUS current
	DESCRIPTION
        "
        Current 15-min SEFS counter inv. 
        :This OID indicates that the current 
        15-min severely Errored Framing 
        Second counter is invalid
        "
	::= { pm1004PerfLineCurrent15CntEntry 8 }


pm1004PerfLineCurrent15CntSefsValuePortn OBJECT-TYPE
	SYNTAX  Unsigned32
	MAX-ACCESS read-only
	STATUS current
	DESCRIPTION
        "
        Current 15-min SEFS counter :This 
        OID gives the current 15-min severely 
        Errored Framing Second counter
         value
        "
	::= { pm1004PerfLineCurrent15CntEntry 9 }


pm1004PerfLineCurrent15CntInvUasPortn OBJECT-TYPE
	SYNTAX  EkiOnOff
	MAX-ACCESS read-only
	STATUS current
	DESCRIPTION
        "
        Current 15-min UAS counter inv. 
        :This OID indicates that the current 
        15-min UnAvailable Second counter 
        is invalid
        "
	::= { pm1004PerfLineCurrent15CntEntry 10 }


pm1004PerfLineCurrent15CntUasValuePortn OBJECT-TYPE
	SYNTAX  Unsigned32
	MAX-ACCESS read-only
	STATUS current
	DESCRIPTION
        "
        Current 15-min UAS counter :This 
        OID gives the current 15-min UnAvailable 
        Second counter value
        "
	::= { pm1004PerfLineCurrent15CntEntry 11 }


--- *********************************************************
---     TABLE for the pm1004PerfLinePast15Cnt articles
--- *********************************************************

pm1004PerfLinePast15CntTable OBJECT-TYPE
	SYNTAX  SEQUENCE OF Pm1004PerfLinePast15CntEntry
	MAX-ACCESS not-accessible
	STATUS current
	DESCRIPTION
        "
        List of pm1004PerfLinePast15Cnt 
        Article
        "
	::= { pm1004MonLinePerformance 129 }


pm1004PerfLinePast15CntEntry OBJECT-TYPE
	SYNTAX Pm1004PerfLinePast15CntEntry
	MAX-ACCESS not-accessible
	STATUS current
	DESCRIPTION
        "
        Row definition for the pm1004PerfLinePast15Cnt 
        table
        "
	INDEX   { pm1004PerfLinePast15CntIndex }
	::= { pm1004PerfLinePast15CntTable 1 }


Pm1004PerfLinePast15CntEntry ::=
	SEQUENCE {
	pm1004PerfLinePast15CntIndex
		INTEGER,
	pm1004PerfLinePast15CntInvCvPortn
		EkiOnOff,
	pm1004PerfLinePast15CntCvValuePortn
		Unsigned32,
	pm1004PerfLinePast15CntInvEsPortn
		EkiOnOff,
	pm1004PerfLinePast15CntEsValuePortn
		Unsigned32,
	pm1004PerfLinePast15CntInvSesPortn
		EkiOnOff,
	pm1004PerfLinePast15CntSesValuePortn
		Unsigned32,
	pm1004PerfLinePast15CntInvSefsPortn
		EkiOnOff,
	pm1004PerfLinePast15CntSefsValuePortn
		Unsigned32,
	pm1004PerfLinePast15CntInvUasPortn
		EkiOnOff,
	pm1004PerfLinePast15CntUasValuePortn
		Unsigned32
	}


pm1004PerfLinePast15CntIndex OBJECT-TYPE
	SYNTAX  INTEGER(0..128)
	MAX-ACCESS  read-only
	STATUS current
	DESCRIPTION
        "
        Index definition for the pm1004PerfLinePast15Cnt 
        table
        "
	::= { pm1004PerfLinePast15CntEntry 1 }


pm1004PerfLinePast15CntInvCvPortn OBJECT-TYPE
	SYNTAX  EkiOnOff
	MAX-ACCESS read-only
	STATUS current
	DESCRIPTION
        "
        Previous 15-min CV counter inv. 
        :This OID indicates that the previous 
        15-min Coding Violation counter 
        is invalid
        "
	::= { pm1004PerfLinePast15CntEntry 2 }


pm1004PerfLinePast15CntCvValuePortn OBJECT-TYPE
	SYNTAX  Unsigned32
	MAX-ACCESS read-only
	STATUS current
	DESCRIPTION
        "
        Previous 15-min CV counter :This 
        OID gives the previous 15-min Coding 
        Violation counter value
        "
	::= { pm1004PerfLinePast15CntEntry 3 }


pm1004PerfLinePast15CntInvEsPortn OBJECT-TYPE
	SYNTAX  EkiOnOff
	MAX-ACCESS read-only
	STATUS current
	DESCRIPTION
        "
        Previous 15-min ES counter inv. 
        :This OID indicates that the previous 
        15-min Errored Second counter is 
        invalid
        "
	::= { pm1004PerfLinePast15CntEntry 4 }


pm1004PerfLinePast15CntEsValuePortn OBJECT-TYPE
	SYNTAX  Unsigned32
	MAX-ACCESS read-only
	STATUS current
	DESCRIPTION
        "
        Previous 15-min ES counter :This 
        OID gives the previous 15-min Errored 
        Second counter value
        "
	::= { pm1004PerfLinePast15CntEntry 5 }


pm1004PerfLinePast15CntInvSesPortn OBJECT-TYPE
	SYNTAX  EkiOnOff
	MAX-ACCESS read-only
	STATUS current
	DESCRIPTION
        "
        Previous 15-min SES counter inv. 
        :This OID indicates that the previous 
        15-min severely Errored Second
         counter is invalid
        "
	::= { pm1004PerfLinePast15CntEntry 6 }


pm1004PerfLinePast15CntSesValuePortn OBJECT-TYPE
	SYNTAX  Unsigned32
	MAX-ACCESS read-only
	STATUS current
	DESCRIPTION
        "
        Previous 15-min SES counter :This 
        OID gives the previous 15-min severely 
        Errored Second counter value
        "
	::= { pm1004PerfLinePast15CntEntry 7 }


pm1004PerfLinePast15CntInvSefsPortn OBJECT-TYPE
	SYNTAX  EkiOnOff
	MAX-ACCESS read-only
	STATUS current
	DESCRIPTION
        "
        Previous 15-min SEFS counter inv. 
        :This OID indicates that the previous 
        15-min severely Errored Framing 
        Second counter is invalid
        "
	::= { pm1004PerfLinePast15CntEntry 8 }


pm1004PerfLinePast15CntSefsValuePortn OBJECT-TYPE
	SYNTAX  Unsigned32
	MAX-ACCESS read-only
	STATUS current
	DESCRIPTION
        "
        Previous 15-min SEFS counter :This 
        OID gives the previous 15-min severely 
        Errored Framing Second counter
         value
        "
	::= { pm1004PerfLinePast15CntEntry 9 }


pm1004PerfLinePast15CntInvUasPortn OBJECT-TYPE
	SYNTAX  EkiOnOff
	MAX-ACCESS read-only
	STATUS current
	DESCRIPTION
        "
        Previous 15-min UAS counter inv. 
        :This OID indicates that the previous 
        15-min UnAvailable Second counter 
        is invalid
        "
	::= { pm1004PerfLinePast15CntEntry 10 }


pm1004PerfLinePast15CntUasValuePortn OBJECT-TYPE
	SYNTAX  Unsigned32
	MAX-ACCESS read-only
	STATUS current
	DESCRIPTION
        "
        Previous 15-min UAS counter :This 
        OID gives the previous 15-min UnAvailable 
        Second counter value
        "
	::= { pm1004PerfLinePast15CntEntry 11 }


--- *********************************************************
---     TABLE for the pm1004PerfLineCurrent24Cnt articles
--- *********************************************************

pm1004PerfLineCurrent24CntTable OBJECT-TYPE
	SYNTAX  SEQUENCE OF Pm1004PerfLineCurrent24CntEntry
	MAX-ACCESS not-accessible
	STATUS current
	DESCRIPTION
        "
        List of pm1004PerfLineCurrent24Cnt 
        Article
        "
	::= { pm1004MonLinePerformance 130 }


pm1004PerfLineCurrent24CntEntry OBJECT-TYPE
	SYNTAX Pm1004PerfLineCurrent24CntEntry
	MAX-ACCESS not-accessible
	STATUS current
	DESCRIPTION
        "
        Row definition for the pm1004PerfLineCurrent24Cnt 
        table
        "
	INDEX   { pm1004PerfLineCurrent24CntIndex }
	::= { pm1004PerfLineCurrent24CntTable 1 }


Pm1004PerfLineCurrent24CntEntry ::=
	SEQUENCE {
	pm1004PerfLineCurrent24CntIndex
		INTEGER,
	pm1004PerfLineCurrent24CntInvCvPortn
		EkiOnOff,
	pm1004PerfLineCurrent24CntCvValuePortn
		Unsigned32,
	pm1004PerfLineCurrent24CntInvEsPortn
		EkiOnOff,
	pm1004PerfLineCurrent24CntEsValuePortn
		Unsigned32,
	pm1004PerfLineCurrent24CntInvSesPortn
		EkiOnOff,
	pm1004PerfLineCurrent24CntSesValuePortn
		Unsigned32,
	pm1004PerfLineCurrent24CntInvSefsPortn
		EkiOnOff,
	pm1004PerfLineCurrent24CntSefsValuePortn
		Unsigned32,
	pm1004PerfLineCurrent24CntInvUasPortn
		EkiOnOff,
	pm1004PerfLineCurrent24CntUasValuePortn
		Unsigned32
	}


pm1004PerfLineCurrent24CntIndex OBJECT-TYPE
	SYNTAX  INTEGER(0..128)
	MAX-ACCESS  read-only
	STATUS current
	DESCRIPTION
        "
        Index definition for the pm1004PerfLineCurrent24Cnt 
        table
        "
	::= { pm1004PerfLineCurrent24CntEntry 1 }


pm1004PerfLineCurrent24CntInvCvPortn OBJECT-TYPE
	SYNTAX  EkiOnOff
	MAX-ACCESS read-only
	STATUS current
	DESCRIPTION
        "
        Current 24-hours CV counter inv. 
        :This OID indicates that the current 
        24-hours Coding Violation counter 
        is invalid
        "
	::= { pm1004PerfLineCurrent24CntEntry 2 }


pm1004PerfLineCurrent24CntCvValuePortn OBJECT-TYPE
	SYNTAX  Unsigned32
	MAX-ACCESS read-only
	STATUS current
	DESCRIPTION
        "
        Current 24-hours CV counter :This 
        OID gives the current 24-hours
         Coding Violation counter valu
        e
        "
	::= { pm1004PerfLineCurrent24CntEntry 3 }


pm1004PerfLineCurrent24CntInvEsPortn OBJECT-TYPE
	SYNTAX  EkiOnOff
	MAX-ACCESS read-only
	STATUS current
	DESCRIPTION
        "
        Current 24-hours ES counter inv. 
        :This OID indicates that the current 
        24-hours Errored Second counter 
        is invalid
        "
	::= { pm1004PerfLineCurrent24CntEntry 4 }


pm1004PerfLineCurrent24CntEsValuePortn OBJECT-TYPE
	SYNTAX  Unsigned32
	MAX-ACCESS read-only
	STATUS current
	DESCRIPTION
        "
        Current 24-hours ES counter :This 
        OID gives the current 24-hours
         Errored Second counter value
        "
	::= { pm1004PerfLineCurrent24CntEntry 5 }


pm1004PerfLineCurrent24CntInvSesPortn OBJECT-TYPE
	SYNTAX  EkiOnOff
	MAX-ACCESS read-only
	STATUS current
	DESCRIPTION
        "
        Current 24-hours SES counter inv. 
        :This OID indicates that the current 
        24-hours severely Errored Second 
        counter is invalid
        "
	::= { pm1004PerfLineCurrent24CntEntry 6 }


pm1004PerfLineCurrent24CntSesValuePortn OBJECT-TYPE
	SYNTAX  Unsigned32
	MAX-ACCESS read-only
	STATUS current
	DESCRIPTION
        "
        Current 24-hours SES counter :This 
        OID gives the current 24-hours
         severely Errored Second counter 
        value
        "
	::= { pm1004PerfLineCurrent24CntEntry 7 }


pm1004PerfLineCurrent24CntInvSefsPortn OBJECT-TYPE
	SYNTAX  EkiOnOff
	MAX-ACCESS read-only
	STATUS current
	DESCRIPTION
        "
        Current 24-hours SEFS counter
         inv. :This OID indicates that
         the current 24-hours severely
         Errored Framing Second counter 
        is invalid
        "
	::= { pm1004PerfLineCurrent24CntEntry 8 }


pm1004PerfLineCurrent24CntSefsValuePortn OBJECT-TYPE
	SYNTAX  Unsigned32
	MAX-ACCESS read-only
	STATUS current
	DESCRIPTION
        "
        Current 24-hours SEFS counter
         :This OID gives the current 24-hours 
        severely Errored Framing Second 
        counter value
        "
	::= { pm1004PerfLineCurrent24CntEntry 9 }


pm1004PerfLineCurrent24CntInvUasPortn OBJECT-TYPE
	SYNTAX  EkiOnOff
	MAX-ACCESS read-only
	STATUS current
	DESCRIPTION
        "
        Current 24-hours UAS counter inv. 
        :This OID indicates that the current 
        24-hours UnAvailable Second counter 
        is invalid
        "
	::= { pm1004PerfLineCurrent24CntEntry 10 }


pm1004PerfLineCurrent24CntUasValuePortn OBJECT-TYPE
	SYNTAX  Unsigned32
	MAX-ACCESS read-only
	STATUS current
	DESCRIPTION
        "
        Current 24-hours UAS counter :This 
        OID gives the current 24-hours
         UnAvailable Second counter valu
        e
        "
	::= { pm1004PerfLineCurrent24CntEntry 11 }


--- *********************************************************
---     TABLE for the pm1004PerfLinePast24Cnt articles
--- *********************************************************

pm1004PerfLinePast24CntTable OBJECT-TYPE
	SYNTAX  SEQUENCE OF Pm1004PerfLinePast24CntEntry
	MAX-ACCESS not-accessible
	STATUS current
	DESCRIPTION
        "
        List of pm1004PerfLinePast24Cnt 
        Article
        "
	::= { pm1004MonLinePerformance 131 }


pm1004PerfLinePast24CntEntry OBJECT-TYPE
	SYNTAX Pm1004PerfLinePast24CntEntry
	MAX-ACCESS not-accessible
	STATUS current
	DESCRIPTION
        "
        Row definition for the pm1004PerfLinePast24Cnt 
        table
        "
	INDEX   { pm1004PerfLinePast24CntIndex }
	::= { pm1004PerfLinePast24CntTable 1 }


Pm1004PerfLinePast24CntEntry ::=
	SEQUENCE {
	pm1004PerfLinePast24CntIndex
		INTEGER,
	pm1004PerfLinePast24CntInvCvPortn
		EkiOnOff,
	pm1004PerfLinePast24CntCvValuePortn
		Unsigned32,
	pm1004PerfLinePast24CntInvEsPortn
		EkiOnOff,
	pm1004PerfLinePast24CntEsValuePortn
		Unsigned32,
	pm1004PerfLinePast24CntInvSesPortn
		EkiOnOff,
	pm1004PerfLinePast24CntSesValuePortn
		Unsigned32,
	pm1004PerfLinePast24CntInvSefsPortn
		EkiOnOff,
	pm1004PerfLinePast24CntSefsValuePortn
		Unsigned32,
	pm1004PerfLinePast24CntInvUasPortn
		EkiOnOff,
	pm1004PerfLinePast24CntUasValuePortn
		Unsigned32
	}


pm1004PerfLinePast24CntIndex OBJECT-TYPE
	SYNTAX  INTEGER(0..128)
	MAX-ACCESS  read-only
	STATUS current
	DESCRIPTION
        "
        Index definition for the pm1004PerfLinePast24Cnt 
        table
        "
	::= { pm1004PerfLinePast24CntEntry 1 }


pm1004PerfLinePast24CntInvCvPortn OBJECT-TYPE
	SYNTAX  EkiOnOff
	MAX-ACCESS read-only
	STATUS current
	DESCRIPTION
        "
        Previous 24-hours CV counter inv. 
        :This OID indicates that the previous 
        24-hours Coding Violation counter 
        is invalid
        "
	::= { pm1004PerfLinePast24CntEntry 2 }


pm1004PerfLinePast24CntCvValuePortn OBJECT-TYPE
	SYNTAX  Unsigned32
	MAX-ACCESS read-only
	STATUS current
	DESCRIPTION
        "
        Previous 24-hours CV counter :This 
        OID gives the previous 24-hours 
        Coding Violation counter value
        "
	::= { pm1004PerfLinePast24CntEntry 3 }


pm1004PerfLinePast24CntInvEsPortn OBJECT-TYPE
	SYNTAX  EkiOnOff
	MAX-ACCESS read-only
	STATUS current
	DESCRIPTION
        "
        Previous 24-hours ES counter inv. 
        :This OID indicates that the previous 
        24-hours Errored Second counter 
        is invalid
        "
	::= { pm1004PerfLinePast24CntEntry 4 }


pm1004PerfLinePast24CntEsValuePortn OBJECT-TYPE
	SYNTAX  Unsigned32
	MAX-ACCESS read-only
	STATUS current
	DESCRIPTION
        "
        Previous 24-hours ES counter :This 
        OID gives the previous 24-hours 
        Errored Second counter value
        "
	::= { pm1004PerfLinePast24CntEntry 5 }


pm1004PerfLinePast24CntInvSesPortn OBJECT-TYPE
	SYNTAX  EkiOnOff
	MAX-ACCESS read-only
	STATUS current
	DESCRIPTION
        "
        Previous 24-hours SES counter
         inv. :This OID indicates that
         the previous 24-hours severely 
        Errored Second counter is invali
        d
        "
	::= { pm1004PerfLinePast24CntEntry 6 }


pm1004PerfLinePast24CntSesValuePortn OBJECT-TYPE
	SYNTAX  Unsigned32
	MAX-ACCESS read-only
	STATUS current
	DESCRIPTION
        "
        Previous 24-hours SES counter
         :This OID gives the previous 24-hours 
        severely Errored Second counter 
        value
        "
	::= { pm1004PerfLinePast24CntEntry 7 }


pm1004PerfLinePast24CntInvSefsPortn OBJECT-TYPE
	SYNTAX  EkiOnOff
	MAX-ACCESS read-only
	STATUS current
	DESCRIPTION
        "
        Previous 24-hours SEFS counter 
        inv. :This OID indicates that the 
        previous 24-hours severely Errored 
        Framing Second counter is invali
        d
        "
	::= { pm1004PerfLinePast24CntEntry 8 }


pm1004PerfLinePast24CntSefsValuePortn OBJECT-TYPE
	SYNTAX  Unsigned32
	MAX-ACCESS read-only
	STATUS current
	DESCRIPTION
        "
        Previous 24-hours SEFS counter 
        :This OID gives the previous 24-hours 
        severely Errored Framing Second 
        counter value
        "
	::= { pm1004PerfLinePast24CntEntry 9 }


pm1004PerfLinePast24CntInvUasPortn OBJECT-TYPE
	SYNTAX  EkiOnOff
	MAX-ACCESS read-only
	STATUS current
	DESCRIPTION
        "
        Previous 24-hours UAS counter
         inv. :This OID indicates that
         the previous 24-hours UnAvailable 
        Second counter is invalid
        "
	::= { pm1004PerfLinePast24CntEntry 10 }


pm1004PerfLinePast24CntUasValuePortn OBJECT-TYPE
	SYNTAX  Unsigned32
	MAX-ACCESS read-only
	STATUS current
	DESCRIPTION
        "
        Previous 24-hours UAS counter
         :This OID gives the previous 24-hours 
        UnAvailable Second counter valu
        e
        "
	::= { pm1004PerfLinePast24CntEntry 11 }



pm1004PerfEnable OBJECT-TYPE
	SYNTAX EkiOnOff
	MAX-ACCESS read-write
	STATUS current
	DESCRIPTION
        "
        Perf. Mon. Enable :This OID enables 
        the Performance Monitoring applicatio
        n
        "
	::= { pm1004MonSync 257 }


pm1004PerfSyncSource OBJECT-TYPE
	SYNTAX EkiSynchroMode
	MAX-ACCESS read-write
	STATUS current
	DESCRIPTION
        "
        Perf. Mon. Sync. Source :This
         OID selects the Synchronisation 
        source for the Performance Monitoring 
        application (internal of external
        )
        "
	::= { pm1004MonSync 258 }


pm1004Perf15minSync OBJECT-TYPE
	SYNTAX EkiOnOff
	MAX-ACCESS read-write
	STATUS current
	DESCRIPTION
        "
        Perf. Mon. 15-min sync. :This
         OID must be used in external synchronisation 
        mode only to send a 15-min synchronisation 
        command
        "
	::= { pm1004MonSync 259 }


pm1004Perf24hSync OBJECT-TYPE
	SYNTAX EkiOnOff
	MAX-ACCESS read-write
	STATUS current
	DESCRIPTION
        "
        Perf. Mon. 24-hours sync. :This 
        OID must be used in external synchronisation 
        mode only to send a 24-hours synchronisation 
        command
        "
	::= { pm1004MonSync 260 }


pm1004PerfCurrent15MinElapsedTime OBJECT-TYPE
	SYNTAX Counter32
	MAX-ACCESS read-write
	STATUS current
	DESCRIPTION
        "
        Current 15min period Elapsed Time 
         :This OID gives the number of
         seconds elapsed in the current 
        15-minutes period
        "
	::= { pm1004MonTimeStamp 5 }


pm1004PerfCurrent24HoursElapsedTime OBJECT-TYPE
	SYNTAX Counter32
	MAX-ACCESS read-write
	STATUS current
	DESCRIPTION
        "
        Current 24hours period Elapsed 
        Time :This OID gives the number 
        of seconds elapsed in the current 
        24-hours period
        "
	::= { pm1004MonTimeStamp 6 }


pm1004PerfPast15MinElapsedTime OBJECT-TYPE
	SYNTAX Counter32
	MAX-ACCESS read-write
	STATUS current
	DESCRIPTION
        "
        Past 15min period Elapsed Time 
         :This OID gives the number of
         seconds elapsed in the past 15-minutes 
        period
        "
	::= { pm1004MonTimeStamp 7 }


pm1004PerfPast24HoursElapsedTime OBJECT-TYPE
	SYNTAX Counter32
	MAX-ACCESS read-write
	STATUS current
	DESCRIPTION
        "
        Past 24hours period Elapsed Time 
        :This OID gives the number of seconds 
        elapsed in the past 24-hours perio
        d
        "
	::= { pm1004MonTimeStamp 8 }






--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm1004DwlrestartProcess OBJECT IDENTIFIER ::= { pm1004DwlOther 0 }




pm1004DwlColdRestartProcessed OBJECT-TYPE
	  SYNTAX EkiOnOff
	  MAX-ACCESS read-only
	  STATUS current
	  DESCRIPTION
        "
        Cold Restart :This OID indicates 
        that the module last restart was 
        a Cold RESTART
        "
	  ::= { pm1004DwlrestartProcess 2 }



pm1004DwlWarmRestartProcessed OBJECT-TYPE
	  SYNTAX EkiOnOff
	  MAX-ACCESS read-only
	  STATUS current
	  DESCRIPTION
        "
        Warm Restart :This OID indicates 
        that the module last restart was 
        a Warm RESTART
        "
	  ::= { pm1004DwlrestartProcess 1 }



--- *****************************************************
---     LEAF for the swBanksUsed article
--- *****************************************************
pm1004DwlswBanksUsed OBJECT IDENTIFIER ::= { pm1004DwlOther 1 }




pm1004DwlSwBank2Notempty OBJECT-TYPE
	  SYNTAX EkiOnOff
	  MAX-ACCESS read-only
	  STATUS current
	  DESCRIPTION
        "
        SW bank 2 loaded  :This OID indicates 
        a software is loaded in SW bank 
        2  <Help>  This status indicates 
        if the SW bank 2 contains SW packag
        e
        "
	  ::= { pm1004DwlswBanksUsed 6 }



pm1004DwlSwBank1Notempty OBJECT-TYPE
	  SYNTAX EkiOnOff
	  MAX-ACCESS read-only
	  STATUS current
	  DESCRIPTION
        "
        SW bank 1 loaded  :This OID indicates 
        a software is loaded in SW bank 
        1  <Help>  This status indicates 
        if the SW bank 1 contains SW packag
        e
        "
	  ::= { pm1004DwlswBanksUsed 5 }



pm1004DwlSwBank2Used OBJECT-TYPE
	  SYNTAX EkiOnOff
	  MAX-ACCESS read-only
	  STATUS current
	  DESCRIPTION
        "
        SW bank 2 active  :This OID indicates 
        the module is working on SW bank 
        2  <Help>  This status indicates 
        if the SW bank 2 is active or standb
        y
        "
	  ::= { pm1004DwlswBanksUsed 2 }



pm1004DwlSwBank1Used OBJECT-TYPE
	  SYNTAX EkiOnOff
	  MAX-ACCESS read-only
	  STATUS current
	  DESCRIPTION
        "
        SW bank 1 active  :This OID indicates 
        the module is working on SW bank 
        1  <Help>  This status indicates 
        if the SW bank 1 is active or standb
        y
        "
	  ::= { pm1004DwlswBanksUsed 1 }



--- *****************************************************
---     LEAF for the gwBanksUsed article
--- *****************************************************
pm1004DwlgwBanksUsed OBJECT IDENTIFIER ::= { pm1004DwlOther 2 }




pm1004DwlGwBank4Notempty OBJECT-TYPE
	  SYNTAX EkiOnOff
	  MAX-ACCESS read-only
	  STATUS current
	  DESCRIPTION
        "
        GW bank 4 loaded  :This OID indicates 
        a gateware is loaded in GW bank 
        4
        "
	  ::= { pm1004DwlgwBanksUsed 8 }



pm1004DwlGwBank3Notempty OBJECT-TYPE
	  SYNTAX EkiOnOff
	  MAX-ACCESS read-only
	  STATUS current
	  DESCRIPTION
        "
        GW bank 3 loaded  :This OID indicates 
        a gateware is loaded in GW bank 
        3  <Help>  This status indicates 
        if the GW bank 3 contains GW packag
        e
        "
	  ::= { pm1004DwlgwBanksUsed 7 }



pm1004DwlGwBank2Notempty OBJECT-TYPE
	  SYNTAX EkiOnOff
	  MAX-ACCESS read-only
	  STATUS current
	  DESCRIPTION
        "
        GW bank 2 loaded  :This OID indicates 
        a gateware is loaded in GW bank 
        2
        "
	  ::= { pm1004DwlgwBanksUsed 6 }



pm1004DwlGwBank1Notempty OBJECT-TYPE
	  SYNTAX EkiOnOff
	  MAX-ACCESS read-only
	  STATUS current
	  DESCRIPTION
        "
        GW bank 1 loaded  :This OID indicates 
        a gateware is loaded in GW bank 
        1  <Help>  This status indicates 
        if the GW bank 1 contains GW packag
        e
        "
	  ::= { pm1004DwlgwBanksUsed 5 }



pm1004DwlGwBank4Used OBJECT-TYPE
	  SYNTAX EkiOnOff
	  MAX-ACCESS read-only
	  STATUS current
	  DESCRIPTION
        "
        GW bank 4 active  :This OID indicates 
        the module is working on GW bank 
        4
        "
	  ::= { pm1004DwlgwBanksUsed 4 }



pm1004DwlGwBank3Used OBJECT-TYPE
	  SYNTAX EkiOnOff
	  MAX-ACCESS read-only
	  STATUS current
	  DESCRIPTION
        "
        GW bank 3 active  :This OID indicates 
        the module is working on GW bank 
        3  <Help>  This status indicates 
        if the GW bank 3 is active or standb
        y
        "
	  ::= { pm1004DwlgwBanksUsed 3 }



pm1004DwlGwBank2Used OBJECT-TYPE
	  SYNTAX EkiOnOff
	  MAX-ACCESS read-only
	  STATUS current
	  DESCRIPTION
        "
        GW bank 2 active  :This OID indicates 
        the module is working on GW bank 
        2
        "
	  ::= { pm1004DwlgwBanksUsed 2 }



pm1004DwlGwBank1Used OBJECT-TYPE
	  SYNTAX EkiOnOff
	  MAX-ACCESS read-only
	  STATUS current
	  DESCRIPTION
        "
        GW bank 1 active  :This OID indicates 
        the module is working on GW bank 
        1  <Help>  This status indicates 
        if the GW bank 1 is active or standb
        y
        "
	  ::= { pm1004DwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm1004CfgAccessCAisCsf OBJECT IDENTIFIER ::= { pm1004Config 1 }



--- *****************************************************
---     LEAF for the table 0012
--- *****************************************************

pm1004CfgClientcaiscsfTable OBJECT-TYPE
	SYNTAX  SEQUENCE OF Pm1004CfgClientcaiscsfEntry
	MAX-ACCESS not-accessible
	STATUS current
	DESCRIPTION
        "
        List of  Article
        "
	::= { pm1004CfgAccessCAisCsf 1 }


pm1004CfgClientcaiscsfEntry OBJECT-TYPE
	SYNTAX Pm1004CfgClientcaiscsfEntry
	MAX-ACCESS not-accessible
	STATUS current
	DESCRIPTION
        "
        Row definition for the accessCAisCsf 
        table
        "
	INDEX   { pm1004CfgClientcaiscsfIndex }
	::= { pm1004CfgClientcaiscsfTable 1 }


Pm1004CfgClientcaiscsfEntry ::=
	SEQUENCE {
	pm1004CfgClientcaiscsfIndex
		INTEGER,
	pm1004CfgCAisModePortn
		Unsigned32,
	pm1004CfgUpAccessioAlmPortn
		Unsigned32,
	pm1004CfgUpMapperDeAlmPortn
		Unsigned32,
	pm1004CfgUpAccessioSdhAlmPortn
		Unsigned32,
	pm1004CfgDownAccessioAlmPortn
		Unsigned32,
	pm1004CfgDownMapperDeAlmPortn
		Unsigned32,
	pm1004CfgDownDfrmAlmPortn
		Unsigned32,
	pm1004CfgDownLineSyncAlarmsPortn
		Unsigned32,
	pm1004CfgDownAccessioSdhAlmPortn
		Unsigned32
	}


pm1004CfgClientcaiscsfIndex OBJECT-TYPE
	SYNTAX  INTEGER(0..128)
	MAX-ACCESS  read-only
	STATUS current
	DESCRIPTION
        "
        Index definition for the clientcaiscsf 
        table
        "
	::= { pm1004CfgClientcaiscsfEntry 1 }


pm1004CfgCAisModePortn OBJECT-TYPE
	SYNTAX  Unsigned32 (0..65536)
	MAX-ACCESS read-write
	STATUS current
	DESCRIPTION
        "
        CAIS mode  on Client Port :This 
        register enables/disables port
          laser shutdown on CAIS insertion 
        condition
        "
	::= { pm1004CfgClientcaiscsfEntry 3 }


pm1004CfgUpAccessioAlmPortn OBJECT-TYPE
	SYNTAX  Unsigned32 (0..65536)
	MAX-ACCESS read-write
	STATUS current
	DESCRIPTION
        "
        CSF contributors on Client Port 
        :This register configures the contributors 
        to upstream CSF insertion on the 
        port.
        "
	::= { pm1004CfgClientcaiscsfEntry 9 }


pm1004CfgUpMapperDeAlmPortn OBJECT-TYPE
	SYNTAX  Unsigned32 (0..65536)
	MAX-ACCESS read-write
	STATUS current
	DESCRIPTION
        "
        CSF contributors on Client Port 
        :This register configures the contributors 
        to upstream CSF insertion on the 
        port.
        "
	::= { pm1004CfgClientcaiscsfEntry 10 }


pm1004CfgUpAccessioSdhAlmPortn OBJECT-TYPE
	SYNTAX  Unsigned32 (0..65536)
	MAX-ACCESS read-write
	STATUS current
	DESCRIPTION
        "
        CSF contributors on Client Port 
        :This register selects the contributors 
        of SDH register to upstream CAIS/CSF 
        on Port
        "
	::= { pm1004CfgClientcaiscsfEntry 11 }


pm1004CfgDownAccessioAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pm1004CfgClientcaiscsfEntry 17 }


pm1004CfgDownMapperDeAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pm1004CfgClientcaiscsfEntry 18 }


pm1004CfgDownDfrmAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pm1004CfgClientcaiscsfEntry 19 }


pm1004CfgDownLineSyncAlarmsPortn OBJECT-TYPE
	SYNTAX  Unsigned32 (0..65536)
	MAX-ACCESS read-write
	STATUS deprecated
	DESCRIPTION
        "
        CAIS contributors on Client Port 
        :This register configures the contributors 
        to downstream CAIS insertion on 
         port.
        "
	::= { pm1004CfgClientcaiscsfEntry 20 }


pm1004CfgDownAccessioSdhAlmPortn OBJECT-TYPE
	SYNTAX  Unsigned32 (0..65536)
	MAX-ACCESS read-write
	STATUS current
	DESCRIPTION
        "
        CAIS contributors on Client Port 
        :This register selects the contributors 
        of SDH register to downstream CAIS/CSF 
        on Port
        "
	::= { pm1004CfgClientcaiscsfEntry 21 }


--- *****************************************************
---     LEAF for the table Group startup
--- *****************************************************

pm1004CfgStartup OBJECT IDENTIFIER ::= { pm1004Config 2 }



--- *****************************************************
---     LEAF for the table 2111
--- *****************************************************

pm1004CfgClientStartupTable OBJECT-TYPE
	SYNTAX  SEQUENCE OF Pm1004CfgClientStartupEntry
	MAX-ACCESS not-accessible
	STATUS current
	DESCRIPTION
        "
        List of  Article
        "
	::= { pm1004CfgStartup 1 }


pm1004CfgClientStartupEntry OBJECT-TYPE
	SYNTAX Pm1004CfgClientStartupEntry
	MAX-ACCESS not-accessible
	STATUS current
	DESCRIPTION
        "
        Row definition for the startup 
        table
        "
	INDEX   { pm1004CfgClientStartupIndex }
	::= { pm1004CfgClientStartupTable 1 }


Pm1004CfgClientStartupEntry ::=
	SEQUENCE {
	pm1004CfgClientStartupIndex
		INTEGER,
	pm1004CfgSystConfPortPortn
		Unsigned32,
	pm1004CfgNetConfPortPortn
		Unsigned32
	}


pm1004CfgClientStartupIndex OBJECT-TYPE
	SYNTAX  INTEGER(0..128)
	MAX-ACCESS  read-only
	STATUS current
	DESCRIPTION
        "
        Index definition for the clientStartup 
        table
        "
	::= { pm1004CfgClientStartupEntry 1 }


pm1004CfgSystConfPortPortn OBJECT-TYPE
	SYNTAX  Unsigned32 (0..65536)
	MAX-ACCESS read-write
	STATUS current
	DESCRIPTION
        "
        Default Settings on Client Port 
        :This  register configures the
         default initialisation settings 
        on the port.
        "
	::= { pm1004CfgClientStartupEntry 3 }


pm1004CfgNetConfPortPortn OBJECT-TYPE
	SYNTAX  Unsigned32 (0..65536)
	MAX-ACCESS read-write
	STATUS current
	DESCRIPTION
        "
        Default Protocol on Client Port 
        :This register configures the default 
        initialisation protocol on the
         port.
        "
	::= { pm1004CfgClientStartupEntry 4 }


--- *****************************************************
---     LEAF for the table 2191
--- *****************************************************

pm1004tablelineStartup OBJECT IDENTIFIER ::= { pm1004CfgStartup 2 }



pm1004CfgsystConfLine1 OBJECT-TYPE
	  SYNTAX Unsigned32 (0..65536)
	  MAX-ACCESS read-write
	  STATUS current
	  DESCRIPTION
        "
        Default Settings on Line 1 :This 
        register configures the default 
        initialisation settings on Line 
        port 1.
        "
	  ::= { pm1004tablelineStartup 2 }



pm1004CfglineOptions1 OBJECT-TYPE
	  SYNTAX Unsigned32 (0..65536)
	  MAX-ACCESS read-write
	  STATUS current
	  DESCRIPTION
        "
        Default Options on Active Line 
        Port :This register configures
         the default options on the active 
        line port
        "
	  ::= { pm1004tablelineStartup 5 }



pm1004CfgsystConfLine2 OBJECT-TYPE
	  SYNTAX Unsigned32 (0..65536)
	  MAX-ACCESS read-write
	  STATUS current
	  DESCRIPTION
        "
        Default Settings on Line 2 :This 
        register configures the default 
        initialisation settings on Line 
        port 2.
        "
	  ::= { pm1004tablelineStartup 6 }



pm1004CfglineSelection OBJECT-TYPE
	  SYNTAX Unsigned32 (0..65536)
	  MAX-ACCESS read-write
	  STATUS current
	  DESCRIPTION
        "
        Default Settings of active line 
        :This  register configures the
         start up active line.
        "
	  ::= { pm1004tablelineStartup 7 }



--- *****************************************************
---     LEAF for the table 21AB
--- *****************************************************

pm1004CfgXfpTable OBJECT-TYPE
	SYNTAX  SEQUENCE OF Pm1004CfgXfpEntry
	MAX-ACCESS not-accessible
	STATUS current
	DESCRIPTION
        "
        List of  Article
        "
	::= { pm1004CfgStartup 3 }


pm1004CfgXfpEntry OBJECT-TYPE
	SYNTAX Pm1004CfgXfpEntry
	MAX-ACCESS not-accessible
	STATUS current
	DESCRIPTION
        "
        Row definition for the startup 
        table
        "
	INDEX   { pm1004CfgXfpIndex }
	::= { pm1004CfgXfpTable 1 }


Pm1004CfgXfpEntry ::=
	SEQUENCE {
	pm1004CfgXfpIndex
		INTEGER,
	pm1004CfgSystConfXfpPortn
		Unsigned32,
	pm1004CfgDataRateConfXfpPortn
		Unsigned32
	}


pm1004CfgXfpIndex OBJECT-TYPE
	SYNTAX  INTEGER(0..128)
	MAX-ACCESS  read-only
	STATUS current
	DESCRIPTION
        "
        Index definition for the xfp tabl
        e
        "
	::= { pm1004CfgXfpEntry 1 }


pm1004CfgSystConfXfpPortn OBJECT-TYPE
	SYNTAX  Unsigned32 (0..65536)
	MAX-ACCESS read-write
	STATUS current
	DESCRIPTION
        "
        Default settings on XFP Port :This 
        register configures the default 
        initialisation settings on XFP
         port.
        "
	::= { pm1004CfgXfpEntry 3 }


pm1004CfgDataRateConfXfpPortn OBJECT-TYPE
	SYNTAX  Unsigned32 (0..65536)
	MAX-ACCESS read-write
	STATUS deprecated
	DESCRIPTION
        "
        :Reserved
        "
	::= { pm1004CfgXfpEntry 4 }


--- *****************************************************
---     LEAF for the table Group modPerfConfig
--- *****************************************************

pm1004CfgModPerfConfig OBJECT IDENTIFIER ::= { pm1004Config 3 }



--- *****************************************************
---     LEAF for the table 5002
--- *****************************************************

pm1004tablemodPerfConfig OBJECT IDENTIFIER ::= { pm1004CfgModPerfConfig 1 }



pm1004CfgperfMode OBJECT-TYPE
	  SYNTAX Unsigned32 (0..65536)
	  MAX-ACCESS read-write
	  STATUS current
	  DESCRIPTION
        "
        SONET or SDH monitoring mode :This 
        OID defines the line monitoring 
        mode (SONET or SDH mode)
        "
	  ::= { pm1004tablemodPerfConfig 2 }



--- *****************************************************
---     LEAF for the table Group j0Client
--- *****************************************************

pm1004CfgJ0Client OBJECT IDENTIFIER ::= { pm1004Config 4 }



--- *****************************************************
---     LEAF for the table 0013
--- *****************************************************

pm1004CfgEmptyTable OBJECT-TYPE
	SYNTAX  SEQUENCE OF Pm1004CfgEmptyEntry
	MAX-ACCESS not-accessible
	STATUS current
	DESCRIPTION
        "
        List of  Article
        "
	::= { pm1004CfgJ0Client 1 }


pm1004CfgEmptyEntry OBJECT-TYPE
	SYNTAX Pm1004CfgEmptyEntry
	MAX-ACCESS not-accessible
	STATUS current
	DESCRIPTION
        "
        Row definition for the j0Client 
        table
        "
	INDEX   { pm1004CfgEmptyIndex }
	::= { pm1004CfgEmptyTable 1 }


Pm1004CfgEmptyEntry ::=
	SEQUENCE {
	pm1004CfgEmptyIndex
		INTEGER,
	pm1004CfgClientExpectJ0SetupPortn
		Unsigned32
	}


pm1004CfgEmptyIndex OBJECT-TYPE
	SYNTAX  INTEGER(0..128)
	MAX-ACCESS  read-only
	STATUS current
	DESCRIPTION
        "
        Index definition for the empty 
        table
        "
	::= { pm1004CfgEmptyEntry 1 }


pm1004CfgClientExpectJ0SetupPortn OBJECT-TYPE
	SYNTAX  Unsigned32 (0..65536)
	MAX-ACCESS read-write
	STATUS current
	DESCRIPTION
        "
        Expected Trace Identifier mode 
        :This register configures the Expected 
        Trace Identifier Mode (single byte, 
        16 bytes with CRC7, 64 bytes with 
        CRC7 or 64 bytes with CR/LF terminaison
        )
        "
	::= { pm1004CfgEmptyEntry 3 }


--- *****************************************************
---     LEAF for the table Group labels
--- *****************************************************

pm1004CfgLabels OBJECT IDENTIFIER ::= { pm1004Config 5 }



--- *****************************************************
---     LEAF for the table NO_VALUE
--- *****************************************************

pm1004CfgLabelclientTable OBJECT-TYPE
	SYNTAX  SEQUENCE OF Pm1004CfgLabelclientEntry
	MAX-ACCESS not-accessible
	STATUS current
	DESCRIPTION
        "
        List of  Article
        "
	::= { pm1004CfgLabels 1 }


pm1004CfgLabelclientEntry OBJECT-TYPE
	SYNTAX Pm1004CfgLabelclientEntry
	MAX-ACCESS not-accessible
	STATUS current
	DESCRIPTION
        "
        Row definition for the labels
         table
        "
	INDEX   { pm1004CfgLabelclientIndex }
	::= { pm1004CfgLabelclientTable 1 }


Pm1004CfgLabelclientEntry ::=
	SEQUENCE {
	pm1004CfgLabelclientIndex
		INTEGER,
	pm1004CfgLabelclientPortn
		DisplayString
	}


pm1004CfgLabelclientIndex OBJECT-TYPE
	SYNTAX  INTEGER(0..128)
	MAX-ACCESS  read-only
	STATUS current
	DESCRIPTION
        "
        Index definition for the labelclient 
        table
        "
	::= { pm1004CfgLabelclientEntry 1 }


pm1004CfgLabelclientPortn OBJECT-TYPE
	SYNTAX  DisplayString( SIZE(1..16))
	MAX-ACCESS read-write
	STATUS current
	DESCRIPTION
        "
        Default settings on the label
         of the Ports :These registers
         configures the default initialisation 
        settings of the labels of the ports
        .
        "
	::= { pm1004CfgLabelclientEntry 3 }


--- *****************************************************
---     LEAF for the table NO_VALUE
--- *****************************************************

pm1004CfgLabellineTable OBJECT-TYPE
	SYNTAX  SEQUENCE OF Pm1004CfgLabellineEntry
	MAX-ACCESS not-accessible
	STATUS current
	DESCRIPTION
        "
        List of  Article
        "
	::= { pm1004CfgLabels 2 }


pm1004CfgLabellineEntry OBJECT-TYPE
	SYNTAX Pm1004CfgLabellineEntry
	MAX-ACCESS not-accessible
	STATUS current
	DESCRIPTION
        "
        Row definition for the labels
         table
        "
	INDEX   { pm1004CfgLabellineIndex }
	::= { pm1004CfgLabellineTable 1 }


Pm1004CfgLabellineEntry ::=
	SEQUENCE {
	pm1004CfgLabellineIndex
		INTEGER,
	pm1004CfgLabellinePortn
		DisplayString
	}


pm1004CfgLabellineIndex OBJECT-TYPE
	SYNTAX  INTEGER(0..128)
	MAX-ACCESS  read-only
	STATUS current
	DESCRIPTION
        "
        Index definition for the labelline 
        table
        "
	::= { pm1004CfgLabellineEntry 1 }


pm1004CfgLabellinePortn OBJECT-TYPE
	SYNTAX  DisplayString( SIZE(1..16))
	MAX-ACCESS read-write
	STATUS current
	DESCRIPTION
        "
        Default settings on the label
         of the lines :These registers
         configures the default initialisation 
        settings of the labels of the lines
        .
        "
	::= { pm1004CfgLabellineEntry 3 }


--- *****************************************************
---     LEAF for the table Group startuptlh
--- *****************************************************

pm1004CfgStartuptlh OBJECT IDENTIFIER ::= { pm1004Config 6 }



--- *****************************************************
---     LEAF for the table 25A8
--- *****************************************************

pm1004CfgOtxtlhTable OBJECT-TYPE
	SYNTAX  SEQUENCE OF Pm1004CfgOtxtlhEntry
	MAX-ACCESS not-accessible
	STATUS current
	DESCRIPTION
        "
        List of  Article
        "
	::= { pm1004CfgStartuptlh 1 }


pm1004CfgOtxtlhEntry OBJECT-TYPE
	SYNTAX Pm1004CfgOtxtlhEntry
	MAX-ACCESS not-accessible
	STATUS current
	DESCRIPTION
        "
        Row definition for the startuptlh 
        table
        "
	INDEX   { pm1004CfgOtxtlhIndex }
	::= { pm1004CfgOtxtlhTable 1 }


Pm1004CfgOtxtlhEntry ::=
	SEQUENCE {
	pm1004CfgOtxtlhIndex
		INTEGER,
	pm1004CfgNuPortn
		Unsigned32,
	pm1004CfgLineDitherRatePortn
		Unsigned32,
	pm1004CfgLineDitherFhzPortn
		Unsigned32,
	pm1004CfgLinePwrLaserPortn
		Unsigned32,
	pm1004CfgLineFCurrentPortn
		Unsigned32,
	pm1004CfgLineGridCurrentPortn
		Unsigned32,
	pm1004CfgFPortn
		Unsigned32,
	pm1004CfgReservedPortn
		Unsigned32,
	pm1004CfgLinePhotodiodeModePortn
		Unsigned32,
	pm1004CfgLinePhotodiodeValuePortn
		Unsigned32
	}


pm1004CfgOtxtlhIndex OBJECT-TYPE
	SYNTAX  INTEGER(0..128)
	MAX-ACCESS  read-only
	STATUS current
	DESCRIPTION
        "
        Index definition for the otxtlh 
        table
        "
	::= { pm1004CfgOtxtlhEntry 1 }


pm1004CfgNuPortn OBJECT-TYPE
	SYNTAX  Unsigned32 (0..65536)
	MAX-ACCESS read-write
	STATUS deprecated
	DESCRIPTION
        "
        :
        "
	::= { pm1004CfgOtxtlhEntry 3 }


pm1004CfgLineDitherRatePortn OBJECT-TYPE
	SYNTAX  Unsigned32 (0..65536)
	MAX-ACCESS read-write
	STATUS current
	DESCRIPTION
        "
        Default Line OTX TLH FM amplitude 
        :This register configures the start-up 
        width of the frequency modulation 
        of the Line OTX TLH
        "
	::= { pm1004CfgOtxtlhEntry 4 }


pm1004CfgLineDitherFhzPortn OBJECT-TYPE
	SYNTAX  Unsigned32 (0..65536)
	MAX-ACCESS read-write
	STATUS current
	DESCRIPTION
        "
        Default Line OTX TLH FM frequency 
        :This register configures the start-up 
        frequency of the frequency modulation 
        of the Line OTX TLH
        "
	::= { pm1004CfgOtxtlhEntry 5 }


pm1004CfgLinePwrLaserPortn OBJECT-TYPE
	SYNTAX  Unsigned32 (0..65536)
	MAX-ACCESS read-write
	STATUS current
	DESCRIPTION
        "
        Defaut Line OTX TLH output Power 
        :This register configures the start-up 
        output power of the Line OTX TLH 
         (Unit = dBm)
        "
	::= { pm1004CfgOtxtlhEntry 6 }


pm1004CfgLineFCurrentPortn OBJECT-TYPE
	SYNTAX  Unsigned32 (0..65536)
	MAX-ACCESS read-write
	STATUS current
	DESCRIPTION
        "
        Default Line OTX TLH Channel :This 
        register configures the start-up 
        laser channel of the Line OTX TL
        H
        "
	::= { pm1004CfgOtxtlhEntry 7 }


pm1004CfgLineGridCurrentPortn OBJECT-TYPE
	SYNTAX  Unsigned32 (0..65536)
	MAX-ACCESS read-write
	STATUS current
	DESCRIPTION
        "
        Default Line OTX TLH Grid :This 
        register configures the start-up 
        laser grid of the Line OTX TLH
        "
	::= { pm1004CfgOtxtlhEntry 8 }


pm1004CfgFPortn OBJECT-TYPE
	SYNTAX  Unsigned32 (0..65536)
	MAX-ACCESS read-write
	STATUS current
	DESCRIPTION
        "
        Default Line OTX TLH lowest Freq 
        :This register configures the start-up 
        lowest frequency supported on the 
        Line OTX TLH
        "
	::= { pm1004CfgOtxtlhEntry 9 }


pm1004CfgReservedPortn OBJECT-TYPE
	SYNTAX  Unsigned32 (0..65536)
	MAX-ACCESS read-write
	STATUS deprecated
	DESCRIPTION
        "
        :
        "
	::= { pm1004CfgOtxtlhEntry 10 }


pm1004CfgLinePhotodiodeModePortn OBJECT-TYPE
	SYNTAX  Unsigned32 (0..65536)
	MAX-ACCESS read-write
	STATUS current
	DESCRIPTION
        "
        Default Line OTX TLH APD mode
         :This register configures the
         start-up APD mode of the Line
         OTX TLH
        "
	::= { pm1004CfgOtxtlhEntry 11 }


pm1004CfgLinePhotodiodeValuePortn OBJECT-TYPE
	SYNTAX  Unsigned32 (0..65536)
	MAX-ACCESS read-write
	STATUS current
	DESCRIPTION
        "
        Default Line OTX TLH APD atten. 
        :This register configures the start-up 
        APD attenuation on the Line OTX 
        TLH
        "
	::= { pm1004CfgOtxtlhEntry 12 }


--- *****************************************************
---     LEAF for the table Group startuptablefive
--- *****************************************************

pm1004CfgStartuptablefive OBJECT IDENTIFIER ::= { pm1004Config 7 }



--- *****************************************************
---     LEAF for the table 0005
--- *****************************************************

pm1004CfgOtxtlhcapabilitiesTable OBJECT-TYPE
	SYNTAX  SEQUENCE OF Pm1004CfgOtxtlhcapabilitiesEntry
	MAX-ACCESS not-accessible
	STATUS current
	DESCRIPTION
        "
        List of  Article
        "
	::= { pm1004CfgStartuptablefive 1 }


pm1004CfgOtxtlhcapabilitiesEntry OBJECT-TYPE
	SYNTAX Pm1004CfgOtxtlhcapabilitiesEntry
	MAX-ACCESS not-accessible
	STATUS current
	DESCRIPTION
        "
        Row definition for the startuptablefive 
        table
        "
	INDEX   { pm1004CfgOtxtlhcapabilitiesIndex }
	::= { pm1004CfgOtxtlhcapabilitiesTable 1 }


Pm1004CfgOtxtlhcapabilitiesEntry ::=
	SEQUENCE {
	pm1004CfgOtxtlhcapabilitiesIndex
		INTEGER,
	pm1004CfgComponentTypePortn
		Unsigned32,
	pm1004CfgMiscellaneousPortn
		Unsigned32,
	pm1004CfgFirstChannelPortn
		Unsigned32,
	pm1004CfgLastChannelPortn
		Unsigned32,
	pm1004CfgGridPortn
		Unsigned32
	}


pm1004CfgOtxtlhcapabilitiesIndex OBJECT-TYPE
	SYNTAX  INTEGER(0..128)
	MAX-ACCESS  read-only
	STATUS current
	DESCRIPTION
        "
        Index definition for the otxtlhcapabilities 
        table
        "
	::= { pm1004CfgOtxtlhcapabilitiesEntry 1 }


pm1004CfgComponentTypePortn OBJECT-TYPE
	SYNTAX  Unsigned32 (0..65536)
	MAX-ACCESS read-only
	STATUS current
	DESCRIPTION
        "
        Component parameters :This OID 
        defines the component parameter
        s
        "
	::= { pm1004CfgOtxtlhcapabilitiesEntry 3 }


pm1004CfgMiscellaneousPortn OBJECT-TYPE
	SYNTAX  Unsigned32 (0..65536)
	MAX-ACCESS read-only
	STATUS current
	DESCRIPTION
        "
        Miscellaneous default settings 
        :This OID defines the miscellaneous 
        parameters
        "
	::= { pm1004CfgOtxtlhcapabilitiesEntry 4 }


pm1004CfgFirstChannelPortn OBJECT-TYPE
	SYNTAX  Unsigned32 (0..65536)
	MAX-ACCESS read-only
	STATUS current
	DESCRIPTION
        "
        Number of the first channel of 
        the component :This OID defines 
        the first channel number of the 
        PM
        "
	::= { pm1004CfgOtxtlhcapabilitiesEntry 5 }


pm1004CfgLastChannelPortn OBJECT-TYPE
	SYNTAX  Unsigned32 (0..65536)
	MAX-ACCESS read-only
	STATUS current
	DESCRIPTION
        "
        Number of the last channel of
         the component :This OID defines 
        the last channel number of the
         PM
        "
	::= { pm1004CfgOtxtlhcapabilitiesEntry 6 }


pm1004CfgGridPortn OBJECT-TYPE
	SYNTAX  Unsigned32 (0..65536)
	MAX-ACCESS read-only
	STATUS current
	DESCRIPTION
        "
        Grid value of the component :This 
        OID defines the grid of the PM
        "
	::= { pm1004CfgOtxtlhcapabilitiesEntry 7 }



pm1004CfgWriteConfiguration  OBJECT-TYPE
	SYNTAX EkiOnOff
	MAX-ACCESS read-write
	STATUS current
	DESCRIPTION
	"Write configuration to module:This OID 
	 writes the complete configuration to the module"
	::= { pm1004Config 257 }






--- *****************************************************
---     TRAP OBJECTS
--- *****************************************************

pm1004trapPortNumber OBJECT-TYPE
	SYNTAX INTEGER(1..64)
	MAX-ACCESS read-only
	STATUS current
	DESCRIPTION
	"Last port which generates a trap"
	::= { pm1004traps 2 }

pm1004trapLineNumber OBJECT-TYPE
	SYNTAX INTEGER(1..64)
	MAX-ACCESS read-only
	STATUS current
	DESCRIPTION
	"Last Line which generates a trap"
	::= { pm1004traps 3 }

pm1004trapBoardNumber OBJECT-TYPE
	SYNTAX INTEGER(1..64)
	MAX-ACCESS read-only
	STATUS current
	DESCRIPTION
	"Last module which generates a trap"
	::= { pm1004traps 4 }







--- *****************************************************
---     LINE TRAPS
--- *****************************************************

pm1004LineTrapNotUrgentGoesOn NOTIFICATION-TYPE
	OBJECTS {pm1004AlmLineDdmWarningPortn, pm1004trapLineNumber, pm1004trapBoardNumber}
	STATUS current
	--&FILTNAME    "PM1004 Line Not Urgent ON"
	--&ACTIONS     { log, minor }
	--&MATCH       { pm1004AlmLineDdmWarningPortn "on", pm1004trapLineNumber "$2", pm1004trapBoardNumber "$3"}
	--&MESG        "DDM Warning appears on Line Port $2 of PM1004(LH) in Slot $3 ($A)"
	DESCRIPTION "Not urgent Line default is activated"
	::= { pm1004traps 30 }

pm1004LineTrapNotUrgentGoesOff NOTIFICATION-TYPE
	OBJECTS {pm1004AlmLineDdmWarningPortn, pm1004trapLineNumber, pm1004trapBoardNumber}
	STATUS current
	--&FILTNAME    "PM1004 Line Not Urgent OFF"
	--&ACTIONS     { log, normal }
	--&CLEARS      { "PM1004 Line Not Urgent ON" }
	--&MATCH       { pm1004AlmLineDdmWarningPortn "on", pm1004trapLineNumber "$2", pm1004trapBoardNumber "$3"}
	--&MESG        "DDM Warning disappears on Line Port $2 of PM1004 in Slot $3 ($A)"
	DESCRIPTION "Not urgent Line default disappeared"
	::= { pm1004traps 31 }

pm1004LineTrapUrgentGoesOn NOTIFICATION-TYPE
	OBJECTS {pm1004AlmLineDdmAlmPortn, pm1004trapLineNumber, pm1004trapBoardNumber}
	STATUS current
	--&FILTNAME    "PM1004 Line Urgent ON"
	--&ACTIONS     { log, major }
	--&MATCH       { pm1004AlmLineDdmAlmPortn "on", pm1004trapLineNumber "$2", pm1004trapBoardNumber "$3"}
	--&MESG        "DDM Alarm appears on Line Port $2 of PM1004 in Slot $3 ($A)"
	DESCRIPTION "Urgent Line default is activated"
	::= { pm1004traps 32 }

pm1004LineTrapUrgentGoesOff NOTIFICATION-TYPE
	OBJECTS {pm1004AlmLineDdmAlmPortn, pm1004trapLineNumber, pm1004trapBoardNumber}
	STATUS current
	--&FILTNAME    "PM1004 Line Urgent OFF"
	--&ACTIONS     { log, normal }
	--&CLEARS      { "PM1004 Line Urgent ON" }
	--&MATCH       { pm1004AlmLineDdmAlmPortn "on", pm1004trapLineNumber "$2", pm1004trapBoardNumber "$3"}
	--&MESG        "DDM Alarm disappears on Line Port $2 of PM1004 in Slot $3 ($A)"
	DESCRIPTION "Urgent Line default disappeared"
	::= { pm1004traps 33 }

pm1004LineTrapCritGoesOn NOTIFICATION-TYPE
	OBJECTS {pm1004AlmLineFailPortn , pm1004AlmLineHwFailPortn , pm1004trapLineNumber, pm1004trapBoardNumber}
	STATUS current
	--&FILTNAME    "PM1004 Line Fail ON"
	--&ACTIONS     { log, critical }
	--&MATCH       { pm1004AlmLineFailPortn "on", pm1004AlmLineHwFailPortn "*", pm1004trapLineNumber "$3", pm1004trapBoardNumber "$4"}
	--&MESG        "Line Port $3 Down on PM1004 in Slot $4 ($A)"
	
	--&FILTNAME    "PM1004 Line HW Fail ON (Hidden)"
	--&ACTIONS     { info }
	--&MATCH       { pm1004AlmLineFailPortn "*", pm1004AlmLineHwFailPortn "on", pm1004trapLineNumber "$3", pm1004trapBoardNumber "$4"}
	--&MESG        "Line Port $3 Down on PM1004 in Slot $4 ($A)"
	DESCRIPTION "Critical Line default is activated"
	::= { pm1004traps 34 }

pm1004LineTrapCritGoesOff NOTIFICATION-TYPE
	OBJECTS {pm1004AlmLineFailPortn , pm1004AlmLineHwFailPortn , pm1004trapLineNumber, pm1004trapBoardNumber}
	STATUS current
	--&FILTNAME    "PM1004 Line Fail OFF"
	--&ACTIONS     { log,  normal }
	--&CLEARS      { "PM1004 Line Fail ON" }
	--&MATCH       { pm1004AlmLineFailPortn "on", pm1004AlmLineHwFailPortn "*", pm1004trapLineNumber "$3", pm1004trapBoardNumber "$4"}
	--&MESG        "Line Port $3 Up on PM1004 in Slot $4 ($A)"

	--&FILTNAME    "PM1004 Line HW Fail OFF (Hidden)"
	--&ACTIONS     { info }
	--&MATCH       { pm1004AlmLineFailPortn "*", pm1004AlmLineHwFailPortn "on", pm1004trapLineNumber "$3", pm1004trapBoardNumber "$4"}
	--&MESG        "Line Port $3 Up on PM1004 in Slot $4 ($A)"
	DESCRIPTION "Critical Line default disappeared"
	::= { pm1004traps 35 }






--- *****************************************************
---     CLIENT TRAPS
--- *****************************************************

pm1004ClientTrapNotUrgentGoesOn NOTIFICATION-TYPE
	OBJECTS {pm1004AlmSfpDdmWarningPortn, pm1004trapPortNumber, pm1004trapBoardNumber}
	STATUS current
	--&FILTNAME    "PM1004 Client Not Urgent ON"
	--&ACTIONS     { log, minor }
	--&MATCH       { pm1004AlmSfpDdmWarningPortn "on", pm1004trapPortNumber "$2", pm1004trapBoardNumber "$3"}
	--&MESG        "DDM Warning appears on Client Port $2 of PM1004 in Slot $3 ($A)"
	DESCRIPTION "Not urgent client default is activated"
	::= { pm1004traps 40 }

pm1004ClientTrapNotUrgentGoesOff NOTIFICATION-TYPE
	OBJECTS {pm1004AlmSfpDdmWarningPortn, pm1004trapPortNumber, pm1004trapBoardNumber}
	STATUS current
	--&FILTNAME    "PM1004 Client Not Urgent OFF"
	--&ACTIONS     { log, normal }
	--&CLEARS      { "PM1004 Client Not Urgent ON" }
	--&MATCH       { pm1004AlmSfpDdmWarningPortn "on", pm1004trapPortNumber "$2", pm1004trapBoardNumber "$3"}
	--&MESG        "DDM Warning appears on Client Port $2 of PM1004 in Slot $3 ($A)"
	DESCRIPTION "Not urgent client default disappeared"
	::= { pm1004traps 41 }

pm1004ClientTrapUrgentGoesOn NOTIFICATION-TYPE
	OBJECTS {pm1004AlmSfpDdmAlmPortn, pm1004trapPortNumber, pm1004trapBoardNumber}
	STATUS current
	--&FILTNAME    "PM1004 Client Urgent ON"
	--&ACTIONS     { log, major }
	--&MATCH       { pm1004AlmSfpDdmAlmPortn "on", pm1004trapPortNumber "$2", pm1004trapBoardNumber "$3"}
	--&MESG        "DDM Alarm appears on Client Port $2 of PM1004 in Slot $3 ($A)"
	DESCRIPTION "Urgent client default is activated"
	::= { pm1004traps 42 }

pm1004ClientTrapUrgentGoesOff NOTIFICATION-TYPE
	OBJECTS {pm1004AlmSfpDdmAlmPortn, pm1004trapPortNumber, pm1004trapBoardNumber}
	STATUS current
	--&FILTNAME    "PM1004 Client Urgent OFF"
	--&ACTIONS     { log, normal }
	--&CLEARS      { "PM1004 Client Urgent ON" }
	--&MATCH       { pm1004AlmSfpDdmAlmPortn "on", pm1004trapPortNumber "$2", pm1004trapBoardNumber "$3"}
	--&MESG        "DDM Alarm disappears on Client Port $2 of PM1004 in Slot $3 ($A)"
	DESCRIPTION "Urgent client default disappeared"
	::= { pm1004traps 43 }

pm1004ClientTrapCritGoesOn NOTIFICATION-TYPE
	OBJECTS {pm1004AlmFailAccPortn, pm1004AlmHwFailAccPortn, pm1004trapPortNumber, pm1004trapBoardNumber}
	STATUS current
	--&FILTNAME    "PM1004 Client Fail ON"
	--&ACTIONS     { log, critical }
	--&MATCH       { pm1004AlmFailAccPortn "on", pm1004AlmHwFailAccPortn "*", pm1004trapPortNumber "$3", pm1004trapBoardNumber "$4"}
	--&MESG        "Client Port $3 Down on PM1004 in Slot $4 ($A)"
	
	--&FILTNAME    "PM1004 Client HW Fail ON (Hidden)"
	--&ACTIONS     { info }
	--&MATCH       { pm1004AlmFailAccPortn "*", pm1004AlmHwFailAccPortn "on", pm1004trapPortNumber "$3", pm1004trapBoardNumber "$4"}
	--&MESG        "Client Port $3 Down on PM1004 in Slot $4 ($A)"
	DESCRIPTION "Critical client default is activated"
	::= { pm1004traps 44 }

pm1004ClientTrapCritGoesOff NOTIFICATION-TYPE
	OBJECTS {pm1004AlmFailAccPortn, pm1004AlmHwFailAccPortn, pm1004trapPortNumber, pm1004trapBoardNumber}
	STATUS current
	--&FILTNAME    "PM1004 Client Fail OFF"
	--&ACTIONS     { log, normal }
	--&CLEARS      { "PM1004 Client Fail ON" }
	--&MATCH       { pm1004AlmFailAccPortn "on", pm1004AlmHwFailAccPortn "*", pm1004trapPortNumber "$3", pm1004trapBoardNumber "$4"}
	--&MESG        "Client Port $3 Up on PM1004 in Slot $4 ($A)"
	
	--&FILTNAME    "PM1004 Client HW Fail OFF (Hidden)"
	--&ACTIONS     { info }
	--&MATCH       { pm1004AlmFailAccPortn "*", pm1004AlmHwFailAccPortn "on", pm1004trapPortNumber "$3", pm1004trapBoardNumber "$4"}
	--&MESG        "Client Port $3 Up on PM1004 in Slot $4 ($A)"
	DESCRIPTION "Critical client default disappeared"
	::= { pm1004traps 45 }






--- *****************************************************
---     HW TRAPS
--- *****************************************************

pm1004PowerTrapUrgentGoesOn NOTIFICATION-TYPE
	OBJECTS {pm1004AlmDefFuseB, pm1004AlmDefFuseA , pm1004trapBoardNumber}
	STATUS current
	--&FILTNAME    "PM1004 Fuse A Fail ON"
	--&ACTIONS     { log, major }
	--&MATCH       { pm1004AlmDefFuseB "*", pm1004AlmDefFuseA "on", pm1004trapBoardNumber "$3"}
	--&MESG        "Power Input A Fail on PM1004 in Slot $3 ($A)"

	--&FILTNAME    "PM1004 Fuse B Fail ON"
	--&ACTIONS     { log, major }
	--&MATCH       { pm1004AlmDefFuseB "on", pm1004AlmDefFuseA "*", pm1004trapBoardNumber "$3"}
	--&MESG        "Power Input B Fail on PM1004 in Slot $3 ($A)"
	DESCRIPTION "Urgent power supply default is activated"
	::= { pm1004traps 50 }

pm1004PowerTrapUrgentGoesOff NOTIFICATION-TYPE
	OBJECTS {pm1004AlmDefFuseB, pm1004AlmDefFuseA , pm1004trapBoardNumber}
	STATUS current
	--&FILTNAME    "PM1004 Fuse A&B Fail OFF"
	--&ACTIONS     { log, normal}
	--&CLEARS      { "PM1004 Fuse A Fail ON", "PM1004 Fuse B Fail ON" }
	--&MATCH       { pm1004AlmDefFuseB "on", pm1004AlmDefFuseA "on", pm1004trapBoardNumber "$3"}
	--&MESG        "Power Inputs A and B Present on PM1004 in Slot $3 ($A)"
	DESCRIPTION "Urgent power supply default disappeared"
	::= { pm1004traps 51 }






END
