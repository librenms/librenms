-- *****************************************************************
-- EKINOPS-Pm1008DCP.TXT:  MIB
--
--MIB Part Number:3MI00014AJAF
--MIB Version:02
--
-- Copyright (c) 2016 by Ekinops
-- All rights reserved.
-- 
-- *****************************************************************

EKINOPS-Pm1008DCP-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress                
        		FROM SNMPv2-SMI
 	TEXTUAL-CONVENTION,
	DisplayString
                FROM SNMPv2-TC;

modulePm1008dcp MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.net"
        DESCRIPTION
          "MIB for managing Ekinops modules with PM1008DCP software"
	REVISION "200803110000Z"
	DESCRIPTION
	  "Initial Version."
	REVISION "200804080000Z"
	DESCRIPTION
	  "DCC control - a comment change"
	REVISION "200805220000Z"
	DESCRIPTION
	  "Invert values in Pm1008dcpProtectionTimeSlot"
	REVISION "200805300000Z"
	DESCRIPTION
	  "Add OTX-TLH features"
	REVISION "200812030000Z"
	DESCRIPTION
	  "DCC storm info suppress"
	REVISION "200812040000Z"
	DESCRIPTION
	  "Cosmetics for mib compilers"
	REVISION "200906240000Z"
	DESCRIPTION
	  "CondType parameters insertion"
	REVISION "201002090000Z"
	DESCRIPTION
	  "XFP-T and OTX-VLH parameters"
	REVISION "201002170000Z"
	DESCRIPTION
	  "Probcause,AlarmType - NMS"
	REVISION "201003180000Z"
	DESCRIPTION
	  "OTX-VLH Reset"
	REVISION "201011100000Z"
	DESCRIPTION
	  "Formulas in comments and Event on XFP init"
	REVISION "201207020000Z"
	DESCRIPTION
	  "Minor cosmetic updates"
	REVISION "201304020000Z"
	DESCRIPTION
	  "S1,K1,K2 suppress"
	REVISION "201403250000Z"
	DESCRIPTION
	  "Probcause,AlarmType - NMS completion"
	REVISION "201501140000Z"
	DESCRIPTION
	  "Add Loopback objects"
	REVISION "201501140000Z"
	DESCRIPTION
	  "Labels cosmetic updates"
	REVISION "201605190000Z"
	DESCRIPTION
	  "New AlarmType - synthesisAlarm(12)"
	REVISION "201606020000Z"
	DESCRIPTION
	  "Capabilities objects of Table 5"
        ::= { ekinops 27 }



--- *****************************************************
---     LEAF LEVEL 2
--- *****************************************************


pm1008dcpalarms OBJECT IDENTIFIER ::= { modulePm1008dcp 2 }	
pm1008dcpAlmOther OBJECT IDENTIFIER ::= { pm1008dcpalarms 1 }
pm1008dcpAlmOtherNurg OBJECT IDENTIFIER ::= { pm1008dcpAlmOther 1 }
pm1008dcpAlmOtherUrg OBJECT IDENTIFIER ::= { pm1008dcpAlmOther 2 }
pm1008dcpAlmOtherCrit OBJECT IDENTIFIER ::= { pm1008dcpAlmOther 3 }

pm1008dcpAlmClient OBJECT IDENTIFIER ::= { pm1008dcpalarms 2 }
pm1008dcpAlmClientNurg OBJECT IDENTIFIER ::= { pm1008dcpAlmClient 1 }
pm1008dcpAlmClientUrg OBJECT IDENTIFIER ::= { pm1008dcpAlmClient 2 }
pm1008dcpAlmClientCrit OBJECT IDENTIFIER ::= { pm1008dcpAlmClient 3 }
	
pm1008dcpAlmLine OBJECT IDENTIFIER ::= { pm1008dcpalarms 3 }
pm1008dcpAlmLineNurg OBJECT IDENTIFIER ::= { pm1008dcpAlmLine 1 }
pm1008dcpAlmLineUrg OBJECT IDENTIFIER ::= { pm1008dcpAlmLine 2 }
pm1008dcpAlmLineCrit OBJECT IDENTIFIER ::= { pm1008dcpAlmLine 3 }





pm1008dcpmeasures OBJECT IDENTIFIER ::= { modulePm1008dcp 3 }	
pm1008dcpMesrOther OBJECT IDENTIFIER ::= { pm1008dcpmeasures 1 }	
pm1008dcpMesrClient OBJECT IDENTIFIER ::= { pm1008dcpmeasures 2 }	
pm1008dcpMesrLine OBJECT IDENTIFIER ::= { pm1008dcpmeasures 3 }	




pm1008dcpcounters OBJECT IDENTIFIER ::= { modulePm1008dcp 4 }
pm1008dcpCntOther OBJECT IDENTIFIER ::= { pm1008dcpcounters 1 }
pm1008dcpCntClient OBJECT IDENTIFIER ::= { pm1008dcpcounters 2 }
pm1008dcpCntLine OBJECT IDENTIFIER ::= { pm1008dcpcounters 3 }


pm1008dcpcontrolsWrite OBJECT IDENTIFIER ::= { modulePm1008dcp 6 }
pm1008dcpCtrlOther OBJECT IDENTIFIER ::= { pm1008dcpcontrolsWrite 1 }
pm1008dcpCtrlClient OBJECT IDENTIFIER ::= { pm1008dcpcontrolsWrite 2 }
pm1008dcpCtrlLine OBJECT IDENTIFIER ::= { pm1008dcpcontrolsWrite 3 }

pm1008dcpri OBJECT IDENTIFIER ::= { modulePm1008dcp 7 }
pm1008dcpriTable OBJECT IDENTIFIER ::= { pm1008dcpri 1 }

pm1008dcpdownload OBJECT IDENTIFIER ::= { modulePm1008dcp 8 }
pm1008dcpDwlOther OBJECT IDENTIFIER ::= { pm1008dcpdownload 1 }
pm1008dcpDwlClient OBJECT IDENTIFIER ::= { pm1008dcpdownload 2 }
pm1008dcpDwlLine OBJECT IDENTIFIER ::= { pm1008dcpdownload 3 }


pm1008dcpConfig OBJECT IDENTIFIER ::= { modulePm1008dcp 9 }

pm1008dcptraps OBJECT IDENTIFIER ::= { modulePm1008dcp 10 }



pm1008dcpMonitoring OBJECT IDENTIFIER ::= { modulePm1008dcp 11}

pm1008dcpMonOther OBJECT IDENTIFIER ::= { pm1008dcpMonitoring 1 }
pm1008dcpMonRmon OBJECT IDENTIFIER ::= { pm1008dcpMonOther 3 }

pm1008dcpMonClient OBJECT IDENTIFIER ::= { pm1008dcpMonitoring 2 }
pm1008dcpMonClientRmonCounter OBJECT IDENTIFIER ::= { pm1008dcpMonClient 4 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pm1008dcpModeTimeSlot ::= TEXTUAL-CONVENTION
    STATUS      current
    DESCRIPTION "different mode for time slot"
    SYNTAX INTEGER {
		dualPassThrough(1),
		addDropTsA(2),
		addDropTsB(4),
		splitSelectTsA(8),
		splitSelectTsB(16),
		splitSelectTsATsB(32)
           }

Pm1008dcpModeAddDropA ::= TEXTUAL-CONVENTION
    STATUS      current
    DESCRIPTION "different mode for client A"
    SYNTAX INTEGER {
		passThroughA(1),
		addDropTsA(2),
		splitSelectTsA(4)
           }

Pm1008dcpModeAddDrop ::= TEXTUAL-CONVENTION
    STATUS      current
    DESCRIPTION "different mode for client B"
    SYNTAX INTEGER {
		dualPassThrough(1),
		addDropTsA(2),
		addDropTsB(4),
		splitSelectTsA(8),
		splitSelectTsB(16),
		splitSelectTsATsB(32)
           }


Pm1008dcpProtectionTimeSlot ::= TEXTUAL-CONVENTION
    STATUS      current
    DESCRIPTION "protection for control"
    SYNTAX INTEGER {
		auto(0),
		manualX1Line1(257),
		manualX2Line2(513)
           }

Pm1008dcpProtectionStartUp ::= TEXTUAL-CONVENTION
    STATUS      current
    DESCRIPTION "protection for startup"
    SYNTAX INTEGER {
		auto(2),
		manualX2Line2(0),
		manualX1Line1(1)
           }


Pm1008dcpDccMode ::= TEXTUAL-CONVENTION
    STATUS      current
    DESCRIPTION "Mode for DCC"
    SYNTAX INTEGER {
		dccNo(0),
		dcctermLine1(1),
		dcctermLine2(2),
		dcctermLines12(3),
		dccmaster(4),
		dccslaveLine12(7)
           }

Pm1008dcpOtxMode ::= TEXTUAL-CONVENTION
    STATUS      current
    DESCRIPTION "Different modes on OTX-TLH on client and line ports"
    SYNTAX INTEGER {
		otx80mode(1),
		otx60mode(2),
		otxadjustmode(4)
           }

Pm1008dcpOtxGrid ::= TEXTUAL-CONVENTION
    STATUS      current
    DESCRIPTION "Different grids on OTX-TLH on client and line ports"
    SYNTAX INTEGER {
		otxgrid200(200),
		otxgrid100(100),
		otxgrid50(50)
           }

Pm1008dcpAdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm1008dcpOtxChannel ::= TEXTUAL-CONVENTION
    STATUS      current
    DESCRIPTION "Channel selection on OTX-TLH on client and line ports"
    SYNTAX INTEGER 


--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm1008dcpRinvReloadInventory OBJECT-TYPE
  SYNTAX EkiOnOff
  MAX-ACCESS read-write
  STATUS current
  DESCRIPTION
        "Reload the inventory: This OID triggers an 
         inventory reload."
  ::= { pm1008dcpri 2 }

pm1008dcpRinvHwPlatform OBJECT-TYPE
  SYNTAX DisplayString
  MAX-ACCESS read-only
  STATUS current
  DESCRIPTION
        "HW platform description: This OID contains the 
         description of the Hardware platform."
  ::= { pm1008dcpri 3 }
  
pm1008dcpRinvModulePlatform OBJECT-TYPE
  SYNTAX DisplayString
  MAX-ACCESS read-only
  STATUS current
  DESCRIPTION
        "Module platform description: This OID contains the 
         description of the Module."
  ::= { pm1008dcpri 4 }
  
pm1008dcpRinvSwPlatform OBJECT-TYPE
  SYNTAX DisplayString
  MAX-ACCESS read-only
  STATUS current
  DESCRIPTION
        "SW platform description: This OID contains the 
         description of the Software platform."
  ::= { pm1008dcpri 5 }
  
pm1008dcpRinvGwPlatform OBJECT-TYPE
  SYNTAX DisplayString
  MAX-ACCESS read-only
  STATUS current
  DESCRIPTION
        "GW platform desciption: This OID contains the 
         description of the Gateware platform."
  ::= { pm1008dcpri 6 }


pm1008dcpRinvSfpTable OBJECT-TYPE
      SYNTAX  SEQUENCE OF Pm1008dcpRinvSfpEntry
      MAX-ACCESS  not-accessible
      STATUS  current
      DESCRIPTION
              "List of the SFPs on the selected module"
      ::= { pm1008dcpriTable 1 }

pm1008dcpRinvSfpEntry OBJECT-TYPE
        SYNTAX  Pm1008dcpRinvSfpEntry
        MAX-ACCESS  not-accessible
        STATUS  current
        DESCRIPTION
              "Row definition for the SFP table"
        INDEX   { pm1008dcpRinvSfpIndex }
        ::= { pm1008dcpRinvSfpTable 1 }
    


Pm1008dcpRinvSfpEntry::=
        SEQUENCE {
          pm1008dcpRinvSfpIndex 
              Integer32,
          pm1008dcpRinvsfp
              DisplayString
        }


    pm1008dcpRinvSfpIndex OBJECT-TYPE
        SYNTAX  Integer32(1..16)
        MAX-ACCESS  read-only
        STATUS  current
        DESCRIPTION
              "Index for SFP table"
        ::= { pm1008dcpRinvSfpEntry 1 }


    pm1008dcpRinvsfp OBJECT-TYPE
        SYNTAX  DisplayString
        MAX-ACCESS  read-only
        STATUS  current
        DESCRIPTION
              "Inventory for the SFP: This OID contains the inventory for the SFP"
        ::= { pm1008dcpRinvSfpEntry 2 }




pm1008dcpRinvLineTable OBJECT-TYPE
      SYNTAX  SEQUENCE OF Pm1008dcpRinvLineEntry
      MAX-ACCESS  not-accessible
      STATUS  current
      DESCRIPTION
              "List of the XFPs on the selected module"
      ::= { pm1008dcpriTable 2 }

pm1008dcpRinvLineEntry OBJECT-TYPE
        SYNTAX  Pm1008dcpRinvLineEntry
        MAX-ACCESS  not-accessible
        STATUS  current
        DESCRIPTION
              "Row definition for the XFP table"
        INDEX   { pm1008dcpRinvLineIndex }
        ::= { pm1008dcpRinvLineTable 1 }
    


Pm1008dcpRinvLineEntry::=
        SEQUENCE {
          pm1008dcpRinvLineIndex 
              Integer32,
          pm1008dcpRinvxfpLine
              DisplayString
        }


    pm1008dcpRinvLineIndex OBJECT-TYPE
        SYNTAX  Integer32(1..16)
        MAX-ACCESS  read-only
        STATUS  current
        DESCRIPTION
              "Index for XFP table"
        ::= { pm1008dcpRinvLineEntry 1 }


    pm1008dcpRinvxfpLine OBJECT-TYPE
        SYNTAX  DisplayString
        MAX-ACCESS  read-only
        STATUS  current
        DESCRIPTION
              "Inventory for the XFP: This OID contains the inventory for the XFP"
        ::= { pm1008dcpRinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm1008dcpAlmsynthAlm0 OBJECT IDENTIFIER ::= { pm1008dcpAlmOtherCrit 0 }




pm1008dcpAlmDefFuseB OBJECT-TYPE
	  SYNTAX EkiOnOff
	  MAX-ACCESS read-only
	  STATUS current
	  DESCRIPTION
        "
        Fuse B Fail :This OID indicates 
        that the fuse of the power input 
        B is in fail condition  <Help>
          Status of the Fuse B <Condtype> 
        DEF_FUSE_B <Probcause> powerProblem 
        (36) <Alarmtype> equipmentAlarm 
        (5) <Polarity> (2) 
        "
	  ::= { pm1008dcpAlmsynthAlm0 16 }



pm1008dcpAlmDefFuseA OBJECT-TYPE
	  SYNTAX EkiOnOff
	  MAX-ACCESS read-only
	  STATUS current
	  DESCRIPTION
        "
        Fuse A Fail :This OID indicates 
        that the fuse of the power input 
        A is in fail condition  <Help>
          Status of the Fuse A <Condtype> 
        DEF_FUSE_A <Probcause> powerProblem 
        (36) <Alarmtype> equipmentAlarm 
        (5) <Polarity> (2) 
        "
	  ::= { pm1008dcpAlmsynthAlm0 15 }



pm1008dcpAlmModGlobFail OBJECT-TYPE
	  SYNTAX EkiOnOff
	  MAX-ACCESS read-only
	  STATUS current
	  DESCRIPTION
        "
        Module Failure :This OID is set 
        on detection of a failure originating 
        from the PM <Condtype> MOD_GLOB_FAIL 
        <Probcause> equipmentMalfunction 
        (16) <Alarmtype> synthesisAlarm 
        (12) <Polarity> (2) 
        "
	  ::= { pm1008dcpAlmsynthAlm0 9 }



--- *****************************************************
---     LEAF for the synthAlm2 article
--- *****************************************************
pm1008dcpAlmsynthAlm2 OBJECT IDENTIFIER ::= { pm1008dcpAlmOtherNurg 2 }




pm1008dcpAlmMaintenanceOn OBJECT-TYPE
	  SYNTAX EkiOnOff
	  MAX-ACCESS read-only
	  STATUS current
	  DESCRIPTION
        "
        Maintenance Mode :This OID indicates 
        that the PM is in maintenance mode. 
         <Help>  This alarm indicates that 
        the maintenance mode is enabled 
        on the PM <Condtype> MAINTENANCE_ON 
        <Probcause> other (1) <Alarmtype> 
        other (1) <Polarity> (2) 
        "
	  ::= { pm1008dcpAlmsynthAlm2 5 }



pm1008dcpAlmCorrelatOff OBJECT-TYPE
	  SYNTAX EkiOnOff
	  MAX-ACCESS read-only
	  STATUS current
	  DESCRIPTION
        "
        Not Used :This OID, when set,
         indicates that alarm correlation 
        is not being performed. <Condtype> 
        CORRELAT_OFF <Probcause> other
         (1) <Alarmtype> other (1) <Polarity> 
        (2) 
        "
	  ::= { pm1008dcpAlmsynthAlm2 4 }



pm1008dcpAlmConfTableLoad OBJECT-TYPE
	  SYNTAX EkiOnOff
	  MAX-ACCESS read-only
	  STATUS current
	  DESCRIPTION
        "
        PM Configuration Load :This OID 
         is at 1 during the loading of
         configuration tables in the modules 
        RAM. <Condtype> CONF_TABLE_LOAD 
        <Probcause> other (1) <Alarmtype> 
        other (1) <Polarity> (2) 
        "
	  ::= { pm1008dcpAlmsynthAlm2 3 }



pm1008dcpAlmInvUpload OBJECT-TYPE
	  SYNTAX EkiOnOff
	  MAX-ACCESS read-only
	  STATUS current
	  DESCRIPTION
        "
        Inventory Upload :This OID is
         at 1 during the uploading of PM 
        inventory information. <Condtype> 
        INV_UPLOAD <Probcause> other (1) 
        <Alarmtype> other (1) <Polarity> 
        (2) 
        "
	  ::= { pm1008dcpAlmsynthAlm2 2 }



pm1008dcpAlmConfTableSave OBJECT-TYPE
	  SYNTAX EkiOnOff
	  MAX-ACCESS read-only
	  STATUS current
	  DESCRIPTION
        "
        PM Configuration Save :This OID 
        is at 1 during the saving of a
         new configuration table in the 
        module Flash memory. <Condtype> 
        CONF_TABLE_SAVE <Probcause> other 
        (1) <Alarmtype> other (1) <Polarity> 
        (2) 
        "
	  ::= { pm1008dcpAlmsynthAlm2 1 }



--- *********************************************************
---     TABLE for the pm1008dcpAlmsynthAlmLine articles
--- *********************************************************

pm1008dcpAlmsynthAlmLineTable OBJECT-TYPE
	SYNTAX  SEQUENCE OF Pm1008dcpAlmsynthAlmLineEntry
	MAX-ACCESS not-accessible
	STATUS current
	DESCRIPTION
        "
        List of pm1008dcpAlmsynthAlmLine 
        Article
        "
	::= { pm1008dcpAlmLineCrit 7 }


pm1008dcpAlmsynthAlmLineEntry OBJECT-TYPE
	SYNTAX Pm1008dcpAlmsynthAlmLineEntry
	MAX-ACCESS not-accessible
	STATUS current
	DESCRIPTION
        "
        Row definition for the pm1008dcpAlmsynthAlmLine 
        table
        "
	INDEX   { pm1008dcpAlmsynthAlmLineIndex }
	::= { pm1008dcpAlmsynthAlmLineTable 1 }


Pm1008dcpAlmsynthAlmLineEntry ::=
	SEQUENCE {
	pm1008dcpAlmsynthAlmLineIndex
		INTEGER,
	pm1008dcpAlmLineFailPortn
		EkiOnOff,
	pm1008dcpAlmLineDdmAlmPortn
		EkiOnOff,
	pm1008dcpAlmLineDdmWarningPortn
		EkiOnOff,
	pm1008dcpAlmUpRdiInsPortn
		EkiOnOff,
	pm1008dcpAlmLineLocalOosPortn
		EkiOnOff,
	pm1008dcpAlmXfpTxOffPortn
		EkiOnOff,
	pm1008dcpAlmLineHwFailPortn
		EkiOnOff,
	pm1008dcpAlmXfpInitNotComplPortn
		EkiOnOff,
	pm1008dcpAlmXfpAbsentPortn
		EkiOnOff
	}


pm1008dcpAlmsynthAlmLineIndex OBJECT-TYPE
	SYNTAX  INTEGER(0..128)
	MAX-ACCESS  read-only
	STATUS current
	DESCRIPTION
        "
        Index definition for the pm1008dcpAlmsynthAlmLine 
        table
        "
	::= { pm1008dcpAlmsynthAlmLineEntry 1 }


pm1008dcpAlmLineFailPortn OBJECT-TYPE
	SYNTAX  EkiOnOff
	MAX-ACCESS read-only
	STATUS current
	DESCRIPTION
        "
        Line Port Failure :This OID indicates 
        a failure on the line port <Condtype> 
        LINE_FAIL <Probcause> equipmentMalfunction 
        (16) <Alarmtype> synthesisAlarm 
        (12) <Polarity> (2) 
        "
	::= { pm1008dcpAlmsynthAlmLineEntry 13 }


pm1008dcpAlmLineDdmAlmPortn OBJECT-TYPE
	SYNTAX  EkiOnOff
	MAX-ACCESS read-only
	STATUS current
	DESCRIPTION
        "
        Alarm On Line Optical Module DDM 
        :This OID indicates an alarm is 
        present coming out of Line optical 
        interface DDM  <Help>  This alarm 
        indicates if a DDM Alarm has been 
        detected on the line transceiver 
        <Condtype> LINE_DDM_ALM <Probcause> 
        equipmentMalfunction (16) <Alarmtype> 
        synthesisAlarm (12) <Polarity>
         (2) 
        "
	::= { pm1008dcpAlmsynthAlmLineEntry 11 }


pm1008dcpAlmLineDdmWarningPortn OBJECT-TYPE
	SYNTAX  EkiOnOff
	MAX-ACCESS read-only
	STATUS current
	DESCRIPTION
        "
        Warning On Line Optical Module 
        DDM :This OID indicates a warning 
        is present coming out of Line optical 
        interface DDM  <Help>  This alarm 
        indicates if a DDM Warning has
         been detected on the line transceiver 
        <Condtype> LINE_DDM_WARNING <Probcause> 
        equipmentMalfunction (16) <Alarmtype> 
        synthesisAlarm (12) <Polarity>
         (2) 
        "
	::= { pm1008dcpAlmsynthAlmLineEntry 10 }


pm1008dcpAlmUpRdiInsPortn OBJECT-TYPE
	SYNTAX  EkiOnOff
	MAX-ACCESS read-only
	STATUS current
	DESCRIPTION
        "
        MS-RDI/L-RDI Inserted On Line
         :This OID indicates an upstream 
        MS-RDI/L-RDI has been inserted
         in the outgoing 10 Gb/s SDH/SONET 
        signal.   <Help>  This status indicates 
        if a MS-RDI/L-RDI is currently
         inserted on the line interface. 
        <Condtype> UP_RDI_INS <Probcause> 
        informationalStatus(1000) <Alarmtype> 
        other (1) <Polarity> (2) 
        "
	::= { pm1008dcpAlmsynthAlmLineEntry 9 }


pm1008dcpAlmLineLocalOosPortn OBJECT-TYPE
	SYNTAX  EkiOnOff
	MAX-ACCESS read-only
	STATUS current
	DESCRIPTION
        "
        Line Port In Service :This OID 
        indicates that the Line port is 
        In Service (1) of Out or Service 
        (2)  <Help>  This status indicates 
        if the line port is in service
         <Condtype> LINE_LOCAL_OOS <Probcause> 
        informationalStatus(1000) <Alarmtype> 
        other (1) <Polarity> (2) 
        "
	::= { pm1008dcpAlmsynthAlmLineEntry 7 }


pm1008dcpAlmXfpTxOffPortn OBJECT-TYPE
	SYNTAX  EkiOnOff
	MAX-ACCESS read-only
	STATUS current
	DESCRIPTION
        "
        Line Optical Module Laser Shutdown 
        :This OID indicates the line optical 
        output power is on  <Help>  This 
        status indicates if the line transceiver 
        laser is ON or OFF <Condtype> XFP_TX_OFF 
        <Probcause> other (1) <Alarmtype> 
        equipmentAlarm (5) <Polarity> (2) 
        "
	::= { pm1008dcpAlmsynthAlmLineEntry 6 }


pm1008dcpAlmLineHwFailPortn OBJECT-TYPE
	SYNTAX  EkiOnOff
	MAX-ACCESS read-only
	STATUS current
	DESCRIPTION
        "
        Line Port HW Failure :This OID 
        indicates a failure on line port, 
        most probably caused by a HW issue 
        <Condtype> LINE_HW_FAIL <Probcause> 
        equipmentMalfunction (16) <Alarmtype> 
        synthesisAlarm (12) <Polarity>
         (2) 
        "
	::= { pm1008dcpAlmsynthAlmLineEntry 5 }


pm1008dcpAlmXfpInitNotComplPortn OBJECT-TYPE
	SYNTAX  EkiOnOff
	MAX-ACCESS read-only
	STATUS current
	DESCRIPTION
        "
        Line Optical Module Ready :This 
        OID indicates that the optical
         interface (XFP or OTX) is not
         operational.  <Help>  This status 
        indicates if the line transceiver 
        has been correctly initialized
         <Condtype> XFP_INIT_NOT_COMPL
         <Probcause> equipmentMalfunction 
        (16) <Alarmtype> equipmentAlarm 
        (5) <Polarity> (2) <Event> ObjectCDINV
        "
	::= { pm1008dcpAlmsynthAlmLineEntry 3 }


pm1008dcpAlmXfpAbsentPortn OBJECT-TYPE
	SYNTAX  EkiOnOff
	MAX-ACCESS read-only
	STATUS current
	DESCRIPTION
        "
        Line Optical Module Absent :This 
        OID indicates that the line optical 
        interface (XFP or OTX) is not plugged 
        in.  <Help>  This alarm indicates 
        if the line transceiver is present. 
        <Condtype> XFP_ABSENT <Probcause> 
        inputOutputDeviceError (24) <Alarmtype> 
        equipmentAlarm (5) <Polarity> (2) 
        <Event> ObjectCDINV
        "
	::= { pm1008dcpAlmsynthAlmLineEntry 2 }


--- *********************************************************
---     TABLE for the pm1008dcpAlmsynthAlmPort articles
--- *********************************************************

pm1008dcpAlmsynthAlmPortTable OBJECT-TYPE
	SYNTAX  SEQUENCE OF Pm1008dcpAlmsynthAlmPortEntry
	MAX-ACCESS not-accessible
	STATUS current
	DESCRIPTION
        "
        List of pm1008dcpAlmsynthAlmPort 
        Article
        "
	::= { pm1008dcpAlmClientCrit 8 }


pm1008dcpAlmsynthAlmPortEntry OBJECT-TYPE
	SYNTAX Pm1008dcpAlmsynthAlmPortEntry
	MAX-ACCESS not-accessible
	STATUS current
	DESCRIPTION
        "
        Row definition for the pm1008dcpAlmsynthAlmPort 
        table
        "
	INDEX   { pm1008dcpAlmsynthAlmPortIndex }
	::= { pm1008dcpAlmsynthAlmPortTable 1 }


Pm1008dcpAlmsynthAlmPortEntry ::=
	SEQUENCE {
	pm1008dcpAlmsynthAlmPortIndex
		INTEGER,
	pm1008dcpAlmUpCsfPortn
		EkiOnOff,
	pm1008dcpAlmClientActivePortn
		EkiOnOff,
	pm1008dcpAlmFailAccPortn
		EkiOnOff,
	pm1008dcpAlmSfpDdmAlmPortn
		EkiOnOff,
	pm1008dcpAlmSfpDdmWarningPortn
		EkiOnOff,
	pm1008dcpAlmDwCaisPortn
		EkiOnOff,
	pm1008dcpAlmClientRemoteOosPortn
		EkiOnOff,
	pm1008dcpAlmClientLocalOosPortn
		EkiOnOff,
	pm1008dcpAlmDwLsdPortn
		EkiOnOff,
	pm1008dcpAlmHwFailAccPortn
		EkiOnOff,
	pm1008dcpAlmDdmAbsentPortn
		EkiOnOff,
	pm1008dcpAlmSfpAbsentPortn
		EkiOnOff
	}


pm1008dcpAlmsynthAlmPortIndex OBJECT-TYPE
	SYNTAX  INTEGER(0..128)
	MAX-ACCESS  read-only
	STATUS current
	DESCRIPTION
        "
        Index definition for the pm1008dcpAlmsynthAlmPort 
        table
        "
	::= { pm1008dcpAlmsynthAlmPortEntry 1 }


pm1008dcpAlmUpCsfPortn OBJECT-TYPE
	SYNTAX  EkiOnOff
	MAX-ACCESS read-only
	STATUS current
	DESCRIPTION
        "
        Client Signal Fail Inserted :This 
        OID indicates a CSF has been inserted 
        in the upstream client port.  <Help> 
         This status indicates if a Client 
        Signal Fail is currently inserted 
        on the line signal for this client 
        port <Condtype> UP_CSF_1 <Probcause> 
        other (1) <Alarmtype> other (1) 
        <Polarity> (2) 
        "
	::= { pm1008dcpAlmsynthAlmPortEntry 17 }


pm1008dcpAlmClientActivePortn OBJECT-TYPE
	SYNTAX  EkiOnOff
	MAX-ACCESS read-only
	STATUS current
	DESCRIPTION
        "
        Client Sink (Line1 Or Line2) :This 
        bit indicates the Client #n is
         active on receive side  <Help> 
         This status indicates whether
         the Client is extracted from Line 
        1 or Line 2. <Condtype> CLIENT_ACTIVE 
        <Probcause> other (1) <Alarmtype> 
        other (1) <Polarity> (2) 
        "
	::= { pm1008dcpAlmsynthAlmPortEntry 16 }


pm1008dcpAlmFailAccPortn OBJECT-TYPE
	SYNTAX  EkiOnOff
	MAX-ACCESS read-only
	STATUS current
	DESCRIPTION
        "
        Client Access Fail :This OID indicates 
        a failure on the Client port <Condtype> 
        FAIL_ACC_1 <Probcause> equipmentMalfunction 
        (16) <Alarmtype> synthesisAlarm 
        (12) <Polarity> (2) 
        "
	::= { pm1008dcpAlmsynthAlmPortEntry 13 }


pm1008dcpAlmSfpDdmAlmPortn OBJECT-TYPE
	SYNTAX  EkiOnOff
	MAX-ACCESS read-only
	STATUS current
	DESCRIPTION
        "
        Alarm On Client SFP DDM :This
         OID indicates an alarm is being 
        received from the Client SFP DDM 
         <Help>  This alarm indicates if 
        a DDM Alarm has been detected on 
        the client transceiver <Condtype> 
        SFP_DDM_ALM_1 <Probcause> equipmentMalfunction 
        (16) <Alarmtype> synthesisAlarm 
        (12) <Polarity> (2) 
        "
	::= { pm1008dcpAlmsynthAlmPortEntry 11 }


pm1008dcpAlmSfpDdmWarningPortn OBJECT-TYPE
	SYNTAX  EkiOnOff
	MAX-ACCESS read-only
	STATUS current
	DESCRIPTION
        "
        Warning On Client SFP DDM :This 
        OID indicates a warning is being 
        received from the Client SFP DDM 
         <Help>  This alarm indicates if 
        a DDM Warning has been detected 
        on the client transceiver <Condtype> 
        SFP_DDM_WARNING_1 <Probcause> equipmentMalfunction 
        (16) <Alarmtype> synthesisAlarm 
        (12) <Polarity> (2) 
        "
	::= { pm1008dcpAlmsynthAlmPortEntry 10 }


pm1008dcpAlmDwCaisPortn OBJECT-TYPE
	SYNTAX  EkiOnOff
	MAX-ACCESS read-only
	STATUS current
	DESCRIPTION
        "
        Client AIS Inserted :This OID
         indicates a CAIS has been inserted 
        on the output client port.  <Help> 
         This status indictaes if a Client 
        Alarm Indication Signal is currently 
        inserted on the client interface 
        <Condtype> DW_CAIS_1 <Probcause> 
        informationalStatus(1000) <Alarmtype> 
        other (1) <Polarity> (2) 
        "
	::= { pm1008dcpAlmsynthAlmPortEntry 9 }


pm1008dcpAlmClientRemoteOosPortn OBJECT-TYPE
	SYNTAX  EkiOnOff
	MAX-ACCESS read-only
	STATUS current
	DESCRIPTION
        "
        Remote Client Port In Service
         :This OID indicates that the remote 
        Client port is In Service (1) or 
        Out of Service (2)  <Help>  This 
        status indicates if the remote
         client port is in service <Condtype> 
        CLIENT_REMOTE_OOS <Probcause> informationalStatus(1000) 
        <Alarmtype> other (1) <Polarity> 
        (2) 
        "
	::= { pm1008dcpAlmsynthAlmPortEntry 8 }


pm1008dcpAlmClientLocalOosPortn OBJECT-TYPE
	SYNTAX  EkiOnOff
	MAX-ACCESS read-only
	STATUS current
	DESCRIPTION
        "
        Local Client Port In Service :This 
        OID indicates that the local Client 
        port is In Service (1) or Out of 
        Service (2)  <Help>  This status 
        indicates if the local client port 
        is in service <Condtype> CLIENT_LOCAL_OOS 
        <Probcause> informationalStatus(1000) 
        <Alarmtype> other (1) <Polarity> 
        (2) 
        "
	::= { pm1008dcpAlmsynthAlmPortEntry 7 }


pm1008dcpAlmDwLsdPortn OBJECT-TYPE
	SYNTAX  EkiOnOff
	MAX-ACCESS read-only
	STATUS current
	DESCRIPTION
        "
        Client SFP Laser Shutdown :This 
        OID indicates the Client SFP transmitter 
        output is ON.   <Help>  This status 
        indicates if the client transceiver 
        laser is ON or OFF <Condtype> DW_LSD_1 
        <Probcause> other (1) <Alarmtype> 
        equipmentAlarm (5) <Polarity> (2) 
        "
	::= { pm1008dcpAlmsynthAlmPortEntry 6 }


pm1008dcpAlmHwFailAccPortn OBJECT-TYPE
	SYNTAX  EkiOnOff
	MAX-ACCESS read-only
	STATUS current
	DESCRIPTION
        "
        Client HW Fail :This OID indicates 
        a failure on client port, most
         probably caused by a HW issue. 
        <Condtype> HW_FAIL_ACC_1 <Probcause> 
        equipmentMalfunction (16) <Alarmtype> 
        synthesisAlarm (12) <Polarity>
         (2) 
        "
	::= { pm1008dcpAlmsynthAlmPortEntry 5 }


pm1008dcpAlmDdmAbsentPortn OBJECT-TYPE
	SYNTAX  EkiOnOff
	MAX-ACCESS read-only
	STATUS current
	DESCRIPTION
        "
        DDM Supported On Client SFP :This 
        OID indicates that the Client SFP 
        module supports the Digital Diagnostic 
        Monitoring function  <Help>  This 
        status indicates if the client
         transceiver includes the DDM feature 
        <Condtype> DDM_ABSENT_1 <Probcause> 
        informationalStatus(1000) <Alarmtype> 
        other (1) <Polarity> (2) 
        "
	::= { pm1008dcpAlmsynthAlmPortEntry 3 }


pm1008dcpAlmSfpAbsentPortn OBJECT-TYPE
	SYNTAX  EkiOnOff
	MAX-ACCESS read-only
	STATUS current
	DESCRIPTION
        "
        Client SFP Absent :This OID indicates 
        that the SFP module is not present 
        in the client port.  <Help>  This 
        alarm indicates if the client transceiver 
        is present. <Condtype> SFP_ABSENT_1 
        <Probcause> inputOutputDeviceError 
        (24) <Alarmtype> equipmentAlarm 
        (5) <Polarity> (2) <Event> ObjectCDINV
        "
	::= { pm1008dcpAlmsynthAlmPortEntry 2 }


--- *********************************************************
---     TABLE for the pm1008dcpAlmaccessioAlm articles
--- *********************************************************

pm1008dcpAlmaccessioAlmTable OBJECT-TYPE
	SYNTAX  SEQUENCE OF Pm1008dcpAlmaccessioAlmEntry
	MAX-ACCESS not-accessible
	STATUS current
	DESCRIPTION
        "
        List of pm1008dcpAlmaccessioAlm 
        Article
        "
	::= { pm1008dcpAlmClientCrit 16 }


pm1008dcpAlmaccessioAlmEntry OBJECT-TYPE
	SYNTAX Pm1008dcpAlmaccessioAlmEntry
	MAX-ACCESS not-accessible
	STATUS current
	DESCRIPTION
        "
        Row definition for the pm1008dcpAlmaccessioAlm 
        table
        "
	INDEX   { pm1008dcpAlmaccessioAlmIndex }
	::= { pm1008dcpAlmaccessioAlmTable 1 }


Pm1008dcpAlmaccessioAlmEntry ::=
	SEQUENCE {
	pm1008dcpAlmaccessioAlmIndex
		INTEGER,
	pm1008dcpAlmUpLosPortn
		EkiOnOff,
	pm1008dcpAlmDwLasFailPortn
		EkiOnOff
	}


pm1008dcpAlmaccessioAlmIndex OBJECT-TYPE
	SYNTAX  INTEGER(0..128)
	MAX-ACCESS  read-only
	STATUS current
	DESCRIPTION
        "
        Index definition for the pm1008dcpAlmaccessioAlm 
        table
        "
	::= { pm1008dcpAlmaccessioAlmEntry 1 }


pm1008dcpAlmUpLosPortn OBJECT-TYPE
	SYNTAX  EkiOnOff
	MAX-ACCESS read-only
	STATUS current
	DESCRIPTION
        "
        Client Input Loss Of Signal :This 
        OID indicates that no signal is 
        present on the SFP of the client 
        port  <Help>  This alarm indicates 
        if an optical signal is detected 
        on the client transceiver input 
        <Condtype> UP_LOS_1 <Probcause> 
        receiveFailure (41) <Alarmtype> 
        physicalViolation (9) <Polarity> 
        (2) 
        "
	::= { pm1008dcpAlmaccessioAlmEntry 5 }


pm1008dcpAlmDwLasFailPortn OBJECT-TYPE
	SYNTAX  EkiOnOff
	MAX-ACCESS read-only
	STATUS current
	DESCRIPTION
        "
        Client SFP Tx Failed :This OID 
        indicates that the transmitter
         fails for the SFP plugged into 
        the client port (this alarm reports 
        the transmitter failure alarm generated 
        by the SFPs)  <Help>  This alarm 
        indicates if the laser of the client 
        transceiver is in fail condition 
        <Condtype> DW_LAS_FAIL_1 <Probcause> 
        transmitterFailure (56) <Alarmtype> 
        equipmentAlarm (5) <Polarity> (2) 
        "
	::= { pm1008dcpAlmaccessioAlmEntry 2 }


--- *********************************************************
---     TABLE for the pm1008dcpAlmsfpAlmDdm articles
--- *********************************************************

pm1008dcpAlmsfpAlmDdmTable OBJECT-TYPE
	SYNTAX  SEQUENCE OF Pm1008dcpAlmsfpAlmDdmEntry
	MAX-ACCESS not-accessible
	STATUS current
	DESCRIPTION
        "
        List of pm1008dcpAlmsfpAlmDdm
         Article
        "
	::= { pm1008dcpAlmClientUrg 32 }


pm1008dcpAlmsfpAlmDdmEntry OBJECT-TYPE
	SYNTAX Pm1008dcpAlmsfpAlmDdmEntry
	MAX-ACCESS not-accessible
	STATUS current
	DESCRIPTION
        "
        Row definition for the pm1008dcpAlmsfpAlmDdm 
        table
        "
	INDEX   { pm1008dcpAlmsfpAlmDdmIndex }
	::= { pm1008dcpAlmsfpAlmDdmTable 1 }


Pm1008dcpAlmsfpAlmDdmEntry ::=
	SEQUENCE {
	pm1008dcpAlmsfpAlmDdmIndex
		INTEGER,
	pm1008dcpAlmRxPwrHighAlaPortn
		EkiOnOff,
	pm1008dcpAlmRxPwrLowAlaPortn
		EkiOnOff,
	pm1008dcpAlmTempHighAlaPortn
		EkiOnOff,
	pm1008dcpAlmTempLowAlaPortn
		EkiOnOff,
	pm1008dcpAlmVccHighAlaPortn
		EkiOnOff,
	pm1008dcpAlmVccLowAlaPortn
		EkiOnOff,
	pm1008dcpAlmTxBiasHighAlaPortn
		EkiOnOff,
	pm1008dcpAlmTxBiasLowAlaPortn
		EkiOnOff,
	pm1008dcpAlmTxPwrHighAlaPortn
		EkiOnOff,
	pm1008dcpAlmTxPwrLowAlaPortn
		EkiOnOff
	}


pm1008dcpAlmsfpAlmDdmIndex OBJECT-TYPE
	SYNTAX  INTEGER(0..128)
	MAX-ACCESS  read-only
	STATUS current
	DESCRIPTION
        "
        Index definition for the pm1008dcpAlmsfpAlmDdm 
        table
        "
	::= { pm1008dcpAlmsfpAlmDdmEntry 1 }


pm1008dcpAlmRxPwrHighAlaPortn OBJECT-TYPE
	SYNTAX  EkiOnOff
	MAX-ACCESS read-only
	STATUS current
	DESCRIPTION
        "
        Client SFP Rx Power High :Alarm 
        indicating that the SFP input power 
        of port is higher than the threshold 
        value written in the SFP EEPROM 
        <Condtype> RX_PWR_HIGH_ALA_1 <Probcause> 
        receiveFailure (41) <Alarmtype> 
        equipmentAlarm (5) <Polarity> (2) 
        "
	::= { pm1008dcpAlmsfpAlmDdmEntry 17 }


pm1008dcpAlmRxPwrLowAlaPortn OBJECT-TYPE
	SYNTAX  EkiOnOff
	MAX-ACCESS read-only
	STATUS current
	DESCRIPTION
        "
        Client SFP Rx Power Low :Alarm 
        indicating that the SFP input power 
        of port is lower than the threshold 
        value written in the SFP EEPROM 
        <Condtype> RX_PWR_LOW_ALA_1 <Probcause> 
        receiveFailure (41) <Alarmtype> 
        equipmentAlarm (5) <Polarity> (2) 
        "
	::= { pm1008dcpAlmsfpAlmDdmEntry 16 }


pm1008dcpAlmTempHighAlaPortn OBJECT-TYPE
	SYNTAX  EkiOnOff
	MAX-ACCESS read-only
	STATUS current
	DESCRIPTION
        "
        Client SFP Temp High :Alarm indicating 
        that the SFP temperature of port 
        is higher than the threshold value 
        written in the SFP EEPROM <Condtype> 
        TEMP_HIGH_ALA_1 <Probcause> temperatureUnacceptable 
        (51) <Alarmtype> equipmentAlarm 
        (5) <Polarity> (2) 
        "
	::= { pm1008dcpAlmsfpAlmDdmEntry 9 }


pm1008dcpAlmTempLowAlaPortn OBJECT-TYPE
	SYNTAX  EkiOnOff
	MAX-ACCESS read-only
	STATUS current
	DESCRIPTION
        "
        Client SFP Temp Low :Alarm indicating 
        that the SFP temperature of port 
        is lower than the threshold value 
        written in the SFP EEPROM <Condtype> 
        TEMP_LOW_ALA_1 <Probcause> temperatureUnacceptable 
        (51) <Alarmtype> equipmentAlarm 
        (5) <Polarity> (2) 
        "
	::= { pm1008dcpAlmsfpAlmDdmEntry 8 }


pm1008dcpAlmVccHighAlaPortn OBJECT-TYPE
	SYNTAX  EkiOnOff
	MAX-ACCESS read-only
	STATUS current
	DESCRIPTION
        "
        Client SFP Power Supply High :Alarm 
        indicating that the SFP power supply 
        of port is higher than the threshold 
        value written in the SFP EEPROM 
         <Condtype> VCC_HIGH_ALA_1 <Probcause> 
        powerProblem (36) <Alarmtype> equipmentAlarm 
        (5) <Polarity> (2) 
        "
	::= { pm1008dcpAlmsfpAlmDdmEntry 7 }


pm1008dcpAlmVccLowAlaPortn OBJECT-TYPE
	SYNTAX  EkiOnOff
	MAX-ACCESS read-only
	STATUS current
	DESCRIPTION
        "
        Client SFP Power Supply Low :Alarm 
        indicating that the SFP power supply 
        of port is lower than the threshold 
        value written in the SFP EEPROM 
         <Condtype> VCC_LOW_ALA_1 <Probcause> 
        powerProblem (36) <Alarmtype> equipmentAlarm 
        (5) <Polarity> (2) 
        "
	::= { pm1008dcpAlmsfpAlmDdmEntry 6 }


pm1008dcpAlmTxBiasHighAlaPortn OBJECT-TYPE
	SYNTAX  EkiOnOff
	MAX-ACCESS read-only
	STATUS current
	DESCRIPTION
        "
        Client SFP Bias High :Alarm indicating 
        that the SFP laser bias current 
        of port is higher than the threshold 
        value written in the SFP EEPROM 
        <Condtype> TX_BIAS_HIGH_ALA_1 <Probcause> 
        transmitterFailure (56) <Alarmtype> 
        equipmentAlarm (5) <Polarity> (2) 
        "
	::= { pm1008dcpAlmsfpAlmDdmEntry 5 }


pm1008dcpAlmTxBiasLowAlaPortn OBJECT-TYPE
	SYNTAX  EkiOnOff
	MAX-ACCESS read-only
	STATUS current
	DESCRIPTION
        "
        Client SFP Bias Low :Alarm indicating 
        that the SFP laser bias current 
        of port is lower than the threshold 
        value written in the SFP EEPROM 
        <Condtype> TX_BIAS_LOW_ALA_1 <Probcause> 
        transmitterFailure (56) <Alarmtype> 
        equipmentAlarm (5) <Polarity> (2) 
        "
	::= { pm1008dcpAlmsfpAlmDdmEntry 4 }


pm1008dcpAlmTxPwrHighAlaPortn OBJECT-TYPE
	SYNTAX  EkiOnOff
	MAX-ACCESS read-only
	STATUS current
	DESCRIPTION
        "
        Client SFP Tx Power High :Alarm 
        indicating that the SFP output
         power of port is higher than the 
        threshold value written in the
         SFP EEPROM <Condtype> TX_PWR_HIGH_ALA_1 
        <Probcause> transmitterFailure
         (56) <Alarmtype> equipmentAlarm 
        (5) <Polarity> (2) 
        "
	::= { pm1008dcpAlmsfpAlmDdmEntry 3 }


pm1008dcpAlmTxPwrLowAlaPortn OBJECT-TYPE
	SYNTAX  EkiOnOff
	MAX-ACCESS read-only
	STATUS current
	DESCRIPTION
        "
        Client SFP Tx Power Low :Alarm 
        indicating that the SFP output
         power of port is lower than the 
        threshold value written in the
         SFP EEPROM <Condtype> TX_PWR_LOW_ALA_1 
        <Probcause> transmitterFailure
         (56) <Alarmtype> equipmentAlarm 
        (5) <Polarity> (2) 
        "
	::= { pm1008dcpAlmsfpAlmDdmEntry 2 }


--- *********************************************************
---     TABLE for the pm1008dcpAlmsfpWarnDdm articles
--- *********************************************************

pm1008dcpAlmsfpWarnDdmTable OBJECT-TYPE
	SYNTAX  SEQUENCE OF Pm1008dcpAlmsfpWarnDdmEntry
	MAX-ACCESS not-accessible
	STATUS current
	DESCRIPTION
        "
        List of pm1008dcpAlmsfpWarnDdm 
        Article
        "
	::= { pm1008dcpAlmClientNurg 48 }


pm1008dcpAlmsfpWarnDdmEntry OBJECT-TYPE
	SYNTAX Pm1008dcpAlmsfpWarnDdmEntry
	MAX-ACCESS not-accessible
	STATUS current
	DESCRIPTION
        "
        Row definition for the pm1008dcpAlmsfpWarnDdm 
        table
        "
	INDEX   { pm1008dcpAlmsfpWarnDdmIndex }
	::= { pm1008dcpAlmsfpWarnDdmTable 1 }


Pm1008dcpAlmsfpWarnDdmEntry ::=
	SEQUENCE {
	pm1008dcpAlmsfpWarnDdmIndex
		INTEGER,
	pm1008dcpAlmRxPwrHighWngPortn
		EkiOnOff,
	pm1008dcpAlmRxPwrLowWngPortn
		EkiOnOff,
	pm1008dcpAlmTempHighWngPortn
		EkiOnOff,
	pm1008dcpAlmTempLowWngPortn
		EkiOnOff,
	pm1008dcpAlmVccHighWngPortn
		EkiOnOff,
	pm1008dcpAlmVccLowWngPortn
		EkiOnOff,
	pm1008dcpAlmTxBiasHighWngPortn
		EkiOnOff,
	pm1008dcpAlmTxBiasLowWngPortn
		EkiOnOff,
	pm1008dcpAlmTxPwrHighWngPortn
		EkiOnOff,
	pm1008dcpAlmTxPwLowWngPortn
		EkiOnOff
	}


pm1008dcpAlmsfpWarnDdmIndex OBJECT-TYPE
	SYNTAX  INTEGER(0..128)
	MAX-ACCESS  read-only
	STATUS current
	DESCRIPTION
        "
        Index definition for the pm1008dcpAlmsfpWarnDdm 
        table
        "
	::= { pm1008dcpAlmsfpWarnDdmEntry 1 }


pm1008dcpAlmRxPwrHighWngPortn OBJECT-TYPE
	SYNTAX  EkiOnOff
	MAX-ACCESS read-only
	STATUS current
	DESCRIPTION
        "
        Client SFP Rx Power High Warning 
        :Warning indicating that the SFP 
        input power of port is higher than 
        the threshold value written in
         the SFP EEPROM <Condtype> RX_PWR_HIGH_WNG_1 
        <Probcause> receiveFailure (41) 
        <Alarmtype> equipmentAlarm (5)
         <Polarity> (2) 
        "
	::= { pm1008dcpAlmsfpWarnDdmEntry 17 }


pm1008dcpAlmRxPwrLowWngPortn OBJECT-TYPE
	SYNTAX  EkiOnOff
	MAX-ACCESS read-only
	STATUS current
	DESCRIPTION
        "
        Client SFP Rx Power Low Warning 
        :Warning indicating that the SFP 
        input power of port is lower than 
        the threshold value written in
         the SFP EEPROM <Condtype> RX_PWR_LOW_WNG_1 
        <Probcause> receiveFailure (41) 
        <Alarmtype> equipmentAlarm (5)
         <Polarity> (2) 
        "
	::= { pm1008dcpAlmsfpWarnDdmEntry 16 }


pm1008dcpAlmTempHighWngPortn OBJECT-TYPE
	SYNTAX  EkiOnOff
	MAX-ACCESS read-only
	STATUS current
	DESCRIPTION
        "
        Client SFP Temp High Warning :Warning 
        indicating that the SFP temperature 
        of port is higher than the threshold 
        value written in the SFP EEPROM 
        <Condtype> TEMP_HIGH_WNG_1 <Probcause> 
        temperatureUnacceptable (51) <Alarmtype> 
        equipmentAlarm (5) <Polarity> (2) 
        "
	::= { pm1008dcpAlmsfpWarnDdmEntry 9 }


pm1008dcpAlmTempLowWngPortn OBJECT-TYPE
	SYNTAX  EkiOnOff
	MAX-ACCESS read-only
	STATUS current
	DESCRIPTION
        "
        Client SFP Temp Low Warning :Warning 
        indicating that the SFP temperature 
        of port is lower than the threshold 
        value written in the SFP EEPROM 
        <Condtype> TEMP_LOW_WNG_1 <Probcause> 
        temperatureUnacceptable (51) <Alarmtype> 
        equipmentAlarm (5) <Polarity> (2) 
        "
	::= { pm1008dcpAlmsfpWarnDdmEntry 8 }


pm1008dcpAlmVccHighWngPortn OBJECT-TYPE
	SYNTAX  EkiOnOff
	MAX-ACCESS read-only
	STATUS current
	DESCRIPTION
        "
        Client SFP Power Supply High Warning 
        :Warning indicating that the SFP 
        power supply of port is higher
         than the threshold value written 
        in the SFP EEPROM  <Condtype> VCC_HIGH_WNG_1 
        <Probcause> powerProblem (36) <Alarmtype> 
        equipmentAlarm (5) <Polarity> (2) 
        "
	::= { pm1008dcpAlmsfpWarnDdmEntry 7 }


pm1008dcpAlmVccLowWngPortn OBJECT-TYPE
	SYNTAX  EkiOnOff
	MAX-ACCESS read-only
	STATUS current
	DESCRIPTION
        "
        Client SFP Power Supply Low Warning 
        :Warning indicating that the SFP 
        power supply of port is lower than 
        the threshold value written in
         the SFP EEPROM  <Condtype> VCC_LOW_WNG_1 
        <Probcause> powerProblem (36) <Alarmtype> 
        equipmentAlarm (5) <Polarity> (2) 
        "
	::= { pm1008dcpAlmsfpWarnDdmEntry 6 }


pm1008dcpAlmTxBiasHighWngPortn OBJECT-TYPE
	SYNTAX  EkiOnOff
	MAX-ACCESS read-only
	STATUS current
	DESCRIPTION
        "
        Client SFP Bias High Warning :Warning 
        indicating that the SFP laser bias 
        current of port is higher than
         the threshold value written in 
        the SFP EEPROM <Condtype> TX_BIAS_HIGH_WNG_1 
        <Probcause> transmitterFailure
         (56) <Alarmtype> equipmentAlarm 
        (5) <Polarity> (2) 
        "
	::= { pm1008dcpAlmsfpWarnDdmEntry 5 }


pm1008dcpAlmTxBiasLowWngPortn OBJECT-TYPE
	SYNTAX  EkiOnOff
	MAX-ACCESS read-only
	STATUS current
	DESCRIPTION
        "
        Client SFP Bias Low Warning :Warning 
        indicating that the SFP laser bias 
        current of port is lower than the 
        threshold value written in the
         SFP EEPROM <Condtype> TX_BIAS_LOW_WNG_1 
        <Probcause> transmitterFailure
         (56) <Alarmtype> equipmentAlarm 
        (5) <Polarity> (2) 
        "
	::= { pm1008dcpAlmsfpWarnDdmEntry 4 }


pm1008dcpAlmTxPwrHighWngPortn OBJECT-TYPE
	SYNTAX  EkiOnOff
	MAX-ACCESS read-only
	STATUS current
	DESCRIPTION
        "
        Client SFP Tx Power High Warning 
        :Warning indicating that the SFP 
        output power of port is higher
         than the threshold value written 
        in the SFP EEPROM <Condtype> TX_PWR_HIGH_WNG_1 
        <Probcause> transmitterFailure
         (56) <Alarmtype> equipmentAlarm 
        (5) <Polarity> (2) 
        "
	::= { pm1008dcpAlmsfpWarnDdmEntry 3 }


pm1008dcpAlmTxPwLowWngPortn OBJECT-TYPE
	SYNTAX  EkiOnOff
	MAX-ACCESS read-only
	STATUS current
	DESCRIPTION
        "
        Client SFP Tx Power Low Warning 
        :Warning indicating that the SFP 
        output power of port is lower than 
        the threshold value written in
         the SFP EEPROM <Condtype> TX_PW_LOW_WNG_1 
        <Probcause> transmitterFailure
         (56) <Alarmtype> equipmentAlarm 
        (5) <Polarity> (2) 
        "
	::= { pm1008dcpAlmsfpWarnDdmEntry 2 }


--- *********************************************************
---     TABLE for the pm1008dcpAlmmapperDeAlm articles
--- *********************************************************

pm1008dcpAlmmapperDeAlmTable OBJECT-TYPE
	SYNTAX  SEQUENCE OF Pm1008dcpAlmmapperDeAlmEntry
	MAX-ACCESS not-accessible
	STATUS current
	DESCRIPTION
        "
        List of pm1008dcpAlmmapperDeAlm 
        Article
        "
	::= { pm1008dcpAlmClientCrit 72 }


pm1008dcpAlmmapperDeAlmEntry OBJECT-TYPE
	SYNTAX Pm1008dcpAlmmapperDeAlmEntry
	MAX-ACCESS not-accessible
	STATUS current
	DESCRIPTION
        "
        Row definition for the pm1008dcpAlmmapperDeAlm 
        table
        "
	INDEX   { pm1008dcpAlmmapperDeAlmIndex }
	::= { pm1008dcpAlmmapperDeAlmTable 1 }


Pm1008dcpAlmmapperDeAlmEntry ::=
	SEQUENCE {
	pm1008dcpAlmmapperDeAlmIndex
		INTEGER,
	pm1008dcpAlmDwBufferOvlPortn
		EkiOnOff,
	pm1008dcpAlmDwCsfDetPortn
		EkiOnOff,
	pm1008dcpAlmUpBufferOvlPortn
		EkiOnOff,
	pm1008dcpAlmUpAccOosPortn
		EkiOnOff
	}


pm1008dcpAlmmapperDeAlmIndex OBJECT-TYPE
	SYNTAX  INTEGER(0..128)
	MAX-ACCESS  read-only
	STATUS current
	DESCRIPTION
        "
        Index definition for the pm1008dcpAlmmapperDeAlm 
        table
        "
	::= { pm1008dcpAlmmapperDeAlmEntry 1 }


pm1008dcpAlmDwBufferOvlPortn OBJECT-TYPE
	SYNTAX  EkiOnOff
	MAX-ACCESS read-only
	STATUS current
	DESCRIPTION
        "
        Client Downstream Buffer Overload 
        :This OID indicates that the de-mapper 
        buffer for client port is in overload. 
         <Help>  This alarm indicates if 
        there is a downstream FIFO overload 
        for this client port <Condtype> 
        DW_BUFFER_OVL_1 <Probcause> equipmentMalfunction 
        (16) <Alarmtype> equipmentAlarm 
        (5) <Polarity> (2) 
        "
	::= { pm1008dcpAlmmapperDeAlmEntry 15 }


pm1008dcpAlmDwCsfDetPortn OBJECT-TYPE
	SYNTAX  EkiOnOff
	MAX-ACCESS read-only
	STATUS current
	DESCRIPTION
        "
        Client Signal Fail Detected :This 
        OID indicates that a CSF has been 
        detected on client port in the
         downstream direction   <Help>
          This alarm indicates if a Client 
        Signal Fail has been detected in 
        the incoming line frame for this 
        client port <Condtype> DW_CSF_DET_1 
        <Probcause> receiveFailure (41) 
        <Alarmtype> other (1) <Polarity> 
        (2) 
        "
	::= { pm1008dcpAlmmapperDeAlmEntry 12 }


pm1008dcpAlmUpBufferOvlPortn OBJECT-TYPE
	SYNTAX  EkiOnOff
	MAX-ACCESS read-only
	STATUS current
	DESCRIPTION
        "
        Client Upstream Buffer Overload 
        :This OID indicates that the rate 
        adaptation buffer for client port 
        is in overload.  <Help>  This alarm 
        indicates if there is a upstream 
        FIFO overload for this client port 
        <Condtype> UP_BUFFER_OVL_1 <Probcause> 
        receiveFailure (41) <Alarmtype> 
        integrityViolation (7) <Polarity> 
        (2) 
        "
	::= { pm1008dcpAlmmapperDeAlmEntry 11 }


pm1008dcpAlmUpAccOosPortn OBJECT-TYPE
	SYNTAX  EkiOnOff
	MAX-ACCESS read-only
	STATUS current
	DESCRIPTION
        "
        Client Loss Of 10b/8b Synchro
         :This OID indicates the upstream 
        client input port has lost synchronization 
        on its 10B/8B decoder  <Help> 
         This alarms indicates if the input 
        client signal is correctly synchronized 
        with the 10b/8b decoder <Condtype> 
        UP_ACC_OOS_1 <Probcause> receiveFailure 
        (41) <Alarmtype> integrityViolation 
        (7) <Polarity> (2) 
        "
	::= { pm1008dcpAlmmapperDeAlmEntry 2 }


--- *********************************************************
---     TABLE for the pm1008dcpAlmdfrmAlm articles
--- *********************************************************

pm1008dcpAlmdfrmAlmTable OBJECT-TYPE
	SYNTAX  SEQUENCE OF Pm1008dcpAlmdfrmAlmEntry
	MAX-ACCESS not-accessible
	STATUS current
	DESCRIPTION
        "
        List of pm1008dcpAlmdfrmAlm Article
        "
	::= { pm1008dcpAlmLineCrit 128 }


pm1008dcpAlmdfrmAlmEntry OBJECT-TYPE
	SYNTAX Pm1008dcpAlmdfrmAlmEntry
	MAX-ACCESS not-accessible
	STATUS current
	DESCRIPTION
        "
        Row definition for the pm1008dcpAlmdfrmAlm 
        table
        "
	INDEX   { pm1008dcpAlmdfrmAlmIndex }
	::= { pm1008dcpAlmdfrmAlmTable 1 }


Pm1008dcpAlmdfrmAlmEntry ::=
	SEQUENCE {
	pm1008dcpAlmdfrmAlmIndex
		INTEGER,
	pm1008dcpAlmDwLofPortn
		EkiOnOff,
	pm1008dcpAlmDwOofPortn
		EkiOnOff,
	pm1008dcpAlmDwRdiDetPortn
		EkiOnOff,
	pm1008dcpAlmDwAisDetPortn
		EkiOnOff
	}


pm1008dcpAlmdfrmAlmIndex OBJECT-TYPE
	SYNTAX  INTEGER(0..128)
	MAX-ACCESS  read-only
	STATUS current
	DESCRIPTION
        "
        Index definition for the pm1008dcpAlmdfrmAlm 
        table
        "
	::= { pm1008dcpAlmdfrmAlmEntry 1 }


pm1008dcpAlmDwLofPortn OBJECT-TYPE
	SYNTAX  EkiOnOff
	MAX-ACCESS read-only
	STATUS current
	DESCRIPTION
        "
        SONET/SDH Line Loss Of Frame :This 
        OID indicates that a Loss Of Frame 
        has been detected on incoming 
         OC-48c/STM-16c input signal  <Help> 
         This alarm indicates if there
         is a Loss of Frame is detected 
        on the line input signal <Condtype> 
        DW_LOF_1 <Probcause> receiveFailure 
        (41) <Alarmtype> integrityViolation 
        (7) <Polarity> (2) 
        "
	::= { pm1008dcpAlmdfrmAlmEntry 5 }


pm1008dcpAlmDwOofPortn OBJECT-TYPE
	SYNTAX  EkiOnOff
	MAX-ACCESS read-only
	STATUS current
	DESCRIPTION
        "
        SONET/SDH Line Out Of Frame :This 
        OID indicates that an Out Of Frame 
        has been detected on incoming 
         OC-48c/STM-16c input signal  <Help> 
         This alarm indicates if there
         is a Out of Frame is detected
         on the line input signal <Condtype> 
        DW_OOF_1 <Probcause> receiveFailure 
        (41) <Alarmtype> integrityViolation 
        (7) <Polarity> (2) 
        "
	::= { pm1008dcpAlmdfrmAlmEntry 4 }


pm1008dcpAlmDwRdiDetPortn OBJECT-TYPE
	SYNTAX  EkiOnOff
	MAX-ACCESS read-only
	STATUS current
	DESCRIPTION
        "
        MS-RDI/L-RDI Detected On Line
         Input :This OID indicates that 
        an MS-RDI has been detected on
         incoming  OC-48c/STM-16c input 
        signal  <Help>  This alarm indicates 
        if there is a MS-RDI/L-RDI is detected 
        on the line input signal <Condtype> 
        DW_RDI_DET_1 <Probcause> remoteNodeTransmissionError 
        (43) <Alarmtype> other (1) <Polarity> 
        (2) 
        "
	::= { pm1008dcpAlmdfrmAlmEntry 3 }


pm1008dcpAlmDwAisDetPortn OBJECT-TYPE
	SYNTAX  EkiOnOff
	MAX-ACCESS read-only
	STATUS current
	DESCRIPTION
        "
        MS-AIS/L-AIS Detected On Line
         Input :This OID indicates that 
        an MS-AIS has been detected on
         incoming  OC-48c/STM-16c input 
        signal  <Help>  This alarm indicates 
        if there is a MS-AIS/L-AIS is detected 
        on the line input signal <Condtype> 
        DW_AIS_DET_1 <Probcause> receiveFailure 
        (41) <Alarmtype> operationalViolation 
        (8) <Polarity> (2) 
        "
	::= { pm1008dcpAlmdfrmAlmEntry 2 }


--- *********************************************************
---     TABLE for the pm1008dcpAlmdfrmBer articles
--- *********************************************************

pm1008dcpAlmdfrmBerTable OBJECT-TYPE
	SYNTAX  SEQUENCE OF Pm1008dcpAlmdfrmBerEntry
	MAX-ACCESS not-accessible
	STATUS current
	DESCRIPTION
        "
        List of pm1008dcpAlmdfrmBer Article
        "
	::= { pm1008dcpAlmLineUrg 129 }


pm1008dcpAlmdfrmBerEntry OBJECT-TYPE
	SYNTAX Pm1008dcpAlmdfrmBerEntry
	MAX-ACCESS not-accessible
	STATUS current
	DESCRIPTION
        "
        Row definition for the pm1008dcpAlmdfrmBer 
        table
        "
	INDEX   { pm1008dcpAlmdfrmBerIndex }
	::= { pm1008dcpAlmdfrmBerTable 1 }


Pm1008dcpAlmdfrmBerEntry ::=
	SEQUENCE {
	pm1008dcpAlmdfrmBerIndex
		INTEGER,
	pm1008dcpAlmLineDegradePortn
		EkiOnOff,
	pm1008dcpAlmLineSignalFailPortn
		EkiOnOff,
	pm1008dcpAlmLineSignalDegradePortn
		EkiOnOff
	}


pm1008dcpAlmdfrmBerIndex OBJECT-TYPE
	SYNTAX  INTEGER(0..128)
	MAX-ACCESS  read-only
	STATUS current
	DESCRIPTION
        "
        Index definition for the pm1008dcpAlmdfrmBer 
        table
        "
	::= { pm1008dcpAlmdfrmBerEntry 1 }


pm1008dcpAlmLineDegradePortn OBJECT-TYPE
	SYNTAX  EkiOnOff
	MAX-ACCESS read-only
	STATUS current
	DESCRIPTION
        "
        Fixed Line Signal Degrade :This 
        OID indicates that the line input 
        signal is DEGRADE. The assetion 
        hysteresis is fixed to 10-8 (assertion) 
        and 10-9 (de-assertion) <Condtype> 
        LINE_DEGRADE_1 <Probcause> degradedSignal 
        (13) <Alarmtype> qualityOfServiceAlarm 
        (3) <Polarity> (2) 
        "
	::= { pm1008dcpAlmdfrmBerEntry 6 }


pm1008dcpAlmLineSignalFailPortn OBJECT-TYPE
	SYNTAX  EkiOnOff
	MAX-ACCESS read-only
	STATUS current
	DESCRIPTION
        "
        Custom Line Signal Fail :This
         OID indicates that the line input 
        signal is FAIL. The assertion hysteresis 
        can be customized by the host <Condtype> 
        LINE_SIGNAL_FAIL_1 <Probcause>
         receiveFailure (41) <Alarmtype> 
        integrityViolation (7) <Polarity> 
        (2) 
        "
	::= { pm1008dcpAlmdfrmBerEntry 3 }


pm1008dcpAlmLineSignalDegradePortn OBJECT-TYPE
	SYNTAX  EkiOnOff
	MAX-ACCESS read-only
	STATUS current
	DESCRIPTION
        "
        Custom Line Signal Degrade :This 
        OID indicates that the line input 
        signal is DEGRADE. The assertion 
        hysteresis can customized by the 
        host <Condtype> LINE_SIGNAL_DEGRADE_1 
        <Probcause> degradedSignal (13) 
        <Alarmtype> qualityOfServiceAlarm 
        (3) <Polarity> (2) 
        "
	::= { pm1008dcpAlmdfrmBerEntry 2 }


--- *********************************************************
---     TABLE for the pm1008dcpAlmlineSyncAlarms articles
--- *********************************************************

pm1008dcpAlmlineSyncAlarmsTable OBJECT-TYPE
	SYNTAX  SEQUENCE OF Pm1008dcpAlmlineSyncAlarmsEntry
	MAX-ACCESS not-accessible
	STATUS current
	DESCRIPTION
        "
        List of pm1008dcpAlmlineSyncAlarms 
        Article
        "
	::= { pm1008dcpAlmLineCrit 133 }


pm1008dcpAlmlineSyncAlarmsEntry OBJECT-TYPE
	SYNTAX Pm1008dcpAlmlineSyncAlarmsEntry
	MAX-ACCESS not-accessible
	STATUS current
	DESCRIPTION
        "
        Row definition for the pm1008dcpAlmlineSyncAlarms 
        table
        "
	INDEX   { pm1008dcpAlmlineSyncAlarmsIndex }
	::= { pm1008dcpAlmlineSyncAlarmsTable 1 }


Pm1008dcpAlmlineSyncAlarmsEntry ::=
	SEQUENCE {
	pm1008dcpAlmlineSyncAlarmsIndex
		INTEGER,
	pm1008dcpAlmDwLosPortn
		EkiOnOff,
	pm1008dcpAlmUpLockerrPortn
		EkiOnOff,
	pm1008dcpAlmDwLockerrPortn
		EkiOnOff
	}


pm1008dcpAlmlineSyncAlarmsIndex OBJECT-TYPE
	SYNTAX  INTEGER(0..128)
	MAX-ACCESS  read-only
	STATUS current
	DESCRIPTION
        "
        Index definition for the pm1008dcpAlmlineSyncAlarms 
        table
        "
	::= { pm1008dcpAlmlineSyncAlarmsEntry 1 }


pm1008dcpAlmDwLosPortn OBJECT-TYPE
	SYNTAX  EkiOnOff
	MAX-ACCESS read-only
	STATUS current
	DESCRIPTION
        "
        Line Input Loss Of Signal :This 
        OID indicates a loss of signal
         on the 10 Gb/s input.  <Help>
          This alarm indicates if an optical 
        signal is detected on the line
         transceiver input <Condtype> DW_LOS 
        <Probcause> receiveFailure (41) 
        <Alarmtype> physicalViolation (9) 
        <Polarity> (2) 
        "
	::= { pm1008dcpAlmlineSyncAlarmsEntry 17 }


pm1008dcpAlmUpLockerrPortn OBJECT-TYPE
	SYNTAX  EkiOnOff
	MAX-ACCESS read-only
	STATUS current
	DESCRIPTION
        "
        Upstream Clock Lock Error :This 
        OID indicates that the serializer 
        output 10 Gb/s clock multiplier 
        unit is not locked. <Condtype>
         UP_LOCKERR <Probcause> receiveFailure 
        (41) <Alarmtype> equipmentAlarm 
        (5) <Polarity> (2) 
        "
	::= { pm1008dcpAlmlineSyncAlarmsEntry 14 }


pm1008dcpAlmDwLockerrPortn OBJECT-TYPE
	SYNTAX  EkiOnOff
	MAX-ACCESS read-only
	STATUS current
	DESCRIPTION
        "
        Downstream Clock Lock Error :This 
        OID indicates that the deserializer 
        input 10 Gb/s clock recovery is 
        not locked. <Condtype> DW_LOCKERR 
        <Probcause> receiveFailure (41) 
        <Alarmtype> equipmentAlarm (5)
         <Polarity> (2) 
        "
	::= { pm1008dcpAlmlineSyncAlarmsEntry 13 }


--- *****************************************************
---     LEAF for the modInitFailLevel2 article
--- *****************************************************
pm1008dcpAlmmodInitFailLevel2 OBJECT IDENTIFIER ::= { pm1008dcpAlmOtherUrg 194 }




pm1008dcpAlmSwInitFail OBJECT-TYPE
	  SYNTAX EkiOnOff
	  MAX-ACCESS read-only
	  STATUS current
	  DESCRIPTION
        "
        SW Init Fail :This OID indicates 
        that the SW intialization has caused 
        unknown intial conditions  <Help> 
         This alarm indicates if the SW 
        module is correctly initialized 
        <Condtype> SW_INIT_FAIL <Probcause> 
        softwareError (47) <Alarmtype>
         processingErrorAlarm (4) <Polarity> 
        (2) 
        "
	  ::= { pm1008dcpAlmmodInitFailLevel2 5 }



pm1008dcpAlmResetHwInitFail OBJECT-TYPE
	  SYNTAX EkiOnOff
	  MAX-ACCESS read-only
	  STATUS current
	  DESCRIPTION
        "
        Reset HW Init Fail :This OID indicates 
        that the HW intialization has caused 
        unknown intial conditions  <Help> 
         This alarm indicates if the HW 
        has been correctly initialized
         <Condtype> RESET_HW_INIT_FAIL
         <Probcause> softwareError (47) 
        <Alarmtype> processingErrorAlarm 
        (4) <Polarity> (2) 
        "
	  ::= { pm1008dcpAlmmodInitFailLevel2 4 }



pm1008dcpAlmBootUndone OBJECT-TYPE
	  SYNTAX EkiOnOff
	  MAX-ACCESS read-only
	  STATUS current
	  DESCRIPTION
        "
        Boot Undone :This OID indicates 
        that the boot has not been correctly 
        achieved  <Help>  This alarm indicates 
        if the module has correctly boot 
        <Condtype> BOOT_UNDONE <Probcause> 
        softwareError (47) <Alarmtype>
         processingErrorAlarm (4) <Polarity> 
        (2) 
        "
	  ::= { pm1008dcpAlmmodInitFailLevel2 3 }



pm1008dcpAlmNextColdBootForced OBJECT-TYPE
	  SYNTAX EkiOnOff
	  MAX-ACCESS read-only
	  STATUS current
	  DESCRIPTION
        "
        Next Cold Boot Forced :This OID 
        indicates that the next Reset will 
        be forced Cold  <Help>  This alarm 
        indicates that the next reset of 
        the module will be forced to cold 
        reset <Condtype> NEXT_COLD_BOOT_FORCED 
        <Probcause> informationalStatus(1000) 
        <Alarmtype> other (1) <Polarity> 
        (2) 
        "
	  ::= { pm1008dcpAlmmodInitFailLevel2 2 }



pm1008dcpAlmLedFail OBJECT-TYPE
	  SYNTAX EkiOnOff
	  MAX-ACCESS read-only
	  STATUS current
	  DESCRIPTION
        "
        Led Fail :This OID indicates that 
        Led register has not been correctly 
        initalized  <Help>  This alarm
         indicates if the module LEDs are 
        correctly initialized <Condtype> 
        LED_FAIL <Probcause> softwareError 
        (47) <Alarmtype> processingErrorAlarm 
        (4) <Polarity> (2) 
        "
	  ::= { pm1008dcpAlmmodInitFailLevel2 1 }



--- *****************************************************
---     LEAF for the modInitFailLevel3 article
--- *****************************************************
pm1008dcpAlmmodInitFailLevel3 OBJECT IDENTIFIER ::= { pm1008dcpAlmOtherUrg 195 }




pm1008dcpAlmClient8InitFail OBJECT-TYPE
	  SYNTAX EkiOnOff
	  MAX-ACCESS read-only
	  STATUS current
	  DESCRIPTION
        "
        Client8 Init Fail :This OID indicates 
        that Client 8 registers subset
         has not been correctly initialized 
         <Help>  This alarm indicates if 
        the client port 8 is correctly
         initialized <Condtype> CLIENT8_INIT_FAIL 
        <Probcause> softwareError (47)
         <Alarmtype> processingErrorAlarm 
        (4) <Polarity> (2) 
        "
	  ::= { pm1008dcpAlmmodInitFailLevel3 16 }



pm1008dcpAlmClient7InitFail OBJECT-TYPE
	  SYNTAX EkiOnOff
	  MAX-ACCESS read-only
	  STATUS current
	  DESCRIPTION
        "
        Client7 Init Fail :This OID indicates 
        that Client 7 registers subset
         has not been correctly initialized 
         <Help>  This alarm indicates if 
        the client port 7 is correctly
         initialized <Condtype> CLIENT7_INIT_FAIL 
        <Probcause> softwareError (47)
         <Alarmtype> processingErrorAlarm 
        (4) <Polarity> (2) 
        "
	  ::= { pm1008dcpAlmmodInitFailLevel3 15 }



pm1008dcpAlmClient6InitFail OBJECT-TYPE
	  SYNTAX EkiOnOff
	  MAX-ACCESS read-only
	  STATUS current
	  DESCRIPTION
        "
        Client6 Init Fail :This OID indicates 
        that Client 6 registers subset
         has not been correctly initialized 
         <Help>  This alarm indicates if 
        the client port 6 is correctly
         initialized <Condtype> CLIENT6_INIT_FAIL 
        <Probcause> softwareError (47)
         <Alarmtype> processingErrorAlarm 
        (4) <Polarity> (2) 
        "
	  ::= { pm1008dcpAlmmodInitFailLevel3 14 }



pm1008dcpAlmClient5InitFail OBJECT-TYPE
	  SYNTAX EkiOnOff
	  MAX-ACCESS read-only
	  STATUS current
	  DESCRIPTION
        "
        Client5 Init Fail :This OID indicates 
        that Client 5 registers subset
         has not been correctly initialized 
         <Help>  This alarm indicates if 
        the client port 5 is correctly
         initialized <Condtype> CLIENT5_INIT_FAIL 
        <Probcause> softwareError (47)
         <Alarmtype> processingErrorAlarm 
        (4) <Polarity> (2) 
        "
	  ::= { pm1008dcpAlmmodInitFailLevel3 13 }



pm1008dcpAlmClient4InitFail OBJECT-TYPE
	  SYNTAX EkiOnOff
	  MAX-ACCESS read-only
	  STATUS current
	  DESCRIPTION
        "
        Client4 Init Fail :This OID indicates 
        that Client 4 registers subset
         has not been correctly initialized 
         <Help>  This alarm indicates if 
        the client port 4 is correctly
         initialized <Condtype> CLIENT4_INIT_FAIL 
        <Probcause> softwareError (47)
         <Alarmtype> processingErrorAlarm 
        (4) <Polarity> (2) 
        "
	  ::= { pm1008dcpAlmmodInitFailLevel3 12 }



pm1008dcpAlmClient3InitFail OBJECT-TYPE
	  SYNTAX EkiOnOff
	  MAX-ACCESS read-only
	  STATUS current
	  DESCRIPTION
        "
        Client3 Init Fail :This OID indicates 
        that Client 3 registers subset
         has not been correctly initialized 
         <Help>  This alarm indicates if 
        the client port 3 is correctly
         initialized <Condtype> CLIENT3_INIT_FAIL 
        <Probcause> softwareError (47)
         <Alarmtype> processingErrorAlarm 
        (4) <Polarity> (2) 
        "
	  ::= { pm1008dcpAlmmodInitFailLevel3 11 }



pm1008dcpAlmClient2InitFail OBJECT-TYPE
	  SYNTAX EkiOnOff
	  MAX-ACCESS read-only
	  STATUS current
	  DESCRIPTION
        "
        Client2 Init Fail :This OID indicates 
        that Client 2 registers subset
         has not been correctly initialized 
         <Help>  This alarm indicates if 
        the client port 2 is correctly
         initialized <Condtype> CLIENT2_INIT_FAIL 
        <Probcause> softwareError (47)
         <Alarmtype> processingErrorAlarm 
        (4) <Polarity> (2) 
        "
	  ::= { pm1008dcpAlmmodInitFailLevel3 10 }



pm1008dcpAlmClient1InitFail OBJECT-TYPE
	  SYNTAX EkiOnOff
	  MAX-ACCESS read-only
	  STATUS current
	  DESCRIPTION
        "
        Client1 Init Fail :This OID indicates 
        that Client 1 registers subset
         has not been correctly initialized 
         <Help>  This alarm indicates if 
        the client port 1 is correctly
         initialized <Condtype> CLIENT1_INIT_FAIL 
        <Probcause> softwareError (47)
         <Alarmtype> processingErrorAlarm 
        (4) <Polarity> (2) 
        "
	  ::= { pm1008dcpAlmmodInitFailLevel3 9 }



pm1008dcpAlmLine2InitFail OBJECT-TYPE
	  SYNTAX EkiOnOff
	  MAX-ACCESS read-only
	  STATUS current
	  DESCRIPTION
        "
        Line2 Init Fail :This OID indicates 
        that the Line register subset has 
        not been correctly initialized
          <Help>  This alarm indicates
         if the line port 2 is correctly 
        initialized <Condtype> LINE2_INIT_FAIL 
        <Probcause> softwareError (47)
         <Alarmtype> processingErrorAlarm 
        (4) <Polarity> (2) 
        "
	  ::= { pm1008dcpAlmmodInitFailLevel3 8 }



pm1008dcpAlmLine1InitFail OBJECT-TYPE
	  SYNTAX EkiOnOff
	  MAX-ACCESS read-only
	  STATUS current
	  DESCRIPTION
        "
        Line1 Init Fail :This OID indicates 
        that the Line registersvsubset
         has not been correctly initialized 
         <Help>  This alarm indicates if 
        the line port 1 is correctly initialized 
        <Condtype> LINE1_INIT_FAIL <Probcause> 
        softwareError (47) <Alarmtype>
         processingErrorAlarm (4) <Polarity> 
        (2) 
        "
	  ::= { pm1008dcpAlmmodInitFailLevel3 7 }



pm1008dcpAlmXfp2InitFail OBJECT-TYPE
	  SYNTAX EkiOnOff
	  MAX-ACCESS read-only
	  STATUS current
	  DESCRIPTION
        "
        XFP2 Init Fail :This OID indicates 
        that the XFP has not been correctly 
        initialized  <Help>  This alarm 
        indicates if the line transceiver 
        2 is correctly initialized <Condtype> 
        XFP2_INIT_FAIL <Probcause> softwareError 
        (47) <Alarmtype> processingErrorAlarm 
        (4) <Polarity> (2) 
        "
	  ::= { pm1008dcpAlmmodInitFailLevel3 6 }



pm1008dcpAlmXfp1InitFail OBJECT-TYPE
	  SYNTAX EkiOnOff
	  MAX-ACCESS read-only
	  STATUS current
	  DESCRIPTION
        "
        XFP1 Init Fail :This OID indicates 
        that the XFP has not been correctly 
        initialized  <Help>  This alarm 
        indicates if the line transceiver 
        1 is correctly initialized <Condtype> 
        XFP1_INIT_FAIL <Probcause> softwareError 
        (47) <Alarmtype> processingErrorAlarm 
        (4) <Polarity> (2) 
        "
	  ::= { pm1008dcpAlmmodInitFailLevel3 5 }



pm1008dcpAlmInitModuleFail OBJECT-TYPE
	  SYNTAX EkiOnOff
	  MAX-ACCESS read-only
	  STATUS current
	  DESCRIPTION
        "
        Init Module Fail :This OID indicates 
        that the Module has not been correctly 
        initialized  <Help>  This alarm 
        indicates if the SW module is correctly 
        initialized <Condtype> INIT_MODULE_FAIL 
        <Probcause> softwareError (47)
         <Alarmtype> processingErrorAlarm 
        (4) <Polarity> (2) 
        "
	  ::= { pm1008dcpAlmmodInitFailLevel3 3 }



pm1008dcpAlmObmTypeReadFail OBJECT-TYPE
	  SYNTAX EkiOnOff
	  MAX-ACCESS read-only
	  STATUS current
	  DESCRIPTION
        "
        OBM Type Read Fail :This OID indicates 
        that OBM type has not been recognized 
         <Help>  This alarm indicates if 
        the OBM board has been correctly 
        identified <Condtype> OBM_TYPE_READ_FAIL 
        <Probcause> softwareError (47)
         <Alarmtype> processingErrorAlarm 
        (4) <Polarity> (2) 
        "
	  ::= { pm1008dcpAlmmodInitFailLevel3 2 }



pm1008dcpAlmGwIdentFail OBJECT-TYPE
	  SYNTAX EkiOnOff
	  MAX-ACCESS read-only
	  STATUS current
	  DESCRIPTION
        "
        GW Ident Fail :This OID indicates 
        that GW identification has not
         been read  <Help>  This alarm
         indicates if the GW has been correctly 
        identified <Condtype> GW_IDENT_FAIL 
        <Probcause> softwareError (47)
         <Alarmtype> processingErrorAlarm 
        (4) <Polarity> (2) 
        "
	  ::= { pm1008dcpAlmmodInitFailLevel3 1 }



--- *****************************************************
---     LEAF for the adddropTsClientRxProt article
--- *****************************************************
pm1008dcpAlmadddropTsClientRxProt OBJECT IDENTIFIER ::= { pm1008dcpAlmOtherUrg 198 }




pm1008dcpAlmAdddropClient8East OBJECT-TYPE
	  SYNTAX EkiOnOff
	  MAX-ACCESS read-only
	  STATUS current
	  DESCRIPTION
        "
        Client 8 East Rx Side Active :This 
        OID indicates the Client #8 is
         active on East receiving side
         <Condtype> ADDDROP_CLIENT8_EAST 
        <Probcause> other (1) <Alarmtype> 
        other (1) <Polarity> (2) 
        "
	  ::= { pm1008dcpAlmadddropTsClientRxProt 16 }



pm1008dcpAlmAdddropClient7East OBJECT-TYPE
	  SYNTAX EkiOnOff
	  MAX-ACCESS read-only
	  STATUS current
	  DESCRIPTION
        "
        Client 7 East Rx Side Active :This 
        OID indicates the Client #7 is
         active on East receiving side
         <Condtype> ADDDROP_CLIENT7_EAST 
        <Probcause> other (1) <Alarmtype> 
        other (1) <Polarity> (2) 
        "
	  ::= { pm1008dcpAlmadddropTsClientRxProt 15 }



pm1008dcpAlmAdddropClient6East OBJECT-TYPE
	  SYNTAX EkiOnOff
	  MAX-ACCESS read-only
	  STATUS current
	  DESCRIPTION
        "
        Client 6 East Rx Side Active :This 
        OID indicates the Client #6 is
         active on East receiving side
         <Condtype> ADDDROP_CLIENT6_EAST 
        <Probcause> other (1) <Alarmtype> 
        other (1) <Polarity> (2) 
        "
	  ::= { pm1008dcpAlmadddropTsClientRxProt 14 }



pm1008dcpAlmAdddropClient5East OBJECT-TYPE
	  SYNTAX EkiOnOff
	  MAX-ACCESS read-only
	  STATUS current
	  DESCRIPTION
        "
        Client 5 East Rx Side Active :This 
        OID indicates the Client #5 is
         active on East receiving side
         <Condtype> ADDDROP_CLIENT5_EAST 
        <Probcause> other (1) <Alarmtype> 
        other (1) <Polarity> (2) 
        "
	  ::= { pm1008dcpAlmadddropTsClientRxProt 13 }



pm1008dcpAlmAdddropClient4East OBJECT-TYPE
	  SYNTAX EkiOnOff
	  MAX-ACCESS read-only
	  STATUS current
	  DESCRIPTION
        "
        Client 4 East Rx Side Active :This 
        OID indicates the Client #4 is
         active on East receiving side
         <Condtype> ADDDROP_CLIENT4_EAST 
        <Probcause> other (1) <Alarmtype> 
        other (1) <Polarity> (2) 
        "
	  ::= { pm1008dcpAlmadddropTsClientRxProt 12 }



pm1008dcpAlmAdddropClient3East OBJECT-TYPE
	  SYNTAX EkiOnOff
	  MAX-ACCESS read-only
	  STATUS current
	  DESCRIPTION
        "
        Client 3 East Rx Side Active :This 
        OID indicates the Client #3 is
         active on East receiving side
         <Condtype> ADDDROP_CLIENT3_EAST 
        <Probcause> other (1) <Alarmtype> 
        other (1) <Polarity> (2) 
        "
	  ::= { pm1008dcpAlmadddropTsClientRxProt 11 }



pm1008dcpAlmAdddropClient2East OBJECT-TYPE
	  SYNTAX EkiOnOff
	  MAX-ACCESS read-only
	  STATUS current
	  DESCRIPTION
        "
        Client B East Rx Side Active :This 
        OID indicates the Client #2 is
         active on East receiving side
         <Condtype> ADDDROP_CLIENT2_EAST 
        <Probcause> other (1) <Alarmtype> 
        other (1) <Polarity> (2) 
        "
	  ::= { pm1008dcpAlmadddropTsClientRxProt 10 }



pm1008dcpAlmAdddropClient1East OBJECT-TYPE
	  SYNTAX EkiOnOff
	  MAX-ACCESS read-only
	  STATUS current
	  DESCRIPTION
        "
        Client A East Rx Side Active :This 
        OID indicates the Client #1 is
         active on East receiving side
         <Condtype> ADDDROP_CLIENT1_EAST 
        <Probcause> other (1) <Alarmtype> 
        other (1) <Polarity> (2) 
        "
	  ::= { pm1008dcpAlmadddropTsClientRxProt 9 }



pm1008dcpAlmAdddropClient8West OBJECT-TYPE
	  SYNTAX EkiOnOff
	  MAX-ACCESS read-only
	  STATUS current
	  DESCRIPTION
        "
        Client 8 West Rx Side Active :This 
        OID indicates the Client #8 is
         active on West receiving side
         <Condtype> ADDDROP_CLIENT8_WEST 
        <Probcause> other (1) <Alarmtype> 
        other (1) <Polarity> (2) 
        "
	  ::= { pm1008dcpAlmadddropTsClientRxProt 8 }



pm1008dcpAlmAdddropClient7West OBJECT-TYPE
	  SYNTAX EkiOnOff
	  MAX-ACCESS read-only
	  STATUS current
	  DESCRIPTION
        "
        Client 7 West Rx Side Active :This 
        OID indicates the Client #7 is
         active on West receiving side
         <Condtype> ADDDROP_CLIENT7_WEST 
        <Probcause> other (1) <Alarmtype> 
        other (1) <Polarity> (2) 
        "
	  ::= { pm1008dcpAlmadddropTsClientRxProt 7 }



pm1008dcpAlmAdddropClient6West OBJECT-TYPE
	  SYNTAX EkiOnOff
	  MAX-ACCESS read-only
	  STATUS current
	  DESCRIPTION
        "
        Client 6 West Rx Side Active :This 
        OID indicates the Client #6 is
         active on West receiving side
         <Condtype> ADDDROP_CLIENT6_WEST 
        <Probcause> other (1) <Alarmtype> 
        other (1) <Polarity> (2) 
        "
	  ::= { pm1008dcpAlmadddropTsClientRxProt 6 }



pm1008dcpAlmAdddropClient5West OBJECT-TYPE
	  SYNTAX EkiOnOff
	  MAX-ACCESS read-only
	  STATUS current
	  DESCRIPTION
        "
        Client 5 West Rx Side Active :This 
        OID indicates the Client #5 is
         active on West receiving side
         <Condtype> ADDDROP_CLIENT5_WEST 
        <Probcause> other (1) <Alarmtype> 
        other (1) <Polarity> (2) 
        "
	  ::= { pm1008dcpAlmadddropTsClientRxProt 5 }



pm1008dcpAlmAdddropClient4West OBJECT-TYPE
	  SYNTAX EkiOnOff
	  MAX-ACCESS read-only
	  STATUS current
	  DESCRIPTION
        "
        Client 4 West Rx Side Active :This 
        OID indicates the Client #4 is
         active on West receiving side
         <Condtype> ADDDROP_CLIENT4_WEST 
        <Probcause> other (1) <Alarmtype> 
        other (1) <Polarity> (2) 
        "
	  ::= { pm1008dcpAlmadddropTsClientRxProt 4 }



pm1008dcpAlmAdddropClient3West OBJECT-TYPE
	  SYNTAX EkiOnOff
	  MAX-ACCESS read-only
	  STATUS current
	  DESCRIPTION
        "
        Client 3 West Rx Side Active :This 
        OID indicates the Client #3 is
         active on West receiving side
         <Condtype> ADDDROP_CLIENT3_WEST 
        <Probcause> other (1) <Alarmtype> 
        other (1) <Polarity> (2) 
        "
	  ::= { pm1008dcpAlmadddropTsClientRxProt 3 }



pm1008dcpAlmAdddropClient2West OBJECT-TYPE
	  SYNTAX EkiOnOff
	  MAX-ACCESS read-only
	  STATUS current
	  DESCRIPTION
        "
        Client B West Rx Side Active :This 
        OID indicates the Client #2 is
         active on West receiving side
         <Condtype> ADDDROP_CLIENT2_WEST 
        <Probcause> other (1) <Alarmtype> 
        other (1) <Polarity> (2) 
        "
	  ::= { pm1008dcpAlmadddropTsClientRxProt 2 }



pm1008dcpAlmAdddropClient1West OBJECT-TYPE
	  SYNTAX EkiOnOff
	  MAX-ACCESS read-only
	  STATUS current
	  DESCRIPTION
        "
        Client A West Rx Side Active :This 
        OID indicates the Client #1 is
         active on West receiving side
         <Condtype> ADDDROP_CLIENT1_WEST 
        <Probcause> other (1) <Alarmtype> 
        other (1) <Polarity> (2) 
        "
	  ::= { pm1008dcpAlmadddropTsClientRxProt 1 }



--- *********************************************************
---     TABLE for the pm1008dcpAlmlineXfp1Alarm articles
--- *********************************************************

pm1008dcpAlmlineXfp1AlarmTable OBJECT-TYPE
	SYNTAX  SEQUENCE OF Pm1008dcpAlmlineXfp1AlarmEntry
	MAX-ACCESS not-accessible
	STATUS current
	DESCRIPTION
        "
        List of pm1008dcpAlmlineXfp1Alarm 
        Article
        "
	::= { pm1008dcpAlmLineUrg 208 }


pm1008dcpAlmlineXfp1AlarmEntry OBJECT-TYPE
	SYNTAX Pm1008dcpAlmlineXfp1AlarmEntry
	MAX-ACCESS not-accessible
	STATUS current
	DESCRIPTION
        "
        Row definition for the pm1008dcpAlmlineXfp1Alarm 
        table
        "
	INDEX   { pm1008dcpAlmlineXfp1AlarmIndex }
	::= { pm1008dcpAlmlineXfp1AlarmTable 1 }


Pm1008dcpAlmlineXfp1AlarmEntry ::=
	SEQUENCE {
	pm1008dcpAlmlineXfp1AlarmIndex
		INTEGER,
	pm1008dcpAlmRxPowerHighAlarmPortn
		EkiOnOff,
	pm1008dcpAlmRxPowerLowAlarmPortn
		EkiOnOff,
	pm1008dcpAlmTempHighAlarmPortn
		EkiOnOff,
	pm1008dcpAlmTempLowAlarmPortn
		EkiOnOff,
	pm1008dcpAlmTxBiasHighAlarmPortn
		EkiOnOff,
	pm1008dcpAlmTxBiasLowAlarmPortn
		EkiOnOff,
	pm1008dcpAlmTxPowerHighAlarmPortn
		EkiOnOff,
	pm1008dcpAlmTxPowerLowAlarmPortn
		EkiOnOff
	}


pm1008dcpAlmlineXfp1AlarmIndex OBJECT-TYPE
	SYNTAX  INTEGER(0..128)
	MAX-ACCESS  read-only
	STATUS current
	DESCRIPTION
        "
        Index definition for the pm1008dcpAlmlineXfp1Alarm 
        table
        "
	::= { pm1008dcpAlmlineXfp1AlarmEntry 1 }


pm1008dcpAlmRxPowerHighAlarmPortn OBJECT-TYPE
	SYNTAX  EkiOnOff
	MAX-ACCESS read-only
	STATUS current
	DESCRIPTION
        "
        Line Optical Rx Power High :Alarm 
        indicating that the XFP received 
        optical power is higher than the 
        threshold value written in the
         XFP EEPROM <Condtype> RX_POWER_HIGH_ALARM_1 
        <Probcause> receiveFailure (41) 
        <Alarmtype> equipmentAlarm (5)
         <Polarity> (2) 
        "
	::= { pm1008dcpAlmlineXfp1AlarmEntry 17 }


pm1008dcpAlmRxPowerLowAlarmPortn OBJECT-TYPE
	SYNTAX  EkiOnOff
	MAX-ACCESS read-only
	STATUS current
	DESCRIPTION
        "
        Line Optical Rx Power Low :Alarm 
        indicating that the XFP received 
        optical power is lower than the 
        threshold value written in the
         XFP EEPROM  <Condtype> RX_POWER_LOW_ALARM_1 
        <Probcause> receiveFailure (41) 
        <Alarmtype> equipmentAlarm (5)
         <Polarity> (2) 
        "
	::= { pm1008dcpAlmlineXfp1AlarmEntry 16 }


pm1008dcpAlmTempHighAlarmPortn OBJECT-TYPE
	SYNTAX  EkiOnOff
	MAX-ACCESS read-only
	STATUS current
	DESCRIPTION
        "
        Line Transceiver Temp High :Alarm 
        indicating that the XFP/OTX temperature 
        is higher than the threshold value 
        written in the XFP EEPROM <Condtype> 
        TEMP_HIGH_ALARM_1 <Probcause> temperatureUnacceptable 
        (51) <Alarmtype> equipmentAlarm 
        (5) <Polarity> (2) 
        "
	::= { pm1008dcpAlmlineXfp1AlarmEntry 9 }


pm1008dcpAlmTempLowAlarmPortn OBJECT-TYPE
	SYNTAX  EkiOnOff
	MAX-ACCESS read-only
	STATUS current
	DESCRIPTION
        "
        Line Transceiver Temp Low :Alarm 
        indicating that the XFP/OTX temperature 
        is lower than the threshold value 
        written in the XFP/OTX EEPROM <Condtype> 
        TEMP_LOW_ALARM_1 <Probcause> temperatureUnacceptable 
        (51) <Alarmtype> equipmentAlarm 
        (5) <Polarity> (2) 
        "
	::= { pm1008dcpAlmlineXfp1AlarmEntry 8 }


pm1008dcpAlmTxBiasHighAlarmPortn OBJECT-TYPE
	SYNTAX  EkiOnOff
	MAX-ACCESS read-only
	STATUS current
	DESCRIPTION
        "
        Line Transceiver Bias High :Alarm 
        indicating that the XFP/OTX transmitter 
        laser bias current is higher than 
        the threshold value written in
         the XFP EEPROM <Condtype> TX_BIAS_HIGH_ALARM_1 
        <Probcause> transmitterFailure
         (56) <Alarmtype> equipmentAlarm 
        (5) <Polarity> (2) 
        "
	::= { pm1008dcpAlmlineXfp1AlarmEntry 5 }


pm1008dcpAlmTxBiasLowAlarmPortn OBJECT-TYPE
	SYNTAX  EkiOnOff
	MAX-ACCESS read-only
	STATUS current
	DESCRIPTION
        "
        Line Transceiver Bias Low :Alarm 
        indicating that the XFP/OTX transmitter 
        laser bias current is lower than 
        the threshold value written in
         the XFP/OTX EEPROM <Condtype>
         TX_BIAS_LOW_ALARM_1 <Probcause> 
        transmitterFailure (56) <Alarmtype> 
        equipmentAlarm (5) <Polarity> (2) 
        "
	::= { pm1008dcpAlmlineXfp1AlarmEntry 4 }


pm1008dcpAlmTxPowerHighAlarmPortn OBJECT-TYPE
	SYNTAX  EkiOnOff
	MAX-ACCESS read-only
	STATUS current
	DESCRIPTION
        "
        Line Optical Tx Power High :Alarm 
        indicating that the XFP/OTX transmitter 
        transmitter output power is higher 
        than the threshold value written 
        in the XFP EEPROM <Condtype> TX_POWER_HIGH_ALARM_1 
        <Probcause> transmitterFailure
         (56) <Alarmtype> equipmentAlarm 
        (5) <Polarity> (2) 
        "
	::= { pm1008dcpAlmlineXfp1AlarmEntry 3 }


pm1008dcpAlmTxPowerLowAlarmPortn OBJECT-TYPE
	SYNTAX  EkiOnOff
	MAX-ACCESS read-only
	STATUS current
	DESCRIPTION
        "
        Line Optical Tx Power Low :Alarm 
        indicating that the XFP/OTX transmitter 
        transmitter output power is lower 
        than the threshold value written 
        in the XFP/OTX EEPROM <Condtype> 
        TX_POWER_LOW_ALARM_1 <Probcause> 
        transmitterFailure (56) <Alarmtype> 
        equipmentAlarm (5) <Polarity> (2) 
        "
	::= { pm1008dcpAlmlineXfp1AlarmEntry 2 }


--- *********************************************************
---     TABLE for the pm1008dcpAlmlineXfp1Warnings articles
--- *********************************************************

pm1008dcpAlmlineXfp1WarningsTable OBJECT-TYPE
	SYNTAX  SEQUENCE OF Pm1008dcpAlmlineXfp1WarningsEntry
	MAX-ACCESS not-accessible
	STATUS current
	DESCRIPTION
        "
        List of pm1008dcpAlmlineXfp1Warnings 
        Article
        "
	::= { pm1008dcpAlmLineNurg 209 }


pm1008dcpAlmlineXfp1WarningsEntry OBJECT-TYPE
	SYNTAX Pm1008dcpAlmlineXfp1WarningsEntry
	MAX-ACCESS not-accessible
	STATUS current
	DESCRIPTION
        "
        Row definition for the pm1008dcpAlmlineXfp1Warnings 
        table
        "
	INDEX   { pm1008dcpAlmlineXfp1WarningsIndex }
	::= { pm1008dcpAlmlineXfp1WarningsTable 1 }


Pm1008dcpAlmlineXfp1WarningsEntry ::=
	SEQUENCE {
	pm1008dcpAlmlineXfp1WarningsIndex
		INTEGER,
	pm1008dcpAlmRxPowerHighWarningPortn
		EkiOnOff,
	pm1008dcpAlmRxPowerLowWarningPortn
		EkiOnOff,
	pm1008dcpAlmTempHighWarningPortn
		EkiOnOff,
	pm1008dcpAlmTempLowWarningPortn
		EkiOnOff,
	pm1008dcpAlmTxBiasHighWarningPortn
		EkiOnOff,
	pm1008dcpAlmTxBiasLowWarningPortn
		EkiOnOff,
	pm1008dcpAlmTxPowerHighWarningPortn
		EkiOnOff,
	pm1008dcpAlmTxPowerLowWarningPortn
		EkiOnOff
	}


pm1008dcpAlmlineXfp1WarningsIndex OBJECT-TYPE
	SYNTAX  INTEGER(0..128)
	MAX-ACCESS  read-only
	STATUS current
	DESCRIPTION
        "
        Index definition for the pm1008dcpAlmlineXfp1Warnings 
        table
        "
	::= { pm1008dcpAlmlineXfp1WarningsEntry 1 }


pm1008dcpAlmRxPowerHighWarningPortn OBJECT-TYPE
	SYNTAX  EkiOnOff
	MAX-ACCESS read-only
	STATUS current
	DESCRIPTION
        "
        Line Optical Rx Power High Warning 
        :Warning indicating that the XFP 
        received optical power is higher 
        than the threshold value written 
        in the XFP EEPROM <Condtype> RX_POWER_HIGH_WARNING_1 
        <Probcause> receiveFailure (41) 
        <Alarmtype> equipmentAlarm (5)
         <Polarity> (2) 
        "
	::= { pm1008dcpAlmlineXfp1WarningsEntry 17 }


pm1008dcpAlmRxPowerLowWarningPortn OBJECT-TYPE
	SYNTAX  EkiOnOff
	MAX-ACCESS read-only
	STATUS current
	DESCRIPTION
        "
        Line Optical Rx Power Low Warning 
        :Warning indicating that the XFP 
        received optical power is lower 
        than the threshold value written 
        in the XFP EEPROM  <Condtype> RX_POWER_LOW_WARNING_1 
        <Probcause> receiveFailure (41) 
        <Alarmtype> equipmentAlarm (5)
         <Polarity> (2) 
        "
	::= { pm1008dcpAlmlineXfp1WarningsEntry 16 }


pm1008dcpAlmTempHighWarningPortn OBJECT-TYPE
	SYNTAX  EkiOnOff
	MAX-ACCESS read-only
	STATUS current
	DESCRIPTION
        "
        Line Transceiver Temp High Warning 
        :Warning indicating that the XFP/OTX 
        temperature is higher than the
         threshold value written in the 
        XFP EEPROM <Condtype> TEMP_HIGH_WARNING_1 
        <Probcause> temperatureUnacceptable 
        (51) <Alarmtype> equipmentAlarm 
        (5) <Polarity> (2) 
        "
	::= { pm1008dcpAlmlineXfp1WarningsEntry 9 }


pm1008dcpAlmTempLowWarningPortn OBJECT-TYPE
	SYNTAX  EkiOnOff
	MAX-ACCESS read-only
	STATUS current
	DESCRIPTION
        "
        Line Transceiver Temp Low Warning 
        :Warning indicating that the XFP/OTX 
        temperature is lower than the threshold 
        value written in the XFP/OTX EEPROM 
        <Condtype> TEMP_LOW_WARNING_1 <Probcause> 
        temperatureUnacceptable (51) <Alarmtype> 
        equipmentAlarm (5) <Polarity> (2) 
        "
	::= { pm1008dcpAlmlineXfp1WarningsEntry 8 }


pm1008dcpAlmTxBiasHighWarningPortn OBJECT-TYPE
	SYNTAX  EkiOnOff
	MAX-ACCESS read-only
	STATUS current
	DESCRIPTION
        "
        Line Transceiver Bias High Warning 
        :Warning indicating that the XFP/OTX 
        transmitter laser bias current
         is higher than the threshold value 
        written in the XFP EEPROM <Condtype> 
        TX_BIAS_HIGH_WARNING_1 <Probcause> 
        transmitterFailure (56) <Alarmtype> 
        equipmentAlarm (5) <Polarity> (2) 
        "
	::= { pm1008dcpAlmlineXfp1WarningsEntry 5 }


pm1008dcpAlmTxBiasLowWarningPortn OBJECT-TYPE
	SYNTAX  EkiOnOff
	MAX-ACCESS read-only
	STATUS current
	DESCRIPTION
        "
        Line Transceiver Bias Low Warning 
        :Warning indicating that the XFP/OTX 
        transmitter laser bias current
         is lower than the threshold value 
        written in the XFP/OTX EEPROM <Condtype> 
        TX_BIAS_LOW_WARNING_1 <Probcause> 
        transmitterFailure (56) <Alarmtype> 
        equipmentAlarm (5) <Polarity> (2) 
        "
	::= { pm1008dcpAlmlineXfp1WarningsEntry 4 }


pm1008dcpAlmTxPowerHighWarningPortn OBJECT-TYPE
	SYNTAX  EkiOnOff
	MAX-ACCESS read-only
	STATUS current
	DESCRIPTION
        "
        Line Optical Tx Power High Warning 
        :Warning indicating that the XFP/OTX 
        transmitter transmitter output
         power is higher than the threshold 
        value written in the XFP EEPROM 
        <Condtype> TX_POWER_HIGH_WARNING_1 
        <Probcause> transmitterFailure
         (56) <Alarmtype> equipmentAlarm 
        (5) <Polarity> (2) 
        "
	::= { pm1008dcpAlmlineXfp1WarningsEntry 3 }


pm1008dcpAlmTxPowerLowWarningPortn OBJECT-TYPE
	SYNTAX  EkiOnOff
	MAX-ACCESS read-only
	STATUS current
	DESCRIPTION
        "
        Line Optical Tx Power Low Warning 
        :Warning indicating that the XFP/OTX 
        transmitter transmitter output
         power is lower than the threshold 
        value written in the XFP/OTX EEPROM 
        <Condtype> TX_POWER_LOW_WARNING_1 
        <Probcause> transmitterFailure
         (56) <Alarmtype> equipmentAlarm 
        (5) <Polarity> (2) 
        "
	::= { pm1008dcpAlmlineXfp1WarningsEntry 2 }


--- *********************************************************
---     TABLE for the pm1008dcpAlmlineXfp1Alarms articles
--- *********************************************************

pm1008dcpAlmlineXfp1AlarmsTable OBJECT-TYPE
	SYNTAX  SEQUENCE OF Pm1008dcpAlmlineXfp1AlarmsEntry
	MAX-ACCESS not-accessible
	STATUS current
	DESCRIPTION
        "
        List of pm1008dcpAlmlineXfp1Alarms 
        Article
        "
	::= { pm1008dcpAlmLineCrit 211 }


pm1008dcpAlmlineXfp1AlarmsEntry OBJECT-TYPE
	SYNTAX Pm1008dcpAlmlineXfp1AlarmsEntry
	MAX-ACCESS not-accessible
	STATUS current
	DESCRIPTION
        "
        Row definition for the pm1008dcpAlmlineXfp1Alarms 
        table
        "
	INDEX   { pm1008dcpAlmlineXfp1AlarmsIndex }
	::= { pm1008dcpAlmlineXfp1AlarmsTable 1 }


Pm1008dcpAlmlineXfp1AlarmsEntry ::=
	SEQUENCE {
	pm1008dcpAlmlineXfp1AlarmsIndex
		INTEGER,
	pm1008dcpAlmApdSupplyFaultPortn
		EkiOnOff,
	pm1008dcpAlmTecFaultPortn
		EkiOnOff,
	pm1008dcpAlmWavelengthUnlockedPortn
		EkiOnOff,
	pm1008dcpAlmChannelNotAcquiredPortn
		EkiOnOff,
	pm1008dcpAlmTxNrPortn
		EkiOnOff,
	pm1008dcpAlmTxFaultPortn
		EkiOnOff,
	pm1008dcpAlmTxCdrNotLockedPortn
		EkiOnOff,
	pm1008dcpAlmRxNrPortn
		EkiOnOff,
	pm1008dcpAlmRxCdrNotLockedPortn
		EkiOnOff,
	pm1008dcpAlmModNrPortn
		EkiOnOff
	}


pm1008dcpAlmlineXfp1AlarmsIndex OBJECT-TYPE
	SYNTAX  INTEGER(0..128)
	MAX-ACCESS  read-only
	STATUS current
	DESCRIPTION
        "
        Index definition for the pm1008dcpAlmlineXfp1Alarms 
        table
        "
	::= { pm1008dcpAlmlineXfp1AlarmsEntry 1 }


pm1008dcpAlmApdSupplyFaultPortn OBJECT-TYPE
	SYNTAX  EkiOnOff
	MAX-ACCESS read-only
	STATUS current
	DESCRIPTION
        "
        Line Rx Photodiode Power Failed 
        :This OID indicates a failure on 
        the APD power supply  <Help>  This 
        alarm indicates if the APD power 
        supply is in fail condition <Condtype> 
        APD_SUPPLY_FAULT_1 <Probcause>
         receiverFailure (42) <Alarmtype> 
        equipmentAlarm (5) <Polarity> (2) 
        "
	::= { pm1008dcpAlmlineXfp1AlarmsEntry 17 }


pm1008dcpAlmTecFaultPortn OBJECT-TYPE
	SYNTAX  EkiOnOff
	MAX-ACCESS read-only
	STATUS current
	DESCRIPTION
        "
        Line Optical Tx Temp Regul Failed 
        :This OID indicates a failure on 
        the TEC module  <Help>  This alarm 
        indicates if the TEC of the line 
        transceiver is in fail condition 
        <Condtype> TEC_FAULT_1 <Probcause> 
        transmitterFailure (56) <Alarmtype> 
        equipmentAlarm (5) <Polarity> (2) 
        "
	::= { pm1008dcpAlmlineXfp1AlarmsEntry 16 }


pm1008dcpAlmWavelengthUnlockedPortn OBJECT-TYPE
	SYNTAX  EkiOnOff
	MAX-ACCESS read-only
	STATUS current
	DESCRIPTION
        "
        Line Optical Tx Wavelength Unlocked 
        :This OID indicates that the wavelength 
        error is exceeding the manufacturer 
        tolerance  <Help>  This alarm indicates 
        if the wavelenght of the line transceiver 
        is locked <Condtype> WAVELENGTH_UNLOCKED_1 
        <Probcause> transmitterFailure
         (56) <Alarmtype> equipmentAlarm 
        (5) <Polarity> (2) 
        "
	::= { pm1008dcpAlmlineXfp1AlarmsEntry 15 }


pm1008dcpAlmChannelNotAcquiredPortn OBJECT-TYPE
	SYNTAX  EkiOnOff
	MAX-ACCESS read-only
	STATUS current
	DESCRIPTION
        "
        DWDM Channel Not Acquired :This 
        OID indicates the transceiver didn't 
        tune the DWDM Channel succesfully. 
         <Help>  This status indicates
         the transceiver has not tuned
         the DWDM Channel succesfully.
         <Condtype> CHANNEL_NOT_ACQUIRED_1 
        <Probcause> receiveFailure (41) 
        <Alarmtype> equipmentAlarm (5)
         <Polarity> (2) 
        "
	::= { pm1008dcpAlmlineXfp1AlarmsEntry 11 }


pm1008dcpAlmTxNrPortn OBJECT-TYPE
	SYNTAX  EkiOnOff
	MAX-ACCESS read-only
	STATUS current
	DESCRIPTION
        "
        Line Optical Tx Not Ready :This 
        OID indicates a condition has arisen 
        leading to invalid data on the
         transmitting side  <Help>  This 
        alarm indicates if the Tx part
         of the line transceiver is ready 
        <Condtype> TX_NR_1 <Probcause>
         transmitterFailure (56) <Alarmtype> 
        equipmentAlarm (5) <Polarity> (2) 
        "
	::= { pm1008dcpAlmlineXfp1AlarmsEntry 9 }


pm1008dcpAlmTxFaultPortn OBJECT-TYPE
	SYNTAX  EkiOnOff
	MAX-ACCESS read-only
	STATUS current
	DESCRIPTION
        "
        Line Optical Tx Failure :This
         OID indicates a fault condition 
        on the laser detected by the safety 
        syste  <Help>  This alarm indicates 
        if the laser of the line transceiver 
        is in fail condition <Condtype> 
        TX_FAULT_1 <Probcause> transmitterFailure 
        (56) <Alarmtype> equipmentAlarm 
        (5) <Polarity> (2) 
        "
	::= { pm1008dcpAlmlineXfp1AlarmsEntry 8 }


pm1008dcpAlmTxCdrNotLockedPortn OBJECT-TYPE
	SYNTAX  EkiOnOff
	MAX-ACCESS read-only
	STATUS current
	DESCRIPTION
        "
        Line Optical Tx CDR Unlocked :This 
        OID indicates a loss of lock on 
        the transmitting side CDR has been 
        detected.  <Help>  This alarm indicates 
        if the Tx CDR is locked in the
         line transceiver <Condtype> TX_CDR_NOT_LOCKED1_1 
        <Probcause> transmitterFailure
         (56) <Alarmtype> equipmentAlarm 
        (5) <Polarity> (2) 
        "
	::= { pm1008dcpAlmlineXfp1AlarmsEntry 7 }


pm1008dcpAlmRxNrPortn OBJECT-TYPE
	SYNTAX  EkiOnOff
	MAX-ACCESS read-only
	STATUS current
	DESCRIPTION
        "
        Line Optical Rx Not Ready :This 
        OID indicates that a condition
         has arisen leading to invalid
         data on the receiving side.  <Help> 
         This alarm indicates if the Rx 
        part of the line transceiver is 
        ready <Condtype> RX_NR_1 <Probcause> 
        receiveFailure (41) <Alarmtype> 
        equipmentAlarm (5) <Polarity> (2) 
        "
	::= { pm1008dcpAlmlineXfp1AlarmsEntry 6 }


pm1008dcpAlmRxCdrNotLockedPortn OBJECT-TYPE
	SYNTAX  EkiOnOff
	MAX-ACCESS read-only
	STATUS current
	DESCRIPTION
        "
        Line Optical Rx CDR Unlocked :This 
        OID indicates that a loss of lock 
        on the receiving side CDR has been 
        detected  <Help>  This alarm indicates 
        if the Rx CDR is locked in the
         line transceiver <Condtype> RX_CDR_NOT_LOCKED1_1 
        <Probcause> receiveFailure (41) 
        <Alarmtype> equipmentAlarm (5)
         <Polarity> (2) 
        "
	::= { pm1008dcpAlmlineXfp1AlarmsEntry 4 }


pm1008dcpAlmModNrPortn OBJECT-TYPE
	SYNTAX  EkiOnOff
	MAX-ACCESS read-only
	STATUS current
	DESCRIPTION
        "
        Line Optical Module Not Ready
         :This OID indicates that the module 
        is unable to determine correct
         data.  <Help>  This alarm indicates 
        if the line transceiver is ready 
        <Condtype> MOD_NR_1 <Probcause> 
        receiveFailure (41) <Alarmtype> 
        equipmentAlarm (5) <Polarity> (2) 
        "
	::= { pm1008dcpAlmlineXfp1AlarmsEntry 3 }


--- *********************************************************
---     TABLE for the pm1008dcpAlmlineXfp1SupplyAlarm articles
--- *********************************************************

pm1008dcpAlmlineXfp1SupplyAlarmTable OBJECT-TYPE
	SYNTAX  SEQUENCE OF Pm1008dcpAlmlineXfp1SupplyAlarmEntry
	MAX-ACCESS not-accessible
	STATUS current
	DESCRIPTION
        "
        List of pm1008dcpAlmlineXfp1SupplyAlarm 
        Article
        "
	::= { pm1008dcpAlmLineUrg 212 }


pm1008dcpAlmlineXfp1SupplyAlarmEntry OBJECT-TYPE
	SYNTAX Pm1008dcpAlmlineXfp1SupplyAlarmEntry
	MAX-ACCESS not-accessible
	STATUS current
	DESCRIPTION
        "
        Row definition for the pm1008dcpAlmlineXfp1SupplyAlarm 
        table
        "
	INDEX   { pm1008dcpAlmlineXfp1SupplyAlarmIndex }
	::= { pm1008dcpAlmlineXfp1SupplyAlarmTable 1 }


Pm1008dcpAlmlineXfp1SupplyAlarmEntry ::=
	SEQUENCE {
	pm1008dcpAlmlineXfp1SupplyAlarmIndex
		INTEGER,
	pm1008dcpAlmVcc5HighWarningPortn
		EkiOnOff,
	pm1008dcpAlmVcc5LowWarningPortn
		EkiOnOff,
	pm1008dcpAlmVcc3HighWarningPortn
		EkiOnOff,
	pm1008dcpAlmVcc3LowWarningPortn
		EkiOnOff,
	pm1008dcpAlmVcc2HighWarningPortn
		EkiOnOff,
	pm1008dcpAlmVcc2LowWarningPortn
		EkiOnOff,
	pm1008dcpAlmVee5HighWarningPortn
		EkiOnOff,
	pm1008dcpAlmVee5LowWarningPortn
		EkiOnOff,
	pm1008dcpAlmVcc5HighAlarmPortn
		EkiOnOff,
	pm1008dcpAlmVcc5LowAlarmPortn
		EkiOnOff,
	pm1008dcpAlmVcc3HighAlarmPortn
		EkiOnOff,
	pm1008dcpAlmVcc3LowAlarmPortn
		EkiOnOff,
	pm1008dcpAlmVcc2HighAlarmPortn
		EkiOnOff,
	pm1008dcpAlmVcc2LowAlarmPortn
		EkiOnOff,
	pm1008dcpAlmVee5HighAlarmPortn
		EkiOnOff,
	pm1008dcpAlmVee5LowAlarmPortn
		EkiOnOff
	}


pm1008dcpAlmlineXfp1SupplyAlarmIndex OBJECT-TYPE
	SYNTAX  INTEGER(0..128)
	MAX-ACCESS  read-only
	STATUS current
	DESCRIPTION
        "
        Index definition for the pm1008dcpAlmlineXfp1SupplyAlarm 
        table
        "
	::= { pm1008dcpAlmlineXfp1SupplyAlarmEntry 1 }


pm1008dcpAlmVcc5HighWarningPortn OBJECT-TYPE
	SYNTAX  EkiOnOff
	MAX-ACCESS read-only
	STATUS current
	DESCRIPTION
        "
        VCC5 Power Supply High Warning 
        :Warning indicating the XFP/OTX 
        VCC5 power supply is higher than 
        the threshold written in the EEPROM 
        <Condtype> VCC5_HIGH_WARNING_1
         <Probcause> powerProblem (36)
         <Alarmtype> equipmentAlarm (5) 
        <Polarity> (2) 
        "
	::= { pm1008dcpAlmlineXfp1SupplyAlarmEntry 17 }


pm1008dcpAlmVcc5LowWarningPortn OBJECT-TYPE
	SYNTAX  EkiOnOff
	MAX-ACCESS read-only
	STATUS current
	DESCRIPTION
        "
        VCC5 Power Supply Low Warning
         :Warning indicating the XFP/OTX 
        VCC5 power supply is lower than 
        the threshold written in the EEPROM 
        <Condtype> VCC5_LOW_WARNING_1 <Probcause> 
        powerProblem (36) <Alarmtype> equipmentAlarm 
        (5) <Polarity> (2) 
        "
	::= { pm1008dcpAlmlineXfp1SupplyAlarmEntry 16 }


pm1008dcpAlmVcc3HighWarningPortn OBJECT-TYPE
	SYNTAX  EkiOnOff
	MAX-ACCESS read-only
	STATUS current
	DESCRIPTION
        "
        VCC3 Power Supply High Warning 
        :Warning indicating the XFP/OTX 
        VCC3 power supply is higher than 
        the threshold written in the EEPROM 
        <Condtype> VCC3_HIGH_WARNING_1
         <Probcause> powerProblem (36)
         <Alarmtype> equipmentAlarm (5) 
        <Polarity> (2) 
        "
	::= { pm1008dcpAlmlineXfp1SupplyAlarmEntry 15 }


pm1008dcpAlmVcc3LowWarningPortn OBJECT-TYPE
	SYNTAX  EkiOnOff
	MAX-ACCESS read-only
	STATUS current
	DESCRIPTION
        "
        VCC3 Power Supply Low Warning
         :Warning indicating the XFP/OTX 
        VCC3 power supply is lower than 
        the threshold written in the EEPROM 
        <Condtype> VCC3_LOW_WARNING_1 <Probcause> 
        powerProblem (36) <Alarmtype> equipmentAlarm 
        (5) <Polarity> (2) 
        "
	::= { pm1008dcpAlmlineXfp1SupplyAlarmEntry 14 }


pm1008dcpAlmVcc2HighWarningPortn OBJECT-TYPE
	SYNTAX  EkiOnOff
	MAX-ACCESS read-only
	STATUS current
	DESCRIPTION
        "
        VCC2 Power Supply High Warning 
        :Warning indicating the XFP/OTX 
        VCC2 power supply is higher than 
        the threshold written in the EEPROM 
        <Condtype> VCC2_HIGH_WARNING_1
         <Probcause> powerProblem (36)
         <Alarmtype> equipmentAlarm (5) 
        <Polarity> (2) 
        "
	::= { pm1008dcpAlmlineXfp1SupplyAlarmEntry 13 }


pm1008dcpAlmVcc2LowWarningPortn OBJECT-TYPE
	SYNTAX  EkiOnOff
	MAX-ACCESS read-only
	STATUS current
	DESCRIPTION
        "
        VCC2 Power Supply Low Warning
         :Warning indicating the XFP/OTX 
        VCC2 power supply is lower than 
        the threshold written in the EEPROM 
        <Condtype> VCC2_LOW_WARNING_1 <Probcause> 
        powerProblem (36) <Alarmtype> equipmentAlarm 
        (5) <Polarity> (2) 
        "
	::= { pm1008dcpAlmlineXfp1SupplyAlarmEntry 12 }


pm1008dcpAlmVee5HighWarningPortn OBJECT-TYPE
	SYNTAX  EkiOnOff
	MAX-ACCESS read-only
	STATUS current
	DESCRIPTION
        "
        VEE5 Power Supply High Warning 
        :Warning indicating the XFP/OTX 
        VEE5 power supply is higher than 
        the threshold written in the EEPROM 
        <Condtype> VEE5_HIGH_WARNING_1
         <Probcause> powerProblem (36)
         <Alarmtype> equipmentAlarm (5) 
        <Polarity> (2) 
        "
	::= { pm1008dcpAlmlineXfp1SupplyAlarmEntry 11 }


pm1008dcpAlmVee5LowWarningPortn OBJECT-TYPE
	SYNTAX  EkiOnOff
	MAX-ACCESS read-only
	STATUS current
	DESCRIPTION
        "
        VEE5 Power Supply Low Warning
         :Warning indicating the XFP/OTX 
        VEE5 power supply is lower than 
        the threshold written in the EEPROM 
        <Condtype> VEE5_LOW_WARNING_1 <Probcause> 
        powerProblem (36) <Alarmtype> equipmentAlarm 
        (5) <Polarity> (2) 
        "
	::= { pm1008dcpAlmlineXfp1SupplyAlarmEntry 10 }


pm1008dcpAlmVcc5HighAlarmPortn OBJECT-TYPE
	SYNTAX  EkiOnOff
	MAX-ACCESS read-only
	STATUS current
	DESCRIPTION
        "
        VCC5 Power Supply High :Alarm
         indicating the XFP/OTX VCC5 power 
        supply is higher than the threshold 
        written in the EEPROM <Condtype> 
        VCC5_HIGH_ALARM_1 <Probcause> powerProblem 
        (36) <Alarmtype> equipmentAlarm 
        (5) <Polarity> (2) 
        "
	::= { pm1008dcpAlmlineXfp1SupplyAlarmEntry 9 }


pm1008dcpAlmVcc5LowAlarmPortn OBJECT-TYPE
	SYNTAX  EkiOnOff
	MAX-ACCESS read-only
	STATUS current
	DESCRIPTION
        "
        VCC5 Power Supply Low :Alarm indicating 
        the XFP/OTX VCC5 power supply is 
        lower than the threshold written 
        in the EEPROM <Condtype> VCC5_LOW_ALARM_1 
        <Probcause> powerProblem (36) <Alarmtype> 
        equipmentAlarm (5) <Polarity> (2) 
        "
	::= { pm1008dcpAlmlineXfp1SupplyAlarmEntry 8 }


pm1008dcpAlmVcc3HighAlarmPortn OBJECT-TYPE
	SYNTAX  EkiOnOff
	MAX-ACCESS read-only
	STATUS current
	DESCRIPTION
        "
        VCC3 Power Supply High :Alarm
         indicating the XFP/OTX VCC3 power 
        supply is higher than the threshold 
        written in the EEPROM <Condtype> 
        VCC3_HIGH_ALARM_1 <Probcause> powerProblem 
        (36) <Alarmtype> equipmentAlarm 
        (5) <Polarity> (2) 
        "
	::= { pm1008dcpAlmlineXfp1SupplyAlarmEntry 7 }


pm1008dcpAlmVcc3LowAlarmPortn OBJECT-TYPE
	SYNTAX  EkiOnOff
	MAX-ACCESS read-only
	STATUS current
	DESCRIPTION
        "
        VCC3 Power Supply Low :Alarm indicating 
        the XFP/OTX VCC3 power supply is 
        lower than the threshold written 
        in the EEPROM <Condtype> VCC3_LOW_ALARM_1 
        <Probcause> powerProblem (36) <Alarmtype> 
        equipmentAlarm (5) <Polarity> (2) 
        "
	::= { pm1008dcpAlmlineXfp1SupplyAlarmEntry 6 }


pm1008dcpAlmVcc2HighAlarmPortn OBJECT-TYPE
	SYNTAX  EkiOnOff
	MAX-ACCESS read-only
	STATUS current
	DESCRIPTION
        "
        VCC2 Power Supply High :Alarm
         indicating the XFP/OTX VCC2 power 
        supply is higher than the threshold 
        written in the EEPROM <Condtype> 
        VCC2_HIGH_ALARM_1 <Probcause> powerProblem 
        (36) <Alarmtype> equipmentAlarm 
        (5) <Polarity> (2) 
        "
	::= { pm1008dcpAlmlineXfp1SupplyAlarmEntry 5 }


pm1008dcpAlmVcc2LowAlarmPortn OBJECT-TYPE
	SYNTAX  EkiOnOff
	MAX-ACCESS read-only
	STATUS current
	DESCRIPTION
        "
        VCC2 Power Supply Low :Alarm indicating 
        the XFP/OTX VCC2 power supply is 
        lower than the threshold written 
        in the EEPROM <Condtype> VCC2_LOW_ALARM_1 
        <Probcause> powerProblem (36) <Alarmtype> 
        equipmentAlarm (5) <Polarity> (2) 
        "
	::= { pm1008dcpAlmlineXfp1SupplyAlarmEntry 4 }


pm1008dcpAlmVee5HighAlarmPortn OBJECT-TYPE
	SYNTAX  EkiOnOff
	MAX-ACCESS read-only
	STATUS current
	DESCRIPTION
        "
        VEE5 Power Supply High :Alarm
         indicating the XFP/OTX VEE5 power 
        supply is higher than the threshold 
        written in the EEPROM <Condtype> 
        VEE5_HIGH_ALARM_1 <Probcause> powerProblem 
        (36) <Alarmtype> equipmentAlarm 
        (5) <Polarity> (2) 
        "
	::= { pm1008dcpAlmlineXfp1SupplyAlarmEntry 3 }


pm1008dcpAlmVee5LowAlarmPortn OBJECT-TYPE
	SYNTAX  EkiOnOff
	MAX-ACCESS read-only
	STATUS current
	DESCRIPTION
        "
        VEE5 Power Supply Low :Alarm indicating 
        the XFP/OTX VEE5 power supply is 
        lower than the threshold written 
        in the EEPROM <Condtype> VEE5_LOW_ALARM_1 
        <Probcause> powerProblem (36) <Alarmtype> 
        equipmentAlarm (5) <Polarity> (2) 
        "
	::= { pm1008dcpAlmlineXfp1SupplyAlarmEntry 2 }


--- *********************************************************
---     TABLE for the pm1008dcpAlmlineOtx1TlhAlarms articles
--- *********************************************************

pm1008dcpAlmlineOtx1TlhAlarmsTable OBJECT-TYPE
	SYNTAX  SEQUENCE OF Pm1008dcpAlmlineOtx1TlhAlarmsEntry
	MAX-ACCESS not-accessible
	STATUS current
	DESCRIPTION
        "
        List of pm1008dcpAlmlineOtx1TlhAlarms 
        Article
        "
	::= { pm1008dcpAlmLineUrg 224 }


pm1008dcpAlmlineOtx1TlhAlarmsEntry OBJECT-TYPE
	SYNTAX Pm1008dcpAlmlineOtx1TlhAlarmsEntry
	MAX-ACCESS not-accessible
	STATUS current
	DESCRIPTION
        "
        Row definition for the pm1008dcpAlmlineOtx1TlhAlarms 
        table
        "
	INDEX   { pm1008dcpAlmlineOtx1TlhAlarmsIndex }
	::= { pm1008dcpAlmlineOtx1TlhAlarmsTable 1 }


Pm1008dcpAlmlineOtx1TlhAlarmsEntry ::=
	SEQUENCE {
	pm1008dcpAlmlineOtx1TlhAlarmsIndex
		INTEGER,
	pm1008dcpAlmLineLaserTempHighAlaPortn
		EkiOnOff,
	pm1008dcpAlmLineFreqDevHighAlaPortn
		EkiOnOff,
	pm1008dcpAlmLineCdrNotReadyPortn
		EkiOnOff,
	pm1008dcpAlmLineAgingHighAlaPortn
		EkiOnOff,
	pm1008dcpAlmLineModulatorAgingHighAlaPortn
		EkiOnOff
	}


pm1008dcpAlmlineOtx1TlhAlarmsIndex OBJECT-TYPE
	SYNTAX  INTEGER(0..128)
	MAX-ACCESS  read-only
	STATUS current
	DESCRIPTION
        "
        Index definition for the pm1008dcpAlmlineOtx1TlhAlarms 
        table
        "
	::= { pm1008dcpAlmlineOtx1TlhAlarmsEntry 1 }


pm1008dcpAlmLineLaserTempHighAlaPortn OBJECT-TYPE
	SYNTAX  EkiOnOff
	MAX-ACCESS read-only
	STATUS current
	DESCRIPTION
        "
        Line Laser Temp. High Alarm :Alarm 
        indicating the Line OTX TLH laser 
        temperature is higher than the
         threshold written in the EEPROM 
        <Condtype> LINE_LASER_TEMP_HIGH_ALA_1 
        <Probcause> temperatureUnacceptable 
        (51) <Alarmtype> equipmentAlarm 
        (5) <Polarity> (2) 
        "
	::= { pm1008dcpAlmlineOtx1TlhAlarmsEntry 15 }


pm1008dcpAlmLineFreqDevHighAlaPortn OBJECT-TYPE
	SYNTAX  EkiOnOff
	MAX-ACCESS read-only
	STATUS current
	DESCRIPTION
        "
        Line Freq. Deviation High Alarm 
        :Alarm indicating the Line OTX
         TLH frequency deviation is higher 
        than the threshold written in the 
        EEPROM <Condtype> LINE_FREQ_DEV_HIGH_ALA_1 
        <Probcause> transmitterFailure
         (56) <Alarmtype> equipmentAlarm 
        (5) <Polarity> (2) 
        "
	::= { pm1008dcpAlmlineOtx1TlhAlarmsEntry 13 }


pm1008dcpAlmLineCdrNotReadyPortn OBJECT-TYPE
	SYNTAX  EkiOnOff
	MAX-ACCESS read-only
	STATUS current
	DESCRIPTION
        "
        CDR Not Ready :This OID indicates 
        the Clock Data Recovery unit is 
        not yet initialized.   <Help> 
         This alarm indicates the Clock 
        Data Recovery unit is not yet initialized. 
        <Condtype> LINE_CDR_NOT_READY_1 
        <Probcause> receiveFailure (41) 
        <Alarmtype> equipmentAlarm (5)
         <Polarity> (2) 
        "
	::= { pm1008dcpAlmlineOtx1TlhAlarmsEntry 10 }


pm1008dcpAlmLineAgingHighAlaPortn OBJECT-TYPE
	SYNTAX  EkiOnOff
	MAX-ACCESS read-only
	STATUS current
	DESCRIPTION
        "
        Line OTX TLH Aging High Alarm
         :Alarm indicating the Line OTX 
        TLH aging is higher than the threshold 
        written in the EEPROM <Condtype> 
        LINE_AGING_HIGH_ALA_1 <Probcause> 
        transmitterFailure (56) <Alarmtype> 
        equipmentAlarm (5) <Polarity> (2) 
        "
	::= { pm1008dcpAlmlineOtx1TlhAlarmsEntry 7 }


pm1008dcpAlmLineModulatorAgingHighAlaPortn OBJECT-TYPE
	SYNTAX  EkiOnOff
	MAX-ACCESS read-only
	STATUS current
	DESCRIPTION
        "
        Line Modulator Aging High Alarm 
        :Alarm indicating the Line OTX
         TLH modulator aging is higher
         than the threshold written in
         the EEPROM <Condtype> LINE_MODULATOR_AGING_HIGH_ALA_1 
        <Probcause> transmitterFailure
         (56) <Alarmtype> equipmentAlarm 
        (5) <Polarity> (2) 
        "
	::= { pm1008dcpAlmlineOtx1TlhAlarmsEntry 6 }


--- *********************************************************
---     TABLE for the pm1008dcpAlmlineOtx1TlhWarnings articles
--- *********************************************************

pm1008dcpAlmlineOtx1TlhWarningsTable OBJECT-TYPE
	SYNTAX  SEQUENCE OF Pm1008dcpAlmlineOtx1TlhWarningsEntry
	MAX-ACCESS not-accessible
	STATUS current
	DESCRIPTION
        "
        List of pm1008dcpAlmlineOtx1TlhWarnings 
        Article
        "
	::= { pm1008dcpAlmLineNurg 225 }


pm1008dcpAlmlineOtx1TlhWarningsEntry OBJECT-TYPE
	SYNTAX Pm1008dcpAlmlineOtx1TlhWarningsEntry
	MAX-ACCESS not-accessible
	STATUS current
	DESCRIPTION
        "
        Row definition for the pm1008dcpAlmlineOtx1TlhWarnings 
        table
        "
	INDEX   { pm1008dcpAlmlineOtx1TlhWarningsIndex }
	::= { pm1008dcpAlmlineOtx1TlhWarningsTable 1 }


Pm1008dcpAlmlineOtx1TlhWarningsEntry ::=
	SEQUENCE {
	pm1008dcpAlmlineOtx1TlhWarningsIndex
		INTEGER,
	pm1008dcpAlmLineLaserTempHighWarningPortn
		EkiOnOff,
	pm1008dcpAlmLineFreqDevHighWarningPortn
		EkiOnOff,
	pm1008dcpAlmLineAgingHighWarningPortn
		EkiOnOff,
	pm1008dcpAlmLineModulatorAgingHighWarningPortn
		EkiOnOff
	}


pm1008dcpAlmlineOtx1TlhWarningsIndex OBJECT-TYPE
	SYNTAX  INTEGER(0..128)
	MAX-ACCESS  read-only
	STATUS current
	DESCRIPTION
        "
        Index definition for the pm1008dcpAlmlineOtx1TlhWarnings 
        table
        "
	::= { pm1008dcpAlmlineOtx1TlhWarningsEntry 1 }


pm1008dcpAlmLineLaserTempHighWarningPortn OBJECT-TYPE
	SYNTAX  EkiOnOff
	MAX-ACCESS read-only
	STATUS current
	DESCRIPTION
        "
        Line Laser Temp. High Warning
         :Warning indicating the Line OTX 
        TLH laser temperature is higher 
        than the threshold written in the 
        EEPROM <Condtype> LINE_LASER_TEMP_HIGH_WARNING_1 
        <Probcause> temperatureUnacceptable 
        (51) <Alarmtype> equipmentAlarm 
        (5) <Polarity> (2) 
        "
	::= { pm1008dcpAlmlineOtx1TlhWarningsEntry 15 }


pm1008dcpAlmLineFreqDevHighWarningPortn OBJECT-TYPE
	SYNTAX  EkiOnOff
	MAX-ACCESS read-only
	STATUS current
	DESCRIPTION
        "
        Line Freq. Deviation High Warning 
        :Warning indicating the Line OTX 
        TLH frequency deviation is higher 
        than the threshold written in the 
        EEPROM <Condtype> LINE_FREQ_DEV_HIGH_WARNING_1 
        <Probcause> transmitterFailure
         (56) <Alarmtype> equipmentAlarm 
        (5) <Polarity> (2) 
        "
	::= { pm1008dcpAlmlineOtx1TlhWarningsEntry 13 }


pm1008dcpAlmLineAgingHighWarningPortn OBJECT-TYPE
	SYNTAX  EkiOnOff
	MAX-ACCESS read-only
	STATUS current
	DESCRIPTION
        "
        Line OTX TLH Aging High Warning 
        :Warning indicating the Line OTX 
        TLH aging is higher than the threshold 
        written in the EEPROM <Condtype> 
        LINE_AGING_HIGH_WARNING_1 <Probcause> 
        transmitterFailure (56) <Alarmtype> 
        equipmentAlarm (5) <Polarity> (2) 
        "
	::= { pm1008dcpAlmlineOtx1TlhWarningsEntry 7 }


pm1008dcpAlmLineModulatorAgingHighWarningPortn OBJECT-TYPE
	SYNTAX  EkiOnOff
	MAX-ACCESS read-only
	STATUS current
	DESCRIPTION
        "
        Line Modulator Aging High Warning 
        :Warning indicating the Line OTX 
        TLH modulator aging is higher than 
        the threshold written in the EEPROM 
        <Condtype> LINE_MODULATOR_AGING_HIGH_WARNING_1 
        <Probcause> transmitterFailure
         (56) <Alarmtype> equipmentAlarm 
        (5) <Polarity> (2) 
        "
	::= { pm1008dcpAlmlineOtx1TlhWarningsEntry 6 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm1008dcpCtrlconfMgnt1 OBJECT IDENTIFIER ::= { pm1008dcpCtrlOther 1 }




pm1008dcpCtrlConf2Clear1 OBJECT-TYPE
	  SYNTAX EkiOnOff
	  MAX-ACCESS read-write
	  STATUS current
	  DESCRIPTION
        "
        Clear Configuration Tables :This 
        OID clears the configuration tables 
        from configuration2 in the flash. 
         <Help>  This control restores
         the default configuration of the 
        module
        "
	  ::= { pm1008dcpCtrlconfMgnt1 14 }



pm1008dcpCtrlConf2Flash1 OBJECT-TYPE
	  SYNTAX EkiOnOff
	  MAX-ACCESS read-write
	  STATUS current
	  DESCRIPTION
        "
        Write Configuration Tables :This 
        OID saves the current configuration 
        of the PM as configuration2 in
         the flash.  <Help>  This control 
        saves the customer configuration 
        on the module
        "
	  ::= { pm1008dcpCtrlconfMgnt1 10 }



pm1008dcpCtrlConf2Load1 OBJECT-TYPE
	  SYNTAX EkiOnOff
	  MAX-ACCESS read-write
	  STATUS current
	  DESCRIPTION
        "
        Load Configuration Tables Set
         Nb 2 :When set this OID enables 
        loading from flash configuration2 
        into the PM.
        "
	  ::= { pm1008dcpCtrlconfMgnt1 2 }



pm1008dcpCtrlConf1Load1 OBJECT-TYPE
	  SYNTAX EkiOnOff
	  MAX-ACCESS read-write
	  STATUS current
	  DESCRIPTION
        "
        Load Configuration Tables Set
         Nb 1 :When set this OID enables 
        loading from flash configuration1 
        into the PM.
        "
	  ::= { pm1008dcpCtrlconfMgnt1 1 }



--- *****************************************************
---     LEAF for the synth4 article
--- *****************************************************
pm1008dcpCtrlsynth4 OBJECT IDENTIFIER ::= { pm1008dcpCtrlOther 4 }




pm1008dcpCtrlCorrelatOff OBJECT-TYPE
	  SYNTAX EkiOnOff
	  MAX-ACCESS read-write
	  STATUS current
	  DESCRIPTION
        "
        Disable Alarm Correlation :This 
        OID disables the alarm correlation 
        in the PM.
        "
	  ::= { pm1008dcpCtrlsynth4 2 }



pm1008dcpCtrlCorrelatOn OBJECT-TYPE
	  SYNTAX EkiOnOff
	  MAX-ACCESS read-write
	  STATUS current
	  DESCRIPTION
        "
        Enable Alarm Correlation :This 
        OID enables the alarm correlation 
        in the PM.
        "
	  ::= { pm1008dcpCtrlsynth4 1 }



--- *****************************************************
---     LEAF for the swMgnt article
--- *****************************************************
pm1008dcpCtrlswMgnt OBJECT IDENTIFIER ::= { pm1008dcpCtrlOther 5 }




pm1008dcpCtrlLoadSwBank2 OBJECT-TYPE
	  SYNTAX EkiOnOff
	  MAX-ACCESS read-write
	  STATUS current
	  DESCRIPTION
        "
        Set Software Nb 2 As Active :This 
        OID, when set, loads the SW from 
        bank2 into the PM. It must be followed 
        by a reset.  <Help>  This controls 
        selects the second SW bank as the 
        active bank for the next module 
        reset
        "
	  ::= { pm1008dcpCtrlswMgnt 6 }



pm1008dcpCtrlLoadSwBank1 OBJECT-TYPE
	  SYNTAX EkiOnOff
	  MAX-ACCESS read-write
	  STATUS current
	  DESCRIPTION
        "
        Set Software Nb 1 As Active :This 
        OID, when set, loads the SW from 
        bank1 into the PM. It must be followed 
        by a reset.  <Help>  This controls 
        selects the first SW bank as the 
        active bank for the next module 
        reset
        "
	  ::= { pm1008dcpCtrlswMgnt 5 }



pm1008dcpCtrlWarmReset OBJECT-TYPE
	  SYNTAX EkiOnOff
	  MAX-ACCESS read-write
	  STATUS current
	  DESCRIPTION
        "
        PM Warm Reset :This OID, when
         set, causes a warm reset of the 
        PM. This reset is not traffic affecting, 
        and the configuration of PM remains 
        unchanged.  <Help>  This control 
        initiates a warm reset of the module. 
        "
	  ::= { pm1008dcpCtrlswMgnt 3 }



pm1008dcpCtrlColdReset OBJECT-TYPE
	  SYNTAX EkiOnOff
	  MAX-ACCESS read-write
	  STATUS current
	  DESCRIPTION
        "
        PM Cold Reset :This OID, when
         set, causes a cold reset of the 
        PM. This reset is traffic affecting, 
        and the configuration of PM is
         reloaded on start-up.  <Help>
          This control initiates a cold 
        reset of the module. 
        "
	  ::= { pm1008dcpCtrlswMgnt 2 }



--- *****************************************************
---     LEAF for the gwMgnt article
--- *****************************************************
pm1008dcpCtrlgwMgnt OBJECT IDENTIFIER ::= { pm1008dcpCtrlOther 6 }




pm1008dcpCtrlLoadGwBank4 OBJECT-TYPE
	  SYNTAX EkiOnOff
	  MAX-ACCESS read-write
	  STATUS current
	  DESCRIPTION
        "
        Set Gateware Nb 4 As Active :This 
        OID, when set, loads the GW from 
        bank4 (Flash) into the PM. It is 
        followed by an automatic gateware 
        cold reset.
        "
	  ::= { pm1008dcpCtrlgwMgnt 8 }



pm1008dcpCtrlLoadGwBank3 OBJECT-TYPE
	  SYNTAX EkiOnOff
	  MAX-ACCESS read-write
	  STATUS current
	  DESCRIPTION
        "
        Set Gateware Nb 3 As Active :This 
        OID, when set, loads the GW from 
        bank3 (Flash) into the PM. It is 
        followed by an automatic gateware 
        cold reset.  <Help>  This controls 
        initiates a cold reset of the module 
        and select the third GW bank as 
        the active bank
        "
	  ::= { pm1008dcpCtrlgwMgnt 7 }



pm1008dcpCtrlLoadGwBank2 OBJECT-TYPE
	  SYNTAX EkiOnOff
	  MAX-ACCESS read-write
	  STATUS current
	  DESCRIPTION
        "
        Set Gateware Nb 2 As Active :This 
        OID, when set, loads the GW from 
        bank2 (Flash) into the PM. It is 
        followed by an automatic gateware 
        cold reset.
        "
	  ::= { pm1008dcpCtrlgwMgnt 6 }



pm1008dcpCtrlLoadGwBank1 OBJECT-TYPE
	  SYNTAX EkiOnOff
	  MAX-ACCESS read-write
	  STATUS current
	  DESCRIPTION
        "
        Set Gateware Nb 1 As Active :This 
        OID, when set, loads the GW from 
        bank1 (Flash) into the PM. It is 
        followed by an automatic gateware 
        cold reset.  <Help>  This controls 
        initiates a cold reset of the module 
        and select the first GW bank as 
        the active bank
        "
	  ::= { pm1008dcpCtrlgwMgnt 5 }



pm1008dcpCtrlCurrentGwReset OBJECT-TYPE
	  SYNTAX EkiOnOff
	  MAX-ACCESS read-write
	  STATUS current
	  DESCRIPTION
        "
        Active Gateware Reset :This OID, 
        when set, resets the active gateware. 
        It is traffic affecting.
        "
	  ::= { pm1008dcpCtrlgwMgnt 1 }



--- *********************************************************
---     TABLE for the pm1008dcpCtrlaccessLoop articles
--- *********************************************************

pm1008dcpCtrlaccessLoopTable OBJECT-TYPE
	SYNTAX  SEQUENCE OF Pm1008dcpCtrlaccessLoopEntry
	MAX-ACCESS not-accessible
	STATUS current
	DESCRIPTION
        "
        List of pm1008dcpCtrlaccessLoop 
        Article
        "
	::= { pm1008dcpCtrlClient 16 }


pm1008dcpCtrlaccessLoopEntry OBJECT-TYPE
	SYNTAX Pm1008dcpCtrlaccessLoopEntry
	MAX-ACCESS not-accessible
	STATUS current
	DESCRIPTION
        "
        Row definition for the pm1008dcpCtrlaccessLoop 
        table
        "
	INDEX   { pm1008dcpCtrlaccessLoopIndex }
	::= { pm1008dcpCtrlaccessLoopTable 1 }


Pm1008dcpCtrlaccessLoopEntry ::=
	SEQUENCE {
	pm1008dcpCtrlaccessLoopIndex
		INTEGER,
	pm1008dcpCtrlaccessLoopPortn
		EkiState
	}


pm1008dcpCtrlaccessLoopIndex OBJECT-TYPE
	SYNTAX  INTEGER(0..128)
	MAX-ACCESS  read-only
	STATUS current
	DESCRIPTION
        "
        Index definition for the pm1008dcpCtrlaccessLoop 
        table
        "
	::= { pm1008dcpCtrlaccessLoopEntry 1 }


pm1008dcpCtrlaccessLoopPortn OBJECT-TYPE
	SYNTAX  EkiState
	MAX-ACCESS read-write
	STATUS current
	DESCRIPTION
        "
        Client Facility Loopback :This 
        OID operates a Client Facility
         Loopback, looping client input 
        signal on the client output port. 
        The loop is located on the client 
        transceiver  <Help> This maintenance 
        parameter operates a Client Facility 
        Loopback, looping client input
         signal on the client output port. 
        The loop is located on the client 
        transceiver
        "
	::= { pm1008dcpCtrlaccessLoopEntry 2 }


--- *********************************************************
---     TABLE for the pm1008dcpCtrlportOosMode articles
--- *********************************************************

pm1008dcpCtrlportOosModeTable OBJECT-TYPE
	SYNTAX  SEQUENCE OF Pm1008dcpCtrlportOosModeEntry
	MAX-ACCESS not-accessible
	STATUS current
	DESCRIPTION
        "
        List of pm1008dcpCtrlportOosMode 
        Article
        "
	::= { pm1008dcpCtrlClient 18 }


pm1008dcpCtrlportOosModeEntry OBJECT-TYPE
	SYNTAX Pm1008dcpCtrlportOosModeEntry
	MAX-ACCESS not-accessible
	STATUS current
	DESCRIPTION
        "
        Row definition for the pm1008dcpCtrlportOosMode 
        table
        "
	INDEX   { pm1008dcpCtrlportOosModeIndex }
	::= { pm1008dcpCtrlportOosModeTable 1 }


Pm1008dcpCtrlportOosModeEntry ::=
	SEQUENCE {
	pm1008dcpCtrlportOosModeIndex
		INTEGER,
	pm1008dcpCtrlportOosModePortn
		EkiState
	}


pm1008dcpCtrlportOosModeIndex OBJECT-TYPE
	SYNTAX  INTEGER(0..128)
	MAX-ACCESS  read-only
	STATUS current
	DESCRIPTION
        "
        Index definition for the pm1008dcpCtrlportOosMode 
        table
        "
	::= { pm1008dcpCtrlportOosModeEntry 1 }


pm1008dcpCtrlportOosModePortn OBJECT-TYPE
	SYNTAX  EkiState
	MAX-ACCESS read-write
	STATUS current
	DESCRIPTION
        "
        Client Port Out Of Service :This 
        OID sets the client port Out Of 
        Service  <Help>  This controls
         defines the service state of the 
        client port
        "
	::= { pm1008dcpCtrlportOosModeEntry 2 }


--- *********************************************************
---     TABLE for the pm1008dcpCtrlsfpOnCtrl articles
--- *********************************************************

pm1008dcpCtrlsfpOnCtrlTable OBJECT-TYPE
	SYNTAX  SEQUENCE OF Pm1008dcpCtrlsfpOnCtrlEntry
	MAX-ACCESS not-accessible
	STATUS current
	DESCRIPTION
        "
        List of pm1008dcpCtrlsfpOnCtrl 
        Article
        "
	::= { pm1008dcpCtrlClient 19 }


pm1008dcpCtrlsfpOnCtrlEntry OBJECT-TYPE
	SYNTAX Pm1008dcpCtrlsfpOnCtrlEntry
	MAX-ACCESS not-accessible
	STATUS current
	DESCRIPTION
        "
        Row definition for the pm1008dcpCtrlsfpOnCtrl 
        table
        "
	INDEX   { pm1008dcpCtrlsfpOnCtrlIndex }
	::= { pm1008dcpCtrlsfpOnCtrlTable 1 }


Pm1008dcpCtrlsfpOnCtrlEntry ::=
	SEQUENCE {
	pm1008dcpCtrlsfpOnCtrlIndex
		INTEGER,
	pm1008dcpCtrlsfpOnCtrlPortn
		EkiState
	}


pm1008dcpCtrlsfpOnCtrlIndex OBJECT-TYPE
	SYNTAX  INTEGER(0..128)
	MAX-ACCESS  read-only
	STATUS current
	DESCRIPTION
        "
        Index definition for the pm1008dcpCtrlsfpOnCtrl 
        table
        "
	::= { pm1008dcpCtrlsfpOnCtrlEntry 1 }


pm1008dcpCtrlsfpOnCtrlPortn OBJECT-TYPE
	SYNTAX  EkiState
	MAX-ACCESS read-write
	STATUS current
	DESCRIPTION
        "
        Client SFP Optical Laser ON :This 
        OID switches on the SFP.
        "
	::= { pm1008dcpCtrlsfpOnCtrlEntry 2 }


--- *********************************************************
---     TABLE for the pm1008dcpCtrlsfpOffCtrl articles
--- *********************************************************

pm1008dcpCtrlsfpOffCtrlTable OBJECT-TYPE
	SYNTAX  SEQUENCE OF Pm1008dcpCtrlsfpOffCtrlEntry
	MAX-ACCESS not-accessible
	STATUS current
	DESCRIPTION
        "
        List of pm1008dcpCtrlsfpOffCtrl 
        Article
        "
	::= { pm1008dcpCtrlClient 20 }


pm1008dcpCtrlsfpOffCtrlEntry OBJECT-TYPE
	SYNTAX Pm1008dcpCtrlsfpOffCtrlEntry
	MAX-ACCESS not-accessible
	STATUS current
	DESCRIPTION
        "
        Row definition for the pm1008dcpCtrlsfpOffCtrl 
        table
        "
	INDEX   { pm1008dcpCtrlsfpOffCtrlIndex }
	::= { pm1008dcpCtrlsfpOffCtrlTable 1 }


Pm1008dcpCtrlsfpOffCtrlEntry ::=
	SEQUENCE {
	pm1008dcpCtrlsfpOffCtrlIndex
		INTEGER,
	pm1008dcpCtrlsfpOffCtrlPortn
		EkiState
	}


pm1008dcpCtrlsfpOffCtrlIndex OBJECT-TYPE
	SYNTAX  INTEGER(0..128)
	MAX-ACCESS  read-only
	STATUS current
	DESCRIPTION
        "
        Index definition for the pm1008dcpCtrlsfpOffCtrl 
        table
        "
	::= { pm1008dcpCtrlsfpOffCtrlEntry 1 }


pm1008dcpCtrlsfpOffCtrlPortn OBJECT-TYPE
	SYNTAX  EkiState
	MAX-ACCESS read-write
	STATUS current
	DESCRIPTION
        "
        Client SFP Laser Shutdown :This 
        OID switches off the SFP.  <Help> 
         This control defines the laser 
        state of the client transceiver
        "
	::= { pm1008dcpCtrlsfpOffCtrlEntry 2 }


--- *********************************************************
---     TABLE for the pm1008dcpCtrlcsfUpIns articles
--- *********************************************************

pm1008dcpCtrlcsfUpInsTable OBJECT-TYPE
	SYNTAX  SEQUENCE OF Pm1008dcpCtrlcsfUpInsEntry
	MAX-ACCESS not-accessible
	STATUS current
	DESCRIPTION
        "
        List of pm1008dcpCtrlcsfUpIns
         Article
        "
	::= { pm1008dcpCtrlClient 21 }


pm1008dcpCtrlcsfUpInsEntry OBJECT-TYPE
	SYNTAX Pm1008dcpCtrlcsfUpInsEntry
	MAX-ACCESS not-accessible
	STATUS current
	DESCRIPTION
        "
        Row definition for the pm1008dcpCtrlcsfUpIns 
        table
        "
	INDEX   { pm1008dcpCtrlcsfUpInsIndex }
	::= { pm1008dcpCtrlcsfUpInsTable 1 }


Pm1008dcpCtrlcsfUpInsEntry ::=
	SEQUENCE {
	pm1008dcpCtrlcsfUpInsIndex
		INTEGER,
	pm1008dcpCtrlcsfUpInsPortn
		EkiState
	}


pm1008dcpCtrlcsfUpInsIndex OBJECT-TYPE
	SYNTAX  INTEGER(0..128)
	MAX-ACCESS  read-only
	STATUS current
	DESCRIPTION
        "
        Index definition for the pm1008dcpCtrlcsfUpIns 
        table
        "
	::= { pm1008dcpCtrlcsfUpInsEntry 1 }


pm1008dcpCtrlcsfUpInsPortn OBJECT-TYPE
	SYNTAX  EkiState
	MAX-ACCESS read-write
	STATUS current
	DESCRIPTION
        "
        Client Signal Fail Insertion :This 
        OID, when set, inserts  a client 
        signal fail in the upstream client 
        Port.  <Help>  This control inserts 
        a Client Signal Fail for the client 
        port
        "
	::= { pm1008dcpCtrlcsfUpInsEntry 2 }


--- *********************************************************
---     TABLE for the pm1008dcpCtrlcaisDwIns articles
--- *********************************************************

pm1008dcpCtrlcaisDwInsTable OBJECT-TYPE
	SYNTAX  SEQUENCE OF Pm1008dcpCtrlcaisDwInsEntry
	MAX-ACCESS not-accessible
	STATUS current
	DESCRIPTION
        "
        List of pm1008dcpCtrlcaisDwIns 
        Article
        "
	::= { pm1008dcpCtrlClient 22 }


pm1008dcpCtrlcaisDwInsEntry OBJECT-TYPE
	SYNTAX Pm1008dcpCtrlcaisDwInsEntry
	MAX-ACCESS not-accessible
	STATUS current
	DESCRIPTION
        "
        Row definition for the pm1008dcpCtrlcaisDwIns 
        table
        "
	INDEX   { pm1008dcpCtrlcaisDwInsIndex }
	::= { pm1008dcpCtrlcaisDwInsTable 1 }


Pm1008dcpCtrlcaisDwInsEntry ::=
	SEQUENCE {
	pm1008dcpCtrlcaisDwInsIndex
		INTEGER,
	pm1008dcpCtrlcaisDwInsPortn
		EkiState
	}


pm1008dcpCtrlcaisDwInsIndex OBJECT-TYPE
	SYNTAX  INTEGER(0..128)
	MAX-ACCESS  read-only
	STATUS current
	DESCRIPTION
        "
        Index definition for the pm1008dcpCtrlcaisDwIns 
        table
        "
	::= { pm1008dcpCtrlcaisDwInsEntry 1 }


pm1008dcpCtrlcaisDwInsPortn OBJECT-TYPE
	SYNTAX  EkiState
	MAX-ACCESS read-write
	STATUS current
	DESCRIPTION
        "
        Client AIS Insertion :This OID, 
        when set, inserts a client AIS
         on the downstream client Port. 
         <Help>  This control inserts a 
        Client AIS for the client port
        "
	::= { pm1008dcpCtrlcaisDwInsEntry 2 }


--- *********************************************************
---     TABLE for the pm1008dcpCtrlclientAccessTermLoop articles
--- *********************************************************

pm1008dcpCtrlclientAccessTermLoopTable OBJECT-TYPE
	SYNTAX  SEQUENCE OF Pm1008dcpCtrlclientAccessTermLoopEntry
	MAX-ACCESS not-accessible
	STATUS current
	DESCRIPTION
        "
        List of pm1008dcpCtrlclientAccessTermLoop 
        Article
        "
	::= { pm1008dcpCtrlClient 26 }


pm1008dcpCtrlclientAccessTermLoopEntry OBJECT-TYPE
	SYNTAX Pm1008dcpCtrlclientAccessTermLoopEntry
	MAX-ACCESS not-accessible
	STATUS current
	DESCRIPTION
        "
        Row definition for the pm1008dcpCtrlclientAccessTermLoop 
        table
        "
	INDEX   { pm1008dcpCtrlclientAccessTermLoopIndex }
	::= { pm1008dcpCtrlclientAccessTermLoopTable 1 }


Pm1008dcpCtrlclientAccessTermLoopEntry ::=
	SEQUENCE {
	pm1008dcpCtrlclientAccessTermLoopIndex
		INTEGER,
	pm1008dcpCtrlclientAccessTermLoopPortn
		EkiState
	}


pm1008dcpCtrlclientAccessTermLoopIndex OBJECT-TYPE
	SYNTAX  INTEGER(0..128)
	MAX-ACCESS  read-only
	STATUS current
	DESCRIPTION
        "
        Index definition for the pm1008dcpCtrlclientAccessTermLoop 
        table
        "
	::= { pm1008dcpCtrlclientAccessTermLoopEntry 1 }


pm1008dcpCtrlclientAccessTermLoopPortn OBJECT-TYPE
	SYNTAX  EkiState
	MAX-ACCESS read-write
	STATUS current
	DESCRIPTION
        "
        Client Terminal Loopback :This 
        OID operates a Client Terminal
         Loopback, looping client input 
        signal on the client output port. 
        The loop is located on the line 
        transceiver  <Help> This maintenance 
        parameter operates a Client Terminal 
        Loopback, looping client input
         signal on the client output port. 
        The loop is located on the line 
        transceiver
        "
	::= { pm1008dcpCtrlclientAccessTermLoopEntry 2 }


--- *********************************************************
---     TABLE for the pm1008dcpCtrlprotocol articles
--- *********************************************************

pm1008dcpCtrlprotocolTable OBJECT-TYPE
	SYNTAX  SEQUENCE OF Pm1008dcpCtrlprotocolEntry
	MAX-ACCESS not-accessible
	STATUS current
	DESCRIPTION
        "
        List of pm1008dcpCtrlprotocol
         Article
        "
	::= { pm1008dcpCtrlClient 48 }


pm1008dcpCtrlprotocolEntry OBJECT-TYPE
	SYNTAX Pm1008dcpCtrlprotocolEntry
	MAX-ACCESS not-accessible
	STATUS current
	DESCRIPTION
        "
        Row definition for the pm1008dcpCtrlprotocol 
        table
        "
	INDEX   { pm1008dcpCtrlprotocolIndex }
	::= { pm1008dcpCtrlprotocolTable 1 }


Pm1008dcpCtrlprotocolEntry ::=
	SEQUENCE {
	pm1008dcpCtrlprotocolIndex
		INTEGER,
	pm1008dcpCtrlprotocolPortn
		EkiProtocol
	}


pm1008dcpCtrlprotocolIndex OBJECT-TYPE
	SYNTAX  INTEGER(0..128)
	MAX-ACCESS  read-only
	STATUS current
	DESCRIPTION
        "
        Index definition for the pm1008dcpCtrlprotocol 
        table
        "
	::= { pm1008dcpCtrlprotocolEntry 1 }


pm1008dcpCtrlprotocolPortn OBJECT-TYPE
	SYNTAX  EkiProtocol
	MAX-ACCESS read-write
	STATUS current
	DESCRIPTION
        "
        Protocol used for client port: 
        This OID sets the protocol of the 
        Client port.
        "
	::= { pm1008dcpCtrlprotocolEntry 2 }


--- *****************************************************
---     LEAF for the commAccessLoop article
--- *****************************************************
pm1008dcpCtrlcommAccessLoop OBJECT IDENTIFIER ::= { pm1008dcpCtrlLine 64 }




pm1008dcpCtrlCommAccessloop OBJECT-TYPE
	  SYNTAX EkiOnOff
	  MAX-ACCESS read-write
	  STATUS deprecated
	  DESCRIPTION
        "
        PM Full Access Loop Mode :This 
        OID, when set, puts the module
         in common access loop back, looping 
        the 10 Gb/s output signal on the 
        10 Gb/s input.
        "
	  ::= { pm1008dcpCtrlcommAccessLoop 1 }



--- *****************************************************
---     LEAF for the lineLoop article
--- *****************************************************
pm1008dcpCtrllineLoop OBJECT IDENTIFIER ::= { pm1008dcpCtrlLine 66 }




pm1008dcpCtrlLineLoop OBJECT-TYPE
	  SYNTAX EkiOnOff
	  MAX-ACCESS read-write
	  STATUS deprecated
	  DESCRIPTION
        "
        PM Line Loop Mode :This OID, when 
        set at '1' puts the module in line 
        loopback mode, looping the received 
        10 Gb/s signal on the transmit
         10 Gb/s output. The Upstream part 
        of the module is timed on the 10 
        Gb/s recovered clock in that case.
        "
	  ::= { pm1008dcpCtrllineLoop 1 }



--- *****************************************************
---     LEAF for the msAis article
--- *****************************************************
pm1008dcpCtrlmsAis OBJECT IDENTIFIER ::= { pm1008dcpCtrlLine 67 }




pm1008dcpCtrlMsAis OBJECT-TYPE
	  SYNTAX EkiOnOff
	  MAX-ACCESS read-write
	  STATUS current
	  DESCRIPTION
        "
        Insert MS-AIS/L-AIS On Line Output 
        :This OID, when set, inserts an 
        MS-AIS/L-AIS in the outgoing STM-64/OC-192 
        signal.
        "
	  ::= { pm1008dcpCtrlmsAis 1 }



--- *********************************************************
---     TABLE for the pm1008dcpCtrlfecDisable articles
--- *********************************************************

pm1008dcpCtrlfecDisableTable OBJECT-TYPE
	SYNTAX  SEQUENCE OF Pm1008dcpCtrlfecDisableEntry
	MAX-ACCESS not-accessible
	STATUS current
	DESCRIPTION
        "
        List of pm1008dcpCtrlfecDisable 
        Article
        "
	::= { pm1008dcpCtrlLine 69 }


pm1008dcpCtrlfecDisableEntry OBJECT-TYPE
	SYNTAX Pm1008dcpCtrlfecDisableEntry
	MAX-ACCESS not-accessible
	STATUS current
	DESCRIPTION
        "
        Row definition for the pm1008dcpCtrlfecDisable 
        table
        "
	INDEX   { pm1008dcpCtrlfecDisableIndex }
	::= { pm1008dcpCtrlfecDisableTable 1 }


Pm1008dcpCtrlfecDisableEntry ::=
	SEQUENCE {
	pm1008dcpCtrlfecDisableIndex
		INTEGER,
	pm1008dcpCtrlfecDisablePortn
		EkiState
	}


pm1008dcpCtrlfecDisableIndex OBJECT-TYPE
	SYNTAX  INTEGER(0..128)
	MAX-ACCESS  read-only
	STATUS current
	DESCRIPTION
        "
        Index definition for the pm1008dcpCtrlfecDisable 
        table
        "
	::= { pm1008dcpCtrlfecDisableEntry 1 }


pm1008dcpCtrlfecDisablePortn OBJECT-TYPE
	SYNTAX  EkiState
	MAX-ACCESS read-write
	STATUS current
	DESCRIPTION
        "
        Forward Error Correction Inhibition 
        :This OID, when set, inhibits the 
        Forward Error Correction feature 
        on the line input  <Help>  This 
        control enables/disables the Forward 
        Error Correction on the line interface
        "
	::= { pm1008dcpCtrlfecDisableEntry 2 }


--- *********************************************************
---     TABLE for the pm1008dcpCtrllineOosMode articles
--- *********************************************************

pm1008dcpCtrllineOosModeTable OBJECT-TYPE
	SYNTAX  SEQUENCE OF Pm1008dcpCtrllineOosModeEntry
	MAX-ACCESS not-accessible
	STATUS current
	DESCRIPTION
        "
        List of pm1008dcpCtrllineOosMode 
        Article
        "
	::= { pm1008dcpCtrlLine 74 }


pm1008dcpCtrllineOosModeEntry OBJECT-TYPE
	SYNTAX Pm1008dcpCtrllineOosModeEntry
	MAX-ACCESS not-accessible
	STATUS current
	DESCRIPTION
        "
        Row definition for the pm1008dcpCtrllineOosMode 
        table
        "
	INDEX   { pm1008dcpCtrllineOosModeIndex }
	::= { pm1008dcpCtrllineOosModeTable 1 }


Pm1008dcpCtrllineOosModeEntry ::=
	SEQUENCE {
	pm1008dcpCtrllineOosModeIndex
		INTEGER,
	pm1008dcpCtrllineOosModePortn
		EkiState
	}


pm1008dcpCtrllineOosModeIndex OBJECT-TYPE
	SYNTAX  INTEGER(0..128)
	MAX-ACCESS  read-only
	STATUS current
	DESCRIPTION
        "
        Index definition for the pm1008dcpCtrllineOosMode 
        table
        "
	::= { pm1008dcpCtrllineOosModeEntry 1 }


pm1008dcpCtrllineOosModePortn OBJECT-TYPE
	SYNTAX  EkiState
	MAX-ACCESS read-write
	STATUS current
	DESCRIPTION
        "
        Line Port Out Of Service :This 
        OID sets the line port Out Of Service 
         <Help>  This control defines the 
        service state of the line port
        "
	::= { pm1008dcpCtrllineOosModeEntry 2 }


--- *********************************************************
---     TABLE for the pm1008dcpCtrladddropTsClientARxProtect articles
--- *********************************************************

pm1008dcpCtrladddropTsClientARxProtectTable OBJECT-TYPE
	SYNTAX  SEQUENCE OF Pm1008dcpCtrladddropTsClientARxProtectEntry
	MAX-ACCESS not-accessible
	STATUS current
	DESCRIPTION
        "
        List of pm1008dcpCtrladddropTsClientARxProtect 
        Article
        "
	::= { pm1008dcpCtrlClient 128 }


pm1008dcpCtrladddropTsClientARxProtectEntry OBJECT-TYPE
	SYNTAX Pm1008dcpCtrladddropTsClientARxProtectEntry
	MAX-ACCESS not-accessible
	STATUS current
	DESCRIPTION
        "
        Row definition for the pm1008dcpCtrladddropTsClientARxProtect 
        table
        "
	INDEX   { pm1008dcpCtrladddropTsClientARxProtectIndex }
	::= { pm1008dcpCtrladddropTsClientARxProtectTable 1 }


Pm1008dcpCtrladddropTsClientARxProtectEntry ::=
	SEQUENCE {
	pm1008dcpCtrladddropTsClientARxProtectIndex
		INTEGER,
	pm1008dcpCtrladddropTsClientARxProtectPortn
		Pm1008dcpProtectionTimeSlot
	}


pm1008dcpCtrladddropTsClientARxProtectIndex OBJECT-TYPE
	SYNTAX  INTEGER(0..128)
	MAX-ACCESS  read-only
	STATUS current
	DESCRIPTION
        "
        Index definition for the pm1008dcpCtrladddropTsClientARxProtect 
        table
        "
	::= { pm1008dcpCtrladddropTsClientARxProtectEntry 1 }


pm1008dcpCtrladddropTsClientARxProtectPortn OBJECT-TYPE
	SYNTAX  Pm1008dcpProtectionTimeSlot
	MAX-ACCESS read-write
	STATUS current
	DESCRIPTION
        "
        Client A Switch Mode :This bit 
        selects the manual (1) or automatic 
        (0) switch method  <Help>  This 
        control defines the protection
         switch mode on the client interface
        "
	::= { pm1008dcpCtrladddropTsClientARxProtectEntry 2 }


--- *********************************************************
---     TABLE for the pm1008dcpCtrladddropTsPairMode articles
--- *********************************************************

pm1008dcpCtrladddropTsPairModeTable OBJECT-TYPE
	SYNTAX  SEQUENCE OF Pm1008dcpCtrladddropTsPairModeEntry
	MAX-ACCESS not-accessible
	STATUS current
	DESCRIPTION
        "
        List of pm1008dcpCtrladddropTsPairMode 
        Article
        "
	::= { pm1008dcpCtrlClient 136 }


pm1008dcpCtrladddropTsPairModeEntry OBJECT-TYPE
	SYNTAX Pm1008dcpCtrladddropTsPairModeEntry
	MAX-ACCESS not-accessible
	STATUS current
	DESCRIPTION
        "
        Row definition for the pm1008dcpCtrladddropTsPairMode 
        table
        "
	INDEX   { pm1008dcpCtrladddropTsPairModeIndex }
	::= { pm1008dcpCtrladddropTsPairModeTable 1 }


Pm1008dcpCtrladddropTsPairModeEntry ::=
	SEQUENCE {
	pm1008dcpCtrladddropTsPairModeIndex
		INTEGER,
	pm1008dcpCtrladddropTsPairModePortn
		Pm1008dcpModeTimeSlot
	}


pm1008dcpCtrladddropTsPairModeIndex OBJECT-TYPE
	SYNTAX  INTEGER(0..128)
	MAX-ACCESS  read-only
	STATUS current
	DESCRIPTION
        "
        Index definition for the pm1008dcpCtrladddropTsPairMode 
        table
        "
	::= { pm1008dcpCtrladddropTsPairModeEntry 1 }


pm1008dcpCtrladddropTsPairModePortn OBJECT-TYPE
	SYNTAX  Pm1008dcpModeTimeSlot
	MAX-ACCESS read-write
	STATUS current
	DESCRIPTION
        "
        TS Group Mode :This OID selects 
        the mode on the group of clients 
         <Help>   This control defines
         the mode (Add/Drop or Split&Select) 
        of two consecutive Client (1/2
         , 3/4 , 5/6 , 7/8)
        "
	::= { pm1008dcpCtrladddropTsPairModeEntry 2 }


--- *****************************************************
---     LEAF for the ledTest article
--- *****************************************************
pm1008dcpCtrlledTest OBJECT IDENTIFIER ::= { pm1008dcpCtrlOther 192 }




pm1008dcpCtrlLedOff OBJECT-TYPE
	  SYNTAX EkiOnOff
	  MAX-ACCESS read-write
	  STATUS current
	  DESCRIPTION
        "
        Leds Off :This OID switches off 
        all the Leds as a test feature. 
         <Help>  This control initiates 
        a test leds turning all the LEDs 
        to OFF
        "
	  ::= { pm1008dcpCtrlledTest 3 }



pm1008dcpCtrlRedLed OBJECT-TYPE
	  SYNTAX EkiOnOff
	  MAX-ACCESS read-write
	  STATUS current
	  DESCRIPTION
        "
        Red Leds Test :This OID switches 
        on all the red Leds as a test feature. 
         <Help>  This control initiates 
        a test leds turning all the LEDs 
        to red
        "
	  ::= { pm1008dcpCtrlledTest 2 }



pm1008dcpCtrlGreenLed OBJECT-TYPE
	  SYNTAX EkiOnOff
	  MAX-ACCESS read-write
	  STATUS current
	  DESCRIPTION
        "
        Green Leds Test :This OID switches 
        on all the green Leds as a test 
        feature.  <Help>  This control
         initiates a test leds turning
         all the LEDs to green
        "
	  ::= { pm1008dcpCtrlledTest 1 }



--- *****************************************************
---     LEAF for the moduleOosMode article
--- *****************************************************
pm1008dcpCtrlmoduleOosMode OBJECT IDENTIFIER ::= { pm1008dcpCtrlOther 193 }




pm1008dcpCtrlModuleOosMode OBJECT-TYPE
	  SYNTAX EkiOnOff
	  MAX-ACCESS read-write
	  STATUS current
	  DESCRIPTION
        "
        PM Out Of Service :This OID sets 
        the PM Out Of Service  <Help> 
         This control defines the service 
        state of the complete module
        "
	  ::= { pm1008dcpCtrlmoduleOosMode 1 }



--- *****************************************************
---     LEAF for the moduleDccMgnt article
--- *****************************************************

pm1008dcpCtrlmoduleDccMgnt OBJECT-TYPE
	  SYNTAX Pm1008dcpDccMode
	  MAX-ACCESS read-write
	  STATUS current
	  DESCRIPTION
        "
        DCC Mode :This OID defines the 
        DCC mode of the PM (No DCC, Master, 
        Slave Line 1&2, Terminal Line 1, 
        Terminal Line 2, Terminal Line
         1&2)   <Help>  This control defines 
        the DCC mode of the PM (No DCC, 
        Master, Slave Line 1&2, Terminal 
        Line 1, Terminal Line 2 or Terminal 
        Line 1&2)

        "
	  ::= { pm1008dcpCtrlOther 196 }



--- *****************************************************
---     LEAF for the maintenanceMode article
--- *****************************************************
pm1008dcpCtrlmaintenanceMode OBJECT IDENTIFIER ::= { pm1008dcpCtrlOther 197 }




pm1008dcpCtrlMaintenanceMode OBJECT-TYPE
	  SYNTAX EkiOnOff
	  MAX-ACCESS read-write
	  STATUS current
	  DESCRIPTION
        "
        Module Maintenance Mode :This
         OID enables the maintenance mode 
        on the PM.  <Help>  This control 
        enables the maintenance mode on 
        the PM.
        "
	  ::= { pm1008dcpCtrlmaintenanceMode 1 }



--- *********************************************************
---     TABLE for the pm1008dcpCtrlxfpOnoff articles
--- *********************************************************

pm1008dcpCtrlxfpOnoffTable OBJECT-TYPE
	SYNTAX  SEQUENCE OF Pm1008dcpCtrlxfpOnoffEntry
	MAX-ACCESS not-accessible
	STATUS current
	DESCRIPTION
        "
        List of pm1008dcpCtrlxfpOnoff
         Article
        "
	::= { pm1008dcpCtrlLine 208 }


pm1008dcpCtrlxfpOnoffEntry OBJECT-TYPE
	SYNTAX Pm1008dcpCtrlxfpOnoffEntry
	MAX-ACCESS not-accessible
	STATUS current
	DESCRIPTION
        "
        Row definition for the pm1008dcpCtrlxfpOnoff 
        table
        "
	INDEX   { pm1008dcpCtrlxfpOnoffIndex }
	::= { pm1008dcpCtrlxfpOnoffTable 1 }


Pm1008dcpCtrlxfpOnoffEntry ::=
	SEQUENCE {
	pm1008dcpCtrlxfpOnoffIndex
		INTEGER,
	pm1008dcpCtrlxfpOnoffPortn
		EkiState
	}


pm1008dcpCtrlxfpOnoffIndex OBJECT-TYPE
	SYNTAX  INTEGER(0..128)
	MAX-ACCESS  read-only
	STATUS current
	DESCRIPTION
        "
        Index definition for the pm1008dcpCtrlxfpOnoff 
        table
        "
	::= { pm1008dcpCtrlxfpOnoffEntry 1 }


pm1008dcpCtrlxfpOnoffPortn OBJECT-TYPE
	SYNTAX  EkiState
	MAX-ACCESS read-write
	STATUS current
	DESCRIPTION
        "
        Line Optical Laser Shutdown :This 
        OID switches off the XFP or the 
        OTX  <Help>  This control defines 
        the laser state of the line transceiver
        "
	::= { pm1008dcpCtrlxfpOnoffEntry 2 }


--- *********************************************************
---     TABLE for the pm1008dcpCtrlxfpLineLoop articles
--- *********************************************************

pm1008dcpCtrlxfpLineLoopTable OBJECT-TYPE
	SYNTAX  SEQUENCE OF Pm1008dcpCtrlxfpLineLoopEntry
	MAX-ACCESS not-accessible
	STATUS current
	DESCRIPTION
        "
        List of pm1008dcpCtrlxfpLineLoop 
        Article
        "
	::= { pm1008dcpCtrlLine 209 }


pm1008dcpCtrlxfpLineLoopEntry OBJECT-TYPE
	SYNTAX Pm1008dcpCtrlxfpLineLoopEntry
	MAX-ACCESS not-accessible
	STATUS current
	DESCRIPTION
        "
        Row definition for the pm1008dcpCtrlxfpLineLoop 
        table
        "
	INDEX   { pm1008dcpCtrlxfpLineLoopIndex }
	::= { pm1008dcpCtrlxfpLineLoopTable 1 }


Pm1008dcpCtrlxfpLineLoopEntry ::=
	SEQUENCE {
	pm1008dcpCtrlxfpLineLoopIndex
		INTEGER,
	pm1008dcpCtrlxfpLineLoopPortn
		EkiState
	}


pm1008dcpCtrlxfpLineLoopIndex OBJECT-TYPE
	SYNTAX  INTEGER(0..128)
	MAX-ACCESS  read-only
	STATUS current
	DESCRIPTION
        "
        Index definition for the pm1008dcpCtrlxfpLineLoop 
        table
        "
	::= { pm1008dcpCtrlxfpLineLoopEntry 1 }


pm1008dcpCtrlxfpLineLoopPortn OBJECT-TYPE
	SYNTAX  EkiState
	MAX-ACCESS read-write
	STATUS current
	DESCRIPTION
        "
        Line XFP/OTX Loop :This OID operates 
        a line loopback on the XFP or the 
        OTX  <Help>  This control defines 
        the line loop back of the line
         transceiver
        "
	::= { pm1008dcpCtrlxfpLineLoopEntry 2 }


--- *********************************************************
---     TABLE for the pm1008dcpCtrlxfpXfiLoop articles
--- *********************************************************

pm1008dcpCtrlxfpXfiLoopTable OBJECT-TYPE
	SYNTAX  SEQUENCE OF Pm1008dcpCtrlxfpXfiLoopEntry
	MAX-ACCESS not-accessible
	STATUS current
	DESCRIPTION
        "
        List of pm1008dcpCtrlxfpXfiLoop 
        Article
        "
	::= { pm1008dcpCtrlLine 210 }


pm1008dcpCtrlxfpXfiLoopEntry OBJECT-TYPE
	SYNTAX Pm1008dcpCtrlxfpXfiLoopEntry
	MAX-ACCESS not-accessible
	STATUS current
	DESCRIPTION
        "
        Row definition for the pm1008dcpCtrlxfpXfiLoop 
        table
        "
	INDEX   { pm1008dcpCtrlxfpXfiLoopIndex }
	::= { pm1008dcpCtrlxfpXfiLoopTable 1 }


Pm1008dcpCtrlxfpXfiLoopEntry ::=
	SEQUENCE {
	pm1008dcpCtrlxfpXfiLoopIndex
		INTEGER,
	pm1008dcpCtrlxfpXfiLoopPortn
		EkiState
	}


pm1008dcpCtrlxfpXfiLoopIndex OBJECT-TYPE
	SYNTAX  INTEGER(0..128)
	MAX-ACCESS  read-only
	STATUS current
	DESCRIPTION
        "
        Index definition for the pm1008dcpCtrlxfpXfiLoop 
        table
        "
	::= { pm1008dcpCtrlxfpXfiLoopEntry 1 }


pm1008dcpCtrlxfpXfiLoopPortn OBJECT-TYPE
	SYNTAX  EkiState
	MAX-ACCESS read-write
	STATUS current
	DESCRIPTION
        "
        Line XFP/OTX XFI Loop :This OID 
        operates a XFI loopback on the
         XFP or the OTX   <Help>  This
         control defines the XFI loop back 
        of the line transceiver
        "
	::= { pm1008dcpCtrlxfpXfiLoopEntry 2 }


--- *********************************************************
---     TABLE for the pm1008dcpCtrllineTunableChannel articles
--- *********************************************************

pm1008dcpCtrllineTunableChannelTable OBJECT-TYPE
	SYNTAX  SEQUENCE OF Pm1008dcpCtrllineTunableChannelEntry
	MAX-ACCESS not-accessible
	STATUS current
	DESCRIPTION
        "
        List of pm1008dcpCtrllineTunableChannel 
        Article
        "
	::= { pm1008dcpCtrlLine 212 }


pm1008dcpCtrllineTunableChannelEntry OBJECT-TYPE
	SYNTAX Pm1008dcpCtrllineTunableChannelEntry
	MAX-ACCESS not-accessible
	STATUS current
	DESCRIPTION
        "
        Row definition for the pm1008dcpCtrllineTunableChannel 
        table
        "
	INDEX   { pm1008dcpCtrllineTunableChannelIndex }
	::= { pm1008dcpCtrllineTunableChannelTable 1 }


Pm1008dcpCtrllineTunableChannelEntry ::=
	SEQUENCE {
	pm1008dcpCtrllineTunableChannelIndex
		INTEGER,
	pm1008dcpCtrllineTunableChannelPortn
		Pm1008dcpOtxChannel
	}


pm1008dcpCtrllineTunableChannelIndex OBJECT-TYPE
	SYNTAX  INTEGER(0..128)
	MAX-ACCESS  read-only
	STATUS current
	DESCRIPTION
        "
        Index definition for the pm1008dcpCtrllineTunableChannel 
        table
        "
	::= { pm1008dcpCtrllineTunableChannelEntry 1 }


pm1008dcpCtrllineTunableChannelPortn OBJECT-TYPE
	SYNTAX  Pm1008dcpOtxChannel
	MAX-ACCESS read-write
	STATUS current
	DESCRIPTION
        "
        ITU Channel :This OID selects
         the ITU channel of the Line OTX 
        TLH Laser  <Help>   This control 
        defines the ITU channel of the
         Line OTX TLH Laser
        "
	::= { pm1008dcpCtrllineTunableChannelEntry 2 }


--- *********************************************************
---     TABLE for the pm1008dcpCtrllinePhotodiodeMode articles
--- *********************************************************

pm1008dcpCtrllinePhotodiodeModeTable OBJECT-TYPE
	SYNTAX  SEQUENCE OF Pm1008dcpCtrllinePhotodiodeModeEntry
	MAX-ACCESS not-accessible
	STATUS current
	DESCRIPTION
        "
        List of pm1008dcpCtrllinePhotodiodeMode 
        Article
        "
	::= { pm1008dcpCtrlLine 213 }


pm1008dcpCtrllinePhotodiodeModeEntry OBJECT-TYPE
	SYNTAX Pm1008dcpCtrllinePhotodiodeModeEntry
	MAX-ACCESS not-accessible
	STATUS current
	DESCRIPTION
        "
        Row definition for the pm1008dcpCtrllinePhotodiodeMode 
        table
        "
	INDEX   { pm1008dcpCtrllinePhotodiodeModeIndex }
	::= { pm1008dcpCtrllinePhotodiodeModeTable 1 }


Pm1008dcpCtrllinePhotodiodeModeEntry ::=
	SEQUENCE {
	pm1008dcpCtrllinePhotodiodeModeIndex
		INTEGER,
	pm1008dcpCtrllinePhotodiodeModePortn
		Pm1008dcpOtxMode
	}


pm1008dcpCtrllinePhotodiodeModeIndex OBJECT-TYPE
	SYNTAX  INTEGER(0..128)
	MAX-ACCESS  read-only
	STATUS current
	DESCRIPTION
        "
        Index definition for the pm1008dcpCtrllinePhotodiodeMode 
        table
        "
	::= { pm1008dcpCtrllinePhotodiodeModeEntry 1 }


pm1008dcpCtrllinePhotodiodeModePortn OBJECT-TYPE
	SYNTAX  Pm1008dcpOtxMode
	MAX-ACCESS read-write
	STATUS current
	DESCRIPTION
        "
        OTX TLH Rx Sens. Mode :This OID 
        defines the Rx sensiblity mode
         of the Line OTX TLH  <Help>  
         This control defines the receiver 
        sensibility mode of the Line OTX 
        TLH Laser (OTX60, OTX80 or Custom)
        "
	::= { pm1008dcpCtrllinePhotodiodeModeEntry 2 }


--- *********************************************************
---     TABLE for the pm1008dcpCtrllinePhotodiodeValue articles
--- *********************************************************

pm1008dcpCtrllinePhotodiodeValueTable OBJECT-TYPE
	SYNTAX  SEQUENCE OF Pm1008dcpCtrllinePhotodiodeValueEntry
	MAX-ACCESS not-accessible
	STATUS current
	DESCRIPTION
        "
        List of pm1008dcpCtrllinePhotodiodeValue 
        Article
        "
	::= { pm1008dcpCtrlLine 214 }


pm1008dcpCtrllinePhotodiodeValueEntry OBJECT-TYPE
	SYNTAX Pm1008dcpCtrllinePhotodiodeValueEntry
	MAX-ACCESS not-accessible
	STATUS current
	DESCRIPTION
        "
        Row definition for the pm1008dcpCtrllinePhotodiodeValue 
        table
        "
	INDEX   { pm1008dcpCtrllinePhotodiodeValueIndex }
	::= { pm1008dcpCtrllinePhotodiodeValueTable 1 }


Pm1008dcpCtrllinePhotodiodeValueEntry ::=
	SEQUENCE {
	pm1008dcpCtrllinePhotodiodeValueIndex
		INTEGER,
	pm1008dcpCtrllinePhotodiodeValuePortn
		Pm1008dcpAdjustValue
	}


pm1008dcpCtrllinePhotodiodeValueIndex OBJECT-TYPE
	SYNTAX  INTEGER(0..128)
	MAX-ACCESS  read-only
	STATUS current
	DESCRIPTION
        "
        Index definition for the pm1008dcpCtrllinePhotodiodeValue 
        table
        "
	::= { pm1008dcpCtrllinePhotodiodeValueEntry 1 }


pm1008dcpCtrllinePhotodiodeValuePortn OBJECT-TYPE
	SYNTAX  Pm1008dcpAdjustValue
	MAX-ACCESS read-write
	STATUS current
	DESCRIPTION
        "
        OTX TLH Rx Sensibility :This OID 
        sets the Rx sensibility of the
         Line OTX TLH (custom mode only) 
         <Help>   This control defines
         the receiver sensibility value 
        (only in Custom mode) of the Line 
        OTX TLH Laser
        "
	::= { pm1008dcpCtrllinePhotodiodeValueEntry 2 }


--- *********************************************************
---     TABLE for the pm1008dcpCtrllinePowerLaser articles
--- *********************************************************

pm1008dcpCtrllinePowerLaserTable OBJECT-TYPE
	SYNTAX  SEQUENCE OF Pm1008dcpCtrllinePowerLaserEntry
	MAX-ACCESS not-accessible
	STATUS current
	DESCRIPTION
        "
        List of pm1008dcpCtrllinePowerLaser 
        Article
        "
	::= { pm1008dcpCtrlLine 215 }


pm1008dcpCtrllinePowerLaserEntry OBJECT-TYPE
	SYNTAX Pm1008dcpCtrllinePowerLaserEntry
	MAX-ACCESS not-accessible
	STATUS current
	DESCRIPTION
        "
        Row definition for the pm1008dcpCtrllinePowerLaser 
        table
        "
	INDEX   { pm1008dcpCtrllinePowerLaserIndex }
	::= { pm1008dcpCtrllinePowerLaserTable 1 }


Pm1008dcpCtrllinePowerLaserEntry ::=
	SEQUENCE {
	pm1008dcpCtrllinePowerLaserIndex
		INTEGER,
	pm1008dcpCtrllinePowerLaserPortn
		INTEGER 
	}


pm1008dcpCtrllinePowerLaserIndex OBJECT-TYPE
	SYNTAX  INTEGER(0..128)
	MAX-ACCESS  read-only
	STATUS current
	DESCRIPTION
        "
        Index definition for the pm1008dcpCtrllinePowerLaser 
        table
        "
	::= { pm1008dcpCtrllinePowerLaserEntry 1 }


pm1008dcpCtrllinePowerLaserPortn OBJECT-TYPE
	SYNTAX  INTEGER (0..255)
	MAX-ACCESS read-write
	STATUS current
	DESCRIPTION
        "
        Line Laser Output Power [3-5]
         :This OID sets the output power 
        value on the laser of the Line
         OTX TLH (AV=Power*10+158)  (Unit 
        = dBm)  <Help>   This control defines 
        the start-up output power of the 
        Line OTX TLH
        "
	::= { pm1008dcpCtrllinePowerLaserEntry 2 }


--- *********************************************************
---     TABLE for the pm1008dcpCtrlotxVlhReset articles
--- *********************************************************

pm1008dcpCtrlotxVlhResetTable OBJECT-TYPE
	SYNTAX  SEQUENCE OF Pm1008dcpCtrlotxVlhResetEntry
	MAX-ACCESS not-accessible
	STATUS current
	DESCRIPTION
        "
        List of pm1008dcpCtrlotxVlhReset 
        Article
        "
	::= { pm1008dcpCtrlLine 216 }


pm1008dcpCtrlotxVlhResetEntry OBJECT-TYPE
	SYNTAX Pm1008dcpCtrlotxVlhResetEntry
	MAX-ACCESS not-accessible
	STATUS current
	DESCRIPTION
        "
        Row definition for the pm1008dcpCtrlotxVlhReset 
        table
        "
	INDEX   { pm1008dcpCtrlotxVlhResetIndex }
	::= { pm1008dcpCtrlotxVlhResetTable 1 }


Pm1008dcpCtrlotxVlhResetEntry ::=
	SEQUENCE {
	pm1008dcpCtrlotxVlhResetIndex
		INTEGER,
	pm1008dcpCtrlOtxVlhResetPortn
		EkiOnOff
	}


pm1008dcpCtrlotxVlhResetIndex OBJECT-TYPE
	SYNTAX  INTEGER(0..128)
	MAX-ACCESS  read-only
	STATUS current
	DESCRIPTION
        "
        Index definition for the pm1008dcpCtrlotxVlhReset 
        table
        "
	::= { pm1008dcpCtrlotxVlhResetEntry 1 }


pm1008dcpCtrlOtxVlhResetPortn OBJECT-TYPE
	SYNTAX  EkiOnOff
	MAX-ACCESS read-write
	STATUS current
	DESCRIPTION
        "
        OTX-VLH Reset :This OID resets 
        the OTX-VLH module  <Help>  This 
        control resets the OTX-VLH and
         its parameters  
        "
	::= { pm1008dcpCtrlotxVlhResetEntry 2 }


--- *********************************************************
---     TABLE for the pm1008dcpCtrllineAccessLoop articles
--- *********************************************************

pm1008dcpCtrllineAccessLoopTable OBJECT-TYPE
	SYNTAX  SEQUENCE OF Pm1008dcpCtrllineAccessLoopEntry
	MAX-ACCESS not-accessible
	STATUS current
	DESCRIPTION
        "
        List of pm1008dcpCtrllineAccessLoop 
        Article
        "
	::= { pm1008dcpCtrlLine 217 }


pm1008dcpCtrllineAccessLoopEntry OBJECT-TYPE
	SYNTAX Pm1008dcpCtrllineAccessLoopEntry
	MAX-ACCESS not-accessible
	STATUS current
	DESCRIPTION
        "
        Row definition for the pm1008dcpCtrllineAccessLoop 
        table
        "
	INDEX   { pm1008dcpCtrllineAccessLoopIndex }
	::= { pm1008dcpCtrllineAccessLoopTable 1 }


Pm1008dcpCtrllineAccessLoopEntry ::=
	SEQUENCE {
	pm1008dcpCtrllineAccessLoopIndex
		INTEGER,
	pm1008dcpCtrllineAccessLoopPortn
		EkiState
	}


pm1008dcpCtrllineAccessLoopIndex OBJECT-TYPE
	SYNTAX  INTEGER(0..128)
	MAX-ACCESS  read-only
	STATUS current
	DESCRIPTION
        "
        Index definition for the pm1008dcpCtrllineAccessLoop 
        table
        "
	::= { pm1008dcpCtrllineAccessLoopEntry 1 }


pm1008dcpCtrllineAccessLoopPortn OBJECT-TYPE
	SYNTAX  EkiState
	MAX-ACCESS read-write
	STATUS current
	DESCRIPTION
        "
        Line Facility Loopback :This OID 
        operates a Line Facility Loopback, 
        looping line input signal on the 
        line output port. The loop is located 
        on the line transceiver. If the 
        Line signal carries DCC, the management 
        network is impacted  <Help> This 
        maintenance parameter operates
         a Line Facility Loopback, looping 
        line input signal on the line output 
        port. The loop is located on the 
        line transceiver. If the Line signal 
        carries DCC, the management network 
        is impacted
        "
	::= { pm1008dcpCtrllineAccessLoopEntry 2 }


--- *********************************************************
---     TABLE for the pm1008dcpCtrllineLoopTransceiver articles
--- *********************************************************

pm1008dcpCtrllineLoopTransceiverTable OBJECT-TYPE
	SYNTAX  SEQUENCE OF Pm1008dcpCtrllineLoopTransceiverEntry
	MAX-ACCESS not-accessible
	STATUS current
	DESCRIPTION
        "
        List of pm1008dcpCtrllineLoopTransceiver 
        Article
        "
	::= { pm1008dcpCtrlLine 218 }


pm1008dcpCtrllineLoopTransceiverEntry OBJECT-TYPE
	SYNTAX Pm1008dcpCtrllineLoopTransceiverEntry
	MAX-ACCESS not-accessible
	STATUS current
	DESCRIPTION
        "
        Row definition for the pm1008dcpCtrllineLoopTransceiver 
        table
        "
	INDEX   { pm1008dcpCtrllineLoopTransceiverIndex }
	::= { pm1008dcpCtrllineLoopTransceiverTable 1 }


Pm1008dcpCtrllineLoopTransceiverEntry ::=
	SEQUENCE {
	pm1008dcpCtrllineLoopTransceiverIndex
		INTEGER,
	pm1008dcpCtrllineLoopTransceiverPortn
		EkiState
	}


pm1008dcpCtrllineLoopTransceiverIndex OBJECT-TYPE
	SYNTAX  INTEGER(0..128)
	MAX-ACCESS  read-only
	STATUS current
	DESCRIPTION
        "
        Index definition for the pm1008dcpCtrllineLoopTransceiver 
        table
        "
	::= { pm1008dcpCtrllineLoopTransceiverEntry 1 }


pm1008dcpCtrllineLoopTransceiverPortn OBJECT-TYPE
	SYNTAX  EkiState
	MAX-ACCESS read-write
	STATUS current
	DESCRIPTION
        "
        Line Terminal Loopback :This OID 
        operates a Line Terminal Loopback, 
        looping line input signal on the 
        line output port. The loop is located 
        on all client transceivers  <Help> 
        This maintenance parameter operates 
        a Line Terminal Loopback, looping 
        line input signal on the line output 
        port. The loop is located on all 
        client transceivers.
        "
	::= { pm1008dcpCtrllineLoopTransceiverEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm1008dcpCntupRaRemCnt articles
--- *********************************************************

pm1008dcpCntupRaRemCntTable OBJECT-TYPE
	SYNTAX  SEQUENCE OF Pm1008dcpCntupRaRemCntEntry
	MAX-ACCESS not-accessible
	STATUS current
	DESCRIPTION
        "
        List of pm1008dcpCntupRaRemCnt 
        Article
        "
	::= { pm1008dcpCntClient 16 }


pm1008dcpCntupRaRemCntEntry OBJECT-TYPE
	SYNTAX Pm1008dcpCntupRaRemCntEntry
	MAX-ACCESS not-accessible
	STATUS current
	DESCRIPTION
        "
        Row definition for the pm1008dcpCntupRaRemCnt 
        table
        "
	INDEX   { pm1008dcpCntupRaRemCntIndex }
	::= { pm1008dcpCntupRaRemCntTable 1 }


Pm1008dcpCntupRaRemCntEntry ::=
	SEQUENCE {
	pm1008dcpCntupRaRemCntIndex
		INTEGER,
	pm1008dcpCntupRaRemCntValuePortn
		Counter32,
	pm1008dcpCntupRaRemCntErrorPortn
		EkiOnOff,
	pm1008dcpCntupRaRemCntOverloadPortn
		EkiOnOff
	}


pm1008dcpCntupRaRemCntIndex OBJECT-TYPE
	SYNTAX  INTEGER(0..128)
	MAX-ACCESS  read-only
	STATUS current
	DESCRIPTION
        "
        Index definition for the pm1008dcpCntupRaRemCnt 
        table
        "
	::= { pm1008dcpCntupRaRemCntEntry 1 }


pm1008dcpCntupRaRemCntValuePortn OBJECT-TYPE
	SYNTAX  Counter32
	MAX-ACCESS read-only
	STATUS current
	DESCRIPTION
        "
        Client Rate Adapt. Words Removal 
        :This counter is incremented each 
        time a rate adaptation 10B word 
        is removed from the Client input 
        stream
        "
	::= { pm1008dcpCntupRaRemCntEntry 2 }


pm1008dcpCntupRaRemCntErrorPortn OBJECT-TYPE
	SYNTAX  EkiOnOff
	MAX-ACCESS read-only
	STATUS current
	DESCRIPTION
        "
        Client Counter Error :This OID 
        when set indicates the rate adaptation 
        removal counter value is invalid 
        on Port
        "
	::= { pm1008dcpCntupRaRemCntEntry 3 }


pm1008dcpCntupRaRemCntOverloadPortn OBJECT-TYPE
	SYNTAX  EkiOnOff
	MAX-ACCESS read-only
	STATUS current
	DESCRIPTION
        "
        Client Counter Overload :This
         OID when set indicates a rate
         adaptation removal counter overload 
        on Port
        "
	::= { pm1008dcpCntupRaRemCntEntry 4 }


--- *********************************************************
---     TABLE for the pm1008dcpCntupRaInsCnt articles
--- *********************************************************

pm1008dcpCntupRaInsCntTable OBJECT-TYPE
	SYNTAX  SEQUENCE OF Pm1008dcpCntupRaInsCntEntry
	MAX-ACCESS not-accessible
	STATUS current
	DESCRIPTION
        "
        List of pm1008dcpCntupRaInsCnt 
        Article
        "
	::= { pm1008dcpCntClient 24 }


pm1008dcpCntupRaInsCntEntry OBJECT-TYPE
	SYNTAX Pm1008dcpCntupRaInsCntEntry
	MAX-ACCESS not-accessible
	STATUS current
	DESCRIPTION
        "
        Row definition for the pm1008dcpCntupRaInsCnt 
        table
        "
	INDEX   { pm1008dcpCntupRaInsCntIndex }
	::= { pm1008dcpCntupRaInsCntTable 1 }


Pm1008dcpCntupRaInsCntEntry ::=
	SEQUENCE {
	pm1008dcpCntupRaInsCntIndex
		INTEGER,
	pm1008dcpCntupRaInsCntValuePortn
		Counter32,
	pm1008dcpCntupRaInsCntErrorPortn
		EkiOnOff,
	pm1008dcpCntupRaInsCntOverloadPortn
		EkiOnOff
	}


pm1008dcpCntupRaInsCntIndex OBJECT-TYPE
	SYNTAX  INTEGER(0..128)
	MAX-ACCESS  read-only
	STATUS current
	DESCRIPTION
        "
        Index definition for the pm1008dcpCntupRaInsCnt 
        table
        "
	::= { pm1008dcpCntupRaInsCntEntry 1 }


pm1008dcpCntupRaInsCntValuePortn OBJECT-TYPE
	SYNTAX  Counter32
	MAX-ACCESS read-only
	STATUS current
	DESCRIPTION
        "
        Client Rate Adapt. Words Insertion 
        :This counter is incremented each 
        time a rate adaptation 10B word 
        is inserted in the Client input 
        stream
        "
	::= { pm1008dcpCntupRaInsCntEntry 2 }


pm1008dcpCntupRaInsCntErrorPortn OBJECT-TYPE
	SYNTAX  EkiOnOff
	MAX-ACCESS read-only
	STATUS current
	DESCRIPTION
        "
        Client Counter Error :This OID 
        when set indicates the rate adaptation 
        insertion counter value is invalid 
        on Port
        "
	::= { pm1008dcpCntupRaInsCntEntry 3 }


pm1008dcpCntupRaInsCntOverloadPortn OBJECT-TYPE
	SYNTAX  EkiOnOff
	MAX-ACCESS read-only
	STATUS current
	DESCRIPTION
        "
        Client Counter Overload :This
         OID when set indicates a rate
         adaptation insertion counter overload 
        on Port
        "
	::= { pm1008dcpCntupRaInsCntEntry 4 }


--- *********************************************************
---     TABLE for the pm1008dcpCntupRdErrCnt articles
--- *********************************************************

pm1008dcpCntupRdErrCntTable OBJECT-TYPE
	SYNTAX  SEQUENCE OF Pm1008dcpCntupRdErrCntEntry
	MAX-ACCESS not-accessible
	STATUS current
	DESCRIPTION
        "
        List of pm1008dcpCntupRdErrCnt 
        Article
        "
	::= { pm1008dcpCntClient 32 }


pm1008dcpCntupRdErrCntEntry OBJECT-TYPE
	SYNTAX Pm1008dcpCntupRdErrCntEntry
	MAX-ACCESS not-accessible
	STATUS current
	DESCRIPTION
        "
        Row definition for the pm1008dcpCntupRdErrCnt 
        table
        "
	INDEX   { pm1008dcpCntupRdErrCntIndex }
	::= { pm1008dcpCntupRdErrCntTable 1 }


Pm1008dcpCntupRdErrCntEntry ::=
	SEQUENCE {
	pm1008dcpCntupRdErrCntIndex
		INTEGER,
	pm1008dcpCntupRdErrCntValuePortn
		Counter32,
	pm1008dcpCntupRdErrCntErrorPortn
		EkiOnOff,
	pm1008dcpCntupRdErrCntOverloadPortn
		EkiOnOff
	}


pm1008dcpCntupRdErrCntIndex OBJECT-TYPE
	SYNTAX  INTEGER(0..128)
	MAX-ACCESS  read-only
	STATUS current
	DESCRIPTION
        "
        Index definition for the pm1008dcpCntupRdErrCnt 
        table
        "
	::= { pm1008dcpCntupRdErrCntEntry 1 }


pm1008dcpCntupRdErrCntValuePortn OBJECT-TYPE
	SYNTAX  Counter32
	MAX-ACCESS read-only
	STATUS current
	DESCRIPTION
        "
        Client Input Errors :This counter 
        is increased each time a 10b/8b 
        running disparity error is detected 
        on the Client input stream  <Help> 
         This counter gives the number
         of 10b/8b running disparity errors 
        on the client port
        "
	::= { pm1008dcpCntupRdErrCntEntry 2 }


pm1008dcpCntupRdErrCntErrorPortn OBJECT-TYPE
	SYNTAX  EkiOnOff
	MAX-ACCESS read-only
	STATUS current
	DESCRIPTION
        "
        Client Counter Error :This OID 
        when set indicates the client error 
        counter value is invalid on Port
        "
	::= { pm1008dcpCntupRdErrCntEntry 3 }


pm1008dcpCntupRdErrCntOverloadPortn OBJECT-TYPE
	SYNTAX  EkiOnOff
	MAX-ACCESS read-only
	STATUS current
	DESCRIPTION
        "
        Client Counter Overload :This
         OID when set indicates a client 
        input error counter overload on 
        Port
        "
	::= { pm1008dcpCntupRdErrCntEntry 4 }


--- *********************************************************
---     TABLE for the pm1008dcpCntupTimCnt articles
--- *********************************************************

pm1008dcpCntupTimCntTable OBJECT-TYPE
	SYNTAX  SEQUENCE OF Pm1008dcpCntupTimCntEntry
	MAX-ACCESS not-accessible
	STATUS current
	DESCRIPTION
        "
        List of pm1008dcpCntupTimCnt Article
        "
	::= { pm1008dcpCntClient 40 }


pm1008dcpCntupTimCntEntry OBJECT-TYPE
	SYNTAX Pm1008dcpCntupTimCntEntry
	MAX-ACCESS not-accessible
	STATUS current
	DESCRIPTION
        "
        Row definition for the pm1008dcpCntupTimCnt 
        table
        "
	INDEX   { pm1008dcpCntupTimCntIndex }
	::= { pm1008dcpCntupTimCntTable 1 }


Pm1008dcpCntupTimCntEntry ::=
	SEQUENCE {
	pm1008dcpCntupTimCntIndex
		INTEGER,
	pm1008dcpCntupTimCntValuePortn
		Counter32,
	pm1008dcpCntupTimCntErrorPortn
		EkiOnOff,
	pm1008dcpCntupTimCntOverloadPortn
		EkiOnOff
	}


pm1008dcpCntupTimCntIndex OBJECT-TYPE
	SYNTAX  INTEGER(0..128)
	MAX-ACCESS  read-only
	STATUS current
	DESCRIPTION
        "
        Index definition for the pm1008dcpCntupTimCnt 
        table
        "
	::= { pm1008dcpCntupTimCntEntry 1 }


pm1008dcpCntupTimCntValuePortn OBJECT-TYPE
	SYNTAX  Counter32
	MAX-ACCESS read-only
	STATUS current
	DESCRIPTION
        "
        Client Upstream Timer Counter
         :This is the timing counter dedicated 
        to the upstream access counters. 
        It is incremented every 125 us.
        "
	::= { pm1008dcpCntupTimCntEntry 2 }


pm1008dcpCntupTimCntErrorPortn OBJECT-TYPE
	SYNTAX  EkiOnOff
	MAX-ACCESS read-only
	STATUS current
	DESCRIPTION
        "
        Client Counter Error :This OID 
        when set indicates the upstream 
        timing counter value is invalid 
        on Port
        "
	::= { pm1008dcpCntupTimCntEntry 3 }


pm1008dcpCntupTimCntOverloadPortn OBJECT-TYPE
	SYNTAX  EkiOnOff
	MAX-ACCESS read-only
	STATUS current
	DESCRIPTION
        "
        Client Counter Overload :This
         OID when set indicates a upstream 
        timing counter overload on Port
        "
	::= { pm1008dcpCntupTimCntEntry 4 }


--- *********************************************************
---     TABLE for the pm1008dcpCntupCvErrCnt articles
--- *********************************************************

pm1008dcpCntupCvErrCntTable OBJECT-TYPE
	SYNTAX  SEQUENCE OF Pm1008dcpCntupCvErrCntEntry
	MAX-ACCESS not-accessible
	STATUS current
	DESCRIPTION
        "
        List of pm1008dcpCntupCvErrCnt 
        Article
        "
	::= { pm1008dcpCntClient 48 }


pm1008dcpCntupCvErrCntEntry OBJECT-TYPE
	SYNTAX Pm1008dcpCntupCvErrCntEntry
	MAX-ACCESS not-accessible
	STATUS current
	DESCRIPTION
        "
        Row definition for the pm1008dcpCntupCvErrCnt 
        table
        "
	INDEX   { pm1008dcpCntupCvErrCntIndex }
	::= { pm1008dcpCntupCvErrCntTable 1 }


Pm1008dcpCntupCvErrCntEntry ::=
	SEQUENCE {
	pm1008dcpCntupCvErrCntIndex
		INTEGER,
	pm1008dcpCntupCvErrCntValuePortn
		Counter32,
	pm1008dcpCntupCvErrCntErrorPortn
		EkiOnOff,
	pm1008dcpCntupCvErrCntOverloadPortn
		EkiOnOff
	}


pm1008dcpCntupCvErrCntIndex OBJECT-TYPE
	SYNTAX  INTEGER(0..128)
	MAX-ACCESS  read-only
	STATUS current
	DESCRIPTION
        "
        Index definition for the pm1008dcpCntupCvErrCnt 
        table
        "
	::= { pm1008dcpCntupCvErrCntEntry 1 }


pm1008dcpCntupCvErrCntValuePortn OBJECT-TYPE
	SYNTAX  Counter32
	MAX-ACCESS read-only
	STATUS current
	DESCRIPTION
        "
        Client Coding Violation Counter 
        :This counter is increased each 
        time a 10b/8b coding violation
         is detected on the Client input 
        stream
        "
	::= { pm1008dcpCntupCvErrCntEntry 2 }


pm1008dcpCntupCvErrCntErrorPortn OBJECT-TYPE
	SYNTAX  EkiOnOff
	MAX-ACCESS read-only
	STATUS current
	DESCRIPTION
        "
        Client Counter Error :This OID 
        when set indicates the coding violation 
        counter value is invalid on Port
        "
	::= { pm1008dcpCntupCvErrCntEntry 3 }


pm1008dcpCntupCvErrCntOverloadPortn OBJECT-TYPE
	SYNTAX  EkiOnOff
	MAX-ACCESS read-only
	STATUS current
	DESCRIPTION
        "
        Client Counter Overload :This
         OID when set indicates a coding 
        violation counter overload on Port
        "
	::= { pm1008dcpCntupCvErrCntEntry 4 }


--- *********************************************************
---     TABLE for the pm1008dcpCntdwCbipCnt articles
--- *********************************************************

pm1008dcpCntdwCbipCntTable OBJECT-TYPE
	SYNTAX  SEQUENCE OF Pm1008dcpCntdwCbipCntEntry
	MAX-ACCESS not-accessible
	STATUS current
	DESCRIPTION
        "
        List of pm1008dcpCntdwCbipCnt
         Article
        "
	::= { pm1008dcpCntClient 64 }


pm1008dcpCntdwCbipCntEntry OBJECT-TYPE
	SYNTAX Pm1008dcpCntdwCbipCntEntry
	MAX-ACCESS not-accessible
	STATUS current
	DESCRIPTION
        "
        Row definition for the pm1008dcpCntdwCbipCnt 
        table
        "
	INDEX   { pm1008dcpCntdwCbipCntIndex }
	::= { pm1008dcpCntdwCbipCntTable 1 }


Pm1008dcpCntdwCbipCntEntry ::=
	SEQUENCE {
	pm1008dcpCntdwCbipCntIndex
		INTEGER,
	pm1008dcpCntdwCbipCntValuePortn
		Counter32,
	pm1008dcpCntdwCbipCntErrorPortn
		EkiOnOff,
	pm1008dcpCntdwCbipCntOverloadPortn
		EkiOnOff
	}


pm1008dcpCntdwCbipCntIndex OBJECT-TYPE
	SYNTAX  INTEGER(0..128)
	MAX-ACCESS  read-only
	STATUS current
	DESCRIPTION
        "
        Index definition for the pm1008dcpCntdwCbipCnt 
        table
        "
	::= { pm1008dcpCntdwCbipCntEntry 1 }


pm1008dcpCntdwCbipCntValuePortn OBJECT-TYPE
	SYNTAX  Counter32
	MAX-ACCESS read-only
	STATUS current
	DESCRIPTION
        "
        Client Output Errors :This counter 
        is incremented each time a CBIP 
        parity error is detected on the 
        Client output stream  <Help>  This 
        counter gives the number of CBIP 
        errors on the client port
        "
	::= { pm1008dcpCntdwCbipCntEntry 2 }


pm1008dcpCntdwCbipCntErrorPortn OBJECT-TYPE
	SYNTAX  EkiOnOff
	MAX-ACCESS read-only
	STATUS current
	DESCRIPTION
        "
        Client Counter Error :This OID 
        when set indicates the CBIP error 
        counter value is invalid on Port
        "
	::= { pm1008dcpCntdwCbipCntEntry 3 }


pm1008dcpCntdwCbipCntOverloadPortn OBJECT-TYPE
	SYNTAX  EkiOnOff
	MAX-ACCESS read-only
	STATUS current
	DESCRIPTION
        "
        Client CBIP Counter Overload :This 
        OID when set indicates a CBIP error 
        counter overload on Port
        "
	::= { pm1008dcpCntdwCbipCntEntry 4 }


--- *********************************************************
---     TABLE for the pm1008dcpCntdwTimCnt articles
--- *********************************************************

pm1008dcpCntdwTimCntTable OBJECT-TYPE
	SYNTAX  SEQUENCE OF Pm1008dcpCntdwTimCntEntry
	MAX-ACCESS not-accessible
	STATUS current
	DESCRIPTION
        "
        List of pm1008dcpCntdwTimCnt Article
        "
	::= { pm1008dcpCntClient 72 }


pm1008dcpCntdwTimCntEntry OBJECT-TYPE
	SYNTAX Pm1008dcpCntdwTimCntEntry
	MAX-ACCESS not-accessible
	STATUS current
	DESCRIPTION
        "
        Row definition for the pm1008dcpCntdwTimCnt 
        table
        "
	INDEX   { pm1008dcpCntdwTimCntIndex }
	::= { pm1008dcpCntdwTimCntTable 1 }


Pm1008dcpCntdwTimCntEntry ::=
	SEQUENCE {
	pm1008dcpCntdwTimCntIndex
		INTEGER,
	pm1008dcpCntdwTimCntValuePortn
		Counter32,
	pm1008dcpCntdwTimCntErrorPortn
		EkiOnOff,
	pm1008dcpCntdwTimCntOverloadPortn
		EkiOnOff
	}


pm1008dcpCntdwTimCntIndex OBJECT-TYPE
	SYNTAX  INTEGER(0..128)
	MAX-ACCESS  read-only
	STATUS current
	DESCRIPTION
        "
        Index definition for the pm1008dcpCntdwTimCnt 
        table
        "
	::= { pm1008dcpCntdwTimCntEntry 1 }


pm1008dcpCntdwTimCntValuePortn OBJECT-TYPE
	SYNTAX  Counter32
	MAX-ACCESS read-only
	STATUS current
	DESCRIPTION
        "
        Client Downstream Timer Counter 
        :This is the timing counter dedicated 
        to the downstream access counters. 
        It is incremented every 125 us.
        "
	::= { pm1008dcpCntdwTimCntEntry 2 }


pm1008dcpCntdwTimCntErrorPortn OBJECT-TYPE
	SYNTAX  EkiOnOff
	MAX-ACCESS read-only
	STATUS current
	DESCRIPTION
        "
        Client Counter Error :This OID 
        when set indicates the downstream 
        timer counter value is invalid
         on Port
        "
	::= { pm1008dcpCntdwTimCntEntry 3 }


pm1008dcpCntdwTimCntOverloadPortn OBJECT-TYPE
	SYNTAX  EkiOnOff
	MAX-ACCESS read-only
	STATUS current
	DESCRIPTION
        "
        Client Counter Overload :This
         OID when set indicates a downstream 
        timer counter overload on Port
        "
	::= { pm1008dcpCntdwTimCntEntry 4 }


--- *********************************************************
---     TABLE for the pm1008dcpCntdfrmB1ErrCnt articles
--- *********************************************************

pm1008dcpCntdfrmB1ErrCntTable OBJECT-TYPE
	SYNTAX  SEQUENCE OF Pm1008dcpCntdfrmB1ErrCntEntry
	MAX-ACCESS not-accessible
	STATUS current
	DESCRIPTION
        "
        List of pm1008dcpCntdfrmB1ErrCnt 
        Article
        "
	::= { pm1008dcpCntLine 152 }


pm1008dcpCntdfrmB1ErrCntEntry OBJECT-TYPE
	SYNTAX Pm1008dcpCntdfrmB1ErrCntEntry
	MAX-ACCESS not-accessible
	STATUS current
	DESCRIPTION
        "
        Row definition for the pm1008dcpCntdfrmB1ErrCnt 
        table
        "
	INDEX   { pm1008dcpCntdfrmB1ErrCntIndex }
	::= { pm1008dcpCntdfrmB1ErrCntTable 1 }


Pm1008dcpCntdfrmB1ErrCntEntry ::=
	SEQUENCE {
	pm1008dcpCntdfrmB1ErrCntIndex
		INTEGER,
	pm1008dcpCntdfrmB1ErrCntValuePortn
		Counter32,
	pm1008dcpCntdfrmB1ErrCntErrorPortn
		EkiOnOff,
	pm1008dcpCntdfrmB1ErrCntOverloadPortn
		EkiOnOff
	}


pm1008dcpCntdfrmB1ErrCntIndex OBJECT-TYPE
	SYNTAX  INTEGER(0..128)
	MAX-ACCESS  read-only
	STATUS current
	DESCRIPTION
        "
        Index definition for the pm1008dcpCntdfrmB1ErrCnt 
        table
        "
	::= { pm1008dcpCntdfrmB1ErrCntEntry 1 }


pm1008dcpCntdfrmB1ErrCntValuePortn OBJECT-TYPE
	SYNTAX  Counter32
	MAX-ACCESS read-only
	STATUS current
	DESCRIPTION
        "
        Line Input B1 Errors :This counter 
        is incremented each time a B1 error 
        is detected on the Deframer input 
        stream.  <Help>  This counter gives 
        the number of B1 errors on the
         line port
        "
	::= { pm1008dcpCntdfrmB1ErrCntEntry 2 }


pm1008dcpCntdfrmB1ErrCntErrorPortn OBJECT-TYPE
	SYNTAX  EkiOnOff
	MAX-ACCESS read-only
	STATUS current
	DESCRIPTION
        "
        Line Counter Error :This OID when 
        set indicates the B1 error counter 
        value is invalid on Port
        "
	::= { pm1008dcpCntdfrmB1ErrCntEntry 3 }


pm1008dcpCntdfrmB1ErrCntOverloadPortn OBJECT-TYPE
	SYNTAX  EkiOnOff
	MAX-ACCESS read-only
	STATUS current
	DESCRIPTION
        "
        Line Counter Overload :This OID 
        when set indicates a B1 error counter 
        overload on Port
        "
	::= { pm1008dcpCntdfrmB1ErrCntEntry 4 }


--- *********************************************************
---     TABLE for the pm1008dcpCntdfrmTimCnt articles
--- *********************************************************

pm1008dcpCntdfrmTimCntTable OBJECT-TYPE
	SYNTAX  SEQUENCE OF Pm1008dcpCntdfrmTimCntEntry
	MAX-ACCESS not-accessible
	STATUS current
	DESCRIPTION
        "
        List of pm1008dcpCntdfrmTimCnt 
        Article
        "
	::= { pm1008dcpCntLine 153 }


pm1008dcpCntdfrmTimCntEntry OBJECT-TYPE
	SYNTAX Pm1008dcpCntdfrmTimCntEntry
	MAX-ACCESS not-accessible
	STATUS current
	DESCRIPTION
        "
        Row definition for the pm1008dcpCntdfrmTimCnt 
        table
        "
	INDEX   { pm1008dcpCntdfrmTimCntIndex }
	::= { pm1008dcpCntdfrmTimCntTable 1 }


Pm1008dcpCntdfrmTimCntEntry ::=
	SEQUENCE {
	pm1008dcpCntdfrmTimCntIndex
		INTEGER,
	pm1008dcpCntdfrmTimCntValuePortn
		Counter32,
	pm1008dcpCntdfrmTimCntErrorPortn
		EkiOnOff,
	pm1008dcpCntdfrmTimCntOverloadPortn
		EkiOnOff
	}


pm1008dcpCntdfrmTimCntIndex OBJECT-TYPE
	SYNTAX  INTEGER(0..128)
	MAX-ACCESS  read-only
	STATUS current
	DESCRIPTION
        "
        Index definition for the pm1008dcpCntdfrmTimCnt 
        table
        "
	::= { pm1008dcpCntdfrmTimCntEntry 1 }


pm1008dcpCntdfrmTimCntValuePortn OBJECT-TYPE
	SYNTAX  Counter32
	MAX-ACCESS read-only
	STATUS current
	DESCRIPTION
        "
        Line Timer Counter :This is the 
        timing counter dedicated to the 
        downstream deframer counters. It 
        is incremented every 125 us.
        "
	::= { pm1008dcpCntdfrmTimCntEntry 2 }


pm1008dcpCntdfrmTimCntErrorPortn OBJECT-TYPE
	SYNTAX  EkiOnOff
	MAX-ACCESS read-only
	STATUS current
	DESCRIPTION
        "
        Line Counter Error :This OID when 
        set indicates the deframer timer 
        counter value is invalid on Port
        "
	::= { pm1008dcpCntdfrmTimCntEntry 3 }


pm1008dcpCntdfrmTimCntOverloadPortn OBJECT-TYPE
	SYNTAX  EkiOnOff
	MAX-ACCESS read-only
	STATUS current
	DESCRIPTION
        "
        Line Counter Overload :This OID 
        when set indicates a deframer timer 
        counter overload on Port
        "
	::= { pm1008dcpCntdfrmTimCntEntry 4 }


--- *********************************************************
---     TABLE for the pm1008dcpCntdfrmPrimLineErrCnt articles
--- *********************************************************

pm1008dcpCntdfrmPrimLineErrCntTable OBJECT-TYPE
	SYNTAX  SEQUENCE OF Pm1008dcpCntdfrmPrimLineErrCntEntry
	MAX-ACCESS not-accessible
	STATUS current
	DESCRIPTION
        "
        List of pm1008dcpCntdfrmPrimLineErrCnt 
        Article
        "
	::= { pm1008dcpCntLine 154 }


pm1008dcpCntdfrmPrimLineErrCntEntry OBJECT-TYPE
	SYNTAX Pm1008dcpCntdfrmPrimLineErrCntEntry
	MAX-ACCESS not-accessible
	STATUS current
	DESCRIPTION
        "
        Row definition for the pm1008dcpCntdfrmPrimLineErrCnt 
        table
        "
	INDEX   { pm1008dcpCntdfrmPrimLineErrCntIndex }
	::= { pm1008dcpCntdfrmPrimLineErrCntTable 1 }


Pm1008dcpCntdfrmPrimLineErrCntEntry ::=
	SEQUENCE {
	pm1008dcpCntdfrmPrimLineErrCntIndex
		INTEGER,
	pm1008dcpCntdfrmPrimLineErrCntValuePortn
		Counter32,
	pm1008dcpCntdfrmPrimLineErrCntErrorPortn
		EkiOnOff,
	pm1008dcpCntdfrmPrimLineErrCntOverloadPortn
		EkiOnOff
	}


pm1008dcpCntdfrmPrimLineErrCntIndex OBJECT-TYPE
	SYNTAX  INTEGER(0..128)
	MAX-ACCESS  read-only
	STATUS current
	DESCRIPTION
        "
        Index definition for the pm1008dcpCntdfrmPrimLineErrCnt 
        table
        "
	::= { pm1008dcpCntdfrmPrimLineErrCntEntry 1 }


pm1008dcpCntdfrmPrimLineErrCntValuePortn OBJECT-TYPE
	SYNTAX  Counter32
	MAX-ACCESS read-only
	STATUS current
	DESCRIPTION
        "
        Line Input FEC Corrected Errors 
        :This counter is incremented each 
        time the FEC is correcting an error 
        on the line input stream.  <Help> 
         This counter gives the number
         of errors corrected by the FEC 
        on the line port
        "
	::= { pm1008dcpCntdfrmPrimLineErrCntEntry 2 }


pm1008dcpCntdfrmPrimLineErrCntErrorPortn OBJECT-TYPE
	SYNTAX  EkiOnOff
	MAX-ACCESS read-only
	STATUS current
	DESCRIPTION
        "
        FEC Counter Error :This bit when 
        set indicates the FEC corrected 
        errors counter value is invalid 
        on Line
        "
	::= { pm1008dcpCntdfrmPrimLineErrCntEntry 3 }


pm1008dcpCntdfrmPrimLineErrCntOverloadPortn OBJECT-TYPE
	SYNTAX  EkiOnOff
	MAX-ACCESS read-only
	STATUS current
	DESCRIPTION
        "
        FEC Counter Overload :This bit 
        when set indicates a FEC corrected 
        errors counter overload on Line
        "
	::= { pm1008dcpCntdfrmPrimLineErrCntEntry 4 }


pm1008dcpCntCountersReset  OBJECT-TYPE
	SYNTAX EkiOnOff
	MAX-ACCESS read-write
	STATUS current
	DESCRIPTION
	"Counters Reset:This OID resets and restarts all the counters"
	::= { pm1008dcpcounters  259 }

pm1008dcpCntCountersStop  OBJECT-TYPE
	SYNTAX EkiOnOff
	MAX-ACCESS read-write
	STATUS current
	DESCRIPTION
	"Counters stop:This OID stops all the counters"
	::= { pm1008dcpcounters 260 }






--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pm1008dcpMonupRmonByteCnt articles
--- *********************************************************

pm1008dcpMonupRmonByteCntTable OBJECT-TYPE
	SYNTAX  SEQUENCE OF Pm1008dcpMonupRmonByteCntEntry
	MAX-ACCESS not-accessible
	STATUS current
	DESCRIPTION
        "
        List of pm1008dcpMonupRmonByteCnt 
        Article
        "
	::= { pm1008dcpMonClientRmonCounter 16 }


pm1008dcpMonupRmonByteCntEntry OBJECT-TYPE
	SYNTAX Pm1008dcpMonupRmonByteCntEntry
	MAX-ACCESS not-accessible
	STATUS current
	DESCRIPTION
        "
        Row definition for the pm1008dcpMonupRmonByteCnt 
        table
        "
	INDEX   { pm1008dcpMonupRmonByteCntIndex }
	::= { pm1008dcpMonupRmonByteCntTable 1 }


Pm1008dcpMonupRmonByteCntEntry ::=
	SEQUENCE {
	pm1008dcpMonupRmonByteCntIndex
		INTEGER,
	pm1008dcpMonupRmonByteCntValuePortn
		Counter64,
	pm1008dcpMonupRmonByteCntErrorPortn
		EkiOnOff,
	pm1008dcpMonupRmonByteCntOverloadPortn
		EkiOnOff
	}


pm1008dcpMonupRmonByteCntIndex OBJECT-TYPE
	SYNTAX  INTEGER(0..128)
	MAX-ACCESS  read-only
	STATUS current
	DESCRIPTION
        "
        Index definition for the pm1008dcpMonupRmonByteCnt 
        table
        "
	::= { pm1008dcpMonupRmonByteCntEntry 1 }


pm1008dcpMonupRmonByteCntValuePortn OBJECT-TYPE
	SYNTAX  Counter64
	MAX-ACCESS read-only
	STATUS current
	DESCRIPTION
        "
        Client Input Bytes :This counter 
        is increased each time a data byte 
        is received on the client port
          <Help>  This counter gives the 
        number of bytes received on the 
        client port
        "
	::= { pm1008dcpMonupRmonByteCntEntry 2 }


pm1008dcpMonupRmonByteCntErrorPortn OBJECT-TYPE
	SYNTAX  EkiOnOff
	MAX-ACCESS read-only
	STATUS current
	DESCRIPTION
        "
        Bytes Counter Error :This OID
         when set indicates the Bytes counter 
        value is invalid on clinet port
        "
	::= { pm1008dcpMonupRmonByteCntEntry 3 }


pm1008dcpMonupRmonByteCntOverloadPortn OBJECT-TYPE
	SYNTAX  EkiOnOff
	MAX-ACCESS read-only
	STATUS current
	DESCRIPTION
        "
        Bytes Counter Overload :This OID 
        when set indicates a Bytes counter 
        overload on client port
        "
	::= { pm1008dcpMonupRmonByteCntEntry 4 }


--- *********************************************************
---     TABLE for the pm1008dcpMonupRmonCrcErrorCnt articles
--- *********************************************************

pm1008dcpMonupRmonCrcErrorCntTable OBJECT-TYPE
	SYNTAX  SEQUENCE OF Pm1008dcpMonupRmonCrcErrorCntEntry
	MAX-ACCESS not-accessible
	STATUS current
	DESCRIPTION
        "
        List of pm1008dcpMonupRmonCrcErrorCnt 
        Article
        "
	::= { pm1008dcpMonClientRmonCounter 24 }


pm1008dcpMonupRmonCrcErrorCntEntry OBJECT-TYPE
	SYNTAX Pm1008dcpMonupRmonCrcErrorCntEntry
	MAX-ACCESS not-accessible
	STATUS current
	DESCRIPTION
        "
        Row definition for the pm1008dcpMonupRmonCrcErrorCnt 
        table
        "
	INDEX   { pm1008dcpMonupRmonCrcErrorCntIndex }
	::= { pm1008dcpMonupRmonCrcErrorCntTable 1 }


Pm1008dcpMonupRmonCrcErrorCntEntry ::=
	SEQUENCE {
	pm1008dcpMonupRmonCrcErrorCntIndex
		INTEGER,
	pm1008dcpMonupRmonCrcErrorCntValuePortn
		Counter64,
	pm1008dcpMonupRmonCrcErrorCntErrorPortn
		EkiOnOff,
	pm1008dcpMonupRmonCrcErrorCntOverloadPortn
		EkiOnOff
	}


pm1008dcpMonupRmonCrcErrorCntIndex OBJECT-TYPE
	SYNTAX  INTEGER(0..128)
	MAX-ACCESS  read-only
	STATUS current
	DESCRIPTION
        "
        Index definition for the pm1008dcpMonupRmonCrcErrorCnt 
        table
        "
	::= { pm1008dcpMonupRmonCrcErrorCntEntry 1 }


pm1008dcpMonupRmonCrcErrorCntValuePortn OBJECT-TYPE
	SYNTAX  Counter64
	MAX-ACCESS read-only
	STATUS current
	DESCRIPTION
        "
        Client Input CRC Errors :This
         counter is increased each time 
        a CRC error is detected on the
         client port  <Help>  This counter 
        gives the number of CRC Errors
         received on the client port
        "
	::= { pm1008dcpMonupRmonCrcErrorCntEntry 2 }


pm1008dcpMonupRmonCrcErrorCntErrorPortn OBJECT-TYPE
	SYNTAX  EkiOnOff
	MAX-ACCESS read-only
	STATUS current
	DESCRIPTION
        "
        CRC Errors Counter Error :This 
        OID when set indicates the CRC
         Errors counter value is invalid 
        on clinet port
        "
	::= { pm1008dcpMonupRmonCrcErrorCntEntry 3 }


pm1008dcpMonupRmonCrcErrorCntOverloadPortn OBJECT-TYPE
	SYNTAX  EkiOnOff
	MAX-ACCESS read-only
	STATUS current
	DESCRIPTION
        "
        CRC Errors Counter Overload :This 
        OID when set indicates a CRC Errors 
        counter overload on client port
        "
	::= { pm1008dcpMonupRmonCrcErrorCntEntry 4 }


--- *********************************************************
---     TABLE for the pm1008dcpMonupRmonPacketsCnt articles
--- *********************************************************

pm1008dcpMonupRmonPacketsCntTable OBJECT-TYPE
	SYNTAX  SEQUENCE OF Pm1008dcpMonupRmonPacketsCntEntry
	MAX-ACCESS not-accessible
	STATUS current
	DESCRIPTION
        "
        List of pm1008dcpMonupRmonPacketsCnt 
        Article
        "
	::= { pm1008dcpMonClientRmonCounter 32 }


pm1008dcpMonupRmonPacketsCntEntry OBJECT-TYPE
	SYNTAX Pm1008dcpMonupRmonPacketsCntEntry
	MAX-ACCESS not-accessible
	STATUS current
	DESCRIPTION
        "
        Row definition for the pm1008dcpMonupRmonPacketsCnt 
        table
        "
	INDEX   { pm1008dcpMonupRmonPacketsCntIndex }
	::= { pm1008dcpMonupRmonPacketsCntTable 1 }


Pm1008dcpMonupRmonPacketsCntEntry ::=
	SEQUENCE {
	pm1008dcpMonupRmonPacketsCntIndex
		INTEGER,
	pm1008dcpMonupRmonPacketsCntValuePortn
		Counter64,
	pm1008dcpMonupRmonPacketsCntErrorPortn
		EkiOnOff,
	pm1008dcpMonupRmonPacketsCntOverloadPortn
		EkiOnOff
	}


pm1008dcpMonupRmonPacketsCntIndex OBJECT-TYPE
	SYNTAX  INTEGER(0..128)
	MAX-ACCESS  read-only
	STATUS current
	DESCRIPTION
        "
        Index definition for the pm1008dcpMonupRmonPacketsCnt 
        table
        "
	::= { pm1008dcpMonupRmonPacketsCntEntry 1 }


pm1008dcpMonupRmonPacketsCntValuePortn OBJECT-TYPE
	SYNTAX  Counter64
	MAX-ACCESS read-only
	STATUS current
	DESCRIPTION
        "
        Client Input Packets :This counter 
        is increased each time a packet 
        is received on the client port
          <Help>  This counter gives the 
        number of packets received on the 
        client port
        "
	::= { pm1008dcpMonupRmonPacketsCntEntry 2 }


pm1008dcpMonupRmonPacketsCntErrorPortn OBJECT-TYPE
	SYNTAX  EkiOnOff
	MAX-ACCESS read-only
	STATUS current
	DESCRIPTION
        "
        Packets Counter Error :This OID 
        when set indicates the Packets
         counter value is invalid on clinet 
        port
        "
	::= { pm1008dcpMonupRmonPacketsCntEntry 3 }


pm1008dcpMonupRmonPacketsCntOverloadPortn OBJECT-TYPE
	SYNTAX  EkiOnOff
	MAX-ACCESS read-only
	STATUS current
	DESCRIPTION
        "
        Packets Counter Overload :This 
        OID when set indicates a Packets 
        counter overload on client port
        "
	::= { pm1008dcpMonupRmonPacketsCntEntry 4 }


--- *********************************************************
---     TABLE for the pm1008dcpMonupRmonBroadcastCnt articles
--- *********************************************************

pm1008dcpMonupRmonBroadcastCntTable OBJECT-TYPE
	SYNTAX  SEQUENCE OF Pm1008dcpMonupRmonBroadcastCntEntry
	MAX-ACCESS not-accessible
	STATUS current
	DESCRIPTION
        "
        List of pm1008dcpMonupRmonBroadcastCnt 
        Article
        "
	::= { pm1008dcpMonClientRmonCounter 40 }


pm1008dcpMonupRmonBroadcastCntEntry OBJECT-TYPE
	SYNTAX Pm1008dcpMonupRmonBroadcastCntEntry
	MAX-ACCESS not-accessible
	STATUS current
	DESCRIPTION
        "
        Row definition for the pm1008dcpMonupRmonBroadcastCnt 
        table
        "
	INDEX   { pm1008dcpMonupRmonBroadcastCntIndex }
	::= { pm1008dcpMonupRmonBroadcastCntTable 1 }


Pm1008dcpMonupRmonBroadcastCntEntry ::=
	SEQUENCE {
	pm1008dcpMonupRmonBroadcastCntIndex
		INTEGER,
	pm1008dcpMonupRmonBroadcastCntValuePortn
		Counter64,
	pm1008dcpMonupRmonBroadcastCntErrorPortn
		EkiOnOff,
	pm1008dcpMonupRmonBroadcastCntOverloadPortn
		EkiOnOff
	}


pm1008dcpMonupRmonBroadcastCntIndex OBJECT-TYPE
	SYNTAX  INTEGER(0..128)
	MAX-ACCESS  read-only
	STATUS current
	DESCRIPTION
        "
        Index definition for the pm1008dcpMonupRmonBroadcastCnt 
        table
        "
	::= { pm1008dcpMonupRmonBroadcastCntEntry 1 }


pm1008dcpMonupRmonBroadcastCntValuePortn OBJECT-TYPE
	SYNTAX  Counter64
	MAX-ACCESS read-only
	STATUS current
	DESCRIPTION
        "
        Client Input Broadcast Packets 
        :This counter is increased each 
        time a broadcast packet is received 
        on the client port  <Help>  This 
        counter gives the number of Broadcast 
        packets received on the client
         port
        "
	::= { pm1008dcpMonupRmonBroadcastCntEntry 2 }


pm1008dcpMonupRmonBroadcastCntErrorPortn OBJECT-TYPE
	SYNTAX  EkiOnOff
	MAX-ACCESS read-only
	STATUS current
	DESCRIPTION
        "
        Broadcast Counter Error :This
         OID when set indicates the Broadcast 
        counter value is invalid on clinet 
        port
        "
	::= { pm1008dcpMonupRmonBroadcastCntEntry 3 }


pm1008dcpMonupRmonBroadcastCntOverloadPortn OBJECT-TYPE
	SYNTAX  EkiOnOff
	MAX-ACCESS read-only
	STATUS current
	DESCRIPTION
        "
        Broadcast Counter Overload :This 
        OID when set indicates a Broadcast 
        counter overload on client port
        "
	::= { pm1008dcpMonupRmonBroadcastCntEntry 4 }


--- *********************************************************
---     TABLE for the pm1008dcpMonupRmonMulticastCnt articles
--- *********************************************************

pm1008dcpMonupRmonMulticastCntTable OBJECT-TYPE
	SYNTAX  SEQUENCE OF Pm1008dcpMonupRmonMulticastCntEntry
	MAX-ACCESS not-accessible
	STATUS current
	DESCRIPTION
        "
        List of pm1008dcpMonupRmonMulticastCnt 
        Article
        "
	::= { pm1008dcpMonClientRmonCounter 48 }


pm1008dcpMonupRmonMulticastCntEntry OBJECT-TYPE
	SYNTAX Pm1008dcpMonupRmonMulticastCntEntry
	MAX-ACCESS not-accessible
	STATUS current
	DESCRIPTION
        "
        Row definition for the pm1008dcpMonupRmonMulticastCnt 
        table
        "
	INDEX   { pm1008dcpMonupRmonMulticastCntIndex }
	::= { pm1008dcpMonupRmonMulticastCntTable 1 }


Pm1008dcpMonupRmonMulticastCntEntry ::=
	SEQUENCE {
	pm1008dcpMonupRmonMulticastCntIndex
		INTEGER,
	pm1008dcpMonupRmonMulticastCntValuePortn
		Counter64,
	pm1008dcpMonupRmonMulticastCntErrorPortn
		EkiOnOff,
	pm1008dcpMonupRmonMulticastCntOverloadPortn
		EkiOnOff
	}


pm1008dcpMonupRmonMulticastCntIndex OBJECT-TYPE
	SYNTAX  INTEGER(0..128)
	MAX-ACCESS  read-only
	STATUS current
	DESCRIPTION
        "
        Index definition for the pm1008dcpMonupRmonMulticastCnt 
        table
        "
	::= { pm1008dcpMonupRmonMulticastCntEntry 1 }


pm1008dcpMonupRmonMulticastCntValuePortn OBJECT-TYPE
	SYNTAX  Counter64
	MAX-ACCESS read-only
	STATUS current
	DESCRIPTION
        "
        Client Input Multicast Packets 
        :This counter is increased each 
        time a Multicast packet is received 
        on the client port  <Help>  This 
        counter gives the number of Multicast 
        packets received on the client
         port
        "
	::= { pm1008dcpMonupRmonMulticastCntEntry 2 }


pm1008dcpMonupRmonMulticastCntErrorPortn OBJECT-TYPE
	SYNTAX  EkiOnOff
	MAX-ACCESS read-only
	STATUS current
	DESCRIPTION
        "
        Multicast Counter Error :This
         OID when set indicates the Multicast 
        counter value is invalid on clinet 
        port
        "
	::= { pm1008dcpMonupRmonMulticastCntEntry 3 }


pm1008dcpMonupRmonMulticastCntOverloadPortn OBJECT-TYPE
	SYNTAX  EkiOnOff
	MAX-ACCESS read-only
	STATUS current
	DESCRIPTION
        "
        Multicast Counter Overload :This 
        OID when set indicates a Multicast 
        counter overload on client port
        "
	::= { pm1008dcpMonupRmonMulticastCntEntry 4 }


pm1008dcpMonCountersReset  OBJECT-TYPE
	SYNTAX EkiOnOff
	MAX-ACCESS read-write
	STATUS current
	DESCRIPTION
	"RMON Counters Reset:This OID resets and restarts all the RMON counters"
	::= { pm1008dcpMonRmon   359 }

pm1008dcpMonCountersStop  OBJECT-TYPE
	SYNTAX EkiOnOff
	MAX-ACCESS read-write
	STATUS current
	DESCRIPTION
	"RMON Counters stop:This OID stops all the RMON counters"
	::= { pm1008dcpMonRmon  360 }






--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm1008dcpMesrsynth0 OBJECT-TYPE
	  SYNTAX EkiMeasureType
	  MAX-ACCESS read-only
	  STATUS deprecated
	  DESCRIPTION
        "
        Not Used :This OID gives the unit 
        used on AUX1 measurement of XFP 
         (Unit = )
        "
	  ::= { pm1008dcpMesrOther 0 }



pm1008dcpMesrsynth1 OBJECT-TYPE
	  SYNTAX EkiMeasureType
	  MAX-ACCESS read-only
	  STATUS deprecated
	  DESCRIPTION
        "
        Not Used :This OID gives the unit 
        used on AUX2 measurement of XFP 
         (Unit = )
        "
	  ::= { pm1008dcpMesrOther 1 }



--- *********************************************************
---     TABLE for the pm1008dcpMesrtempMeas articles
--- *********************************************************

pm1008dcpMesrtempMeasTable OBJECT-TYPE
	SYNTAX  SEQUENCE OF Pm1008dcpMesrtempMeasEntry
	MAX-ACCESS not-accessible
	STATUS current
	DESCRIPTION
        "
        List of pm1008dcpMesrtempMeas
         Article
        "
	::= { pm1008dcpMesrClient 16 }


pm1008dcpMesrtempMeasEntry OBJECT-TYPE
	SYNTAX Pm1008dcpMesrtempMeasEntry
	MAX-ACCESS not-accessible
	STATUS current
	DESCRIPTION
        "
        Row definition for the pm1008dcpMesrtempMeas 
        table
        "
	INDEX   { pm1008dcpMesrtempMeasIndex }
	::= { pm1008dcpMesrtempMeasTable 1 }


Pm1008dcpMesrtempMeasEntry ::=
	SEQUENCE {
	pm1008dcpMesrtempMeasIndex
		INTEGER,
	pm1008dcpMesrtempMeasPortn
		INTEGER 
	}


pm1008dcpMesrtempMeasIndex OBJECT-TYPE
	SYNTAX  INTEGER(0..128)
	MAX-ACCESS  read-only
	STATUS current
	DESCRIPTION
        "
        Index definition for the pm1008dcpMesrtempMeas 
        table
        "
	::= { pm1008dcpMesrtempMeasEntry 1 }


pm1008dcpMesrtempMeasPortn OBJECT-TYPE
	SYNTAX  INTEGER (0..65535)
	MAX-ACCESS read-only
	STATUS current
	DESCRIPTION
        "
        Client SFP Temperature :This OID 
        gives the temperature value of
         the SFP plugged in port, read
         from the DDM (Digital Diagnostic 
        Monitoring) (Temperature = AV/256) 
        (Unit = C)  <Help>  This measure 
        gives the temperature of the client 
        transceiver
        "
	::= { pm1008dcpMesrtempMeasEntry 2 }


--- *********************************************************
---     TABLE for the pm1008dcpMesrvoltMeas articles
--- *********************************************************

pm1008dcpMesrvoltMeasTable OBJECT-TYPE
	SYNTAX  SEQUENCE OF Pm1008dcpMesrvoltMeasEntry
	MAX-ACCESS not-accessible
	STATUS current
	DESCRIPTION
        "
        List of pm1008dcpMesrvoltMeas
         Article
        "
	::= { pm1008dcpMesrClient 24 }


pm1008dcpMesrvoltMeasEntry OBJECT-TYPE
	SYNTAX Pm1008dcpMesrvoltMeasEntry
	MAX-ACCESS not-accessible
	STATUS current
	DESCRIPTION
        "
        Row definition for the pm1008dcpMesrvoltMeas 
        table
        "
	INDEX   { pm1008dcpMesrvoltMeasIndex }
	::= { pm1008dcpMesrvoltMeasTable 1 }


Pm1008dcpMesrvoltMeasEntry ::=
	SEQUENCE {
	pm1008dcpMesrvoltMeasIndex
		INTEGER,
	pm1008dcpMesrvoltMeasPortn
		INTEGER 
	}


pm1008dcpMesrvoltMeasIndex OBJECT-TYPE
	SYNTAX  INTEGER(0..128)
	MAX-ACCESS  read-only
	STATUS current
	DESCRIPTION
        "
        Index definition for the pm1008dcpMesrvoltMeas 
        table
        "
	::= { pm1008dcpMesrvoltMeasEntry 1 }


pm1008dcpMesrvoltMeasPortn OBJECT-TYPE
	SYNTAX  INTEGER (0..65535)
	MAX-ACCESS read-only
	STATUS current
	DESCRIPTION
        "
        Client SFP Power Supply :This
         OID gives the 3V3 voltage value 
        of the SFP plugged into port, read 
        from the DDM (Digital Diagnostic 
        Monitoring) (Voltage = AV/10000) 
        (Unit = V)  <Help>  This measure 
        gives the 3V3 voltage of the client 
        transceiver
        "
	::= { pm1008dcpMesrvoltMeasEntry 2 }


--- *********************************************************
---     TABLE for the pm1008dcpMesrbiasMeas articles
--- *********************************************************

pm1008dcpMesrbiasMeasTable OBJECT-TYPE
	SYNTAX  SEQUENCE OF Pm1008dcpMesrbiasMeasEntry
	MAX-ACCESS not-accessible
	STATUS current
	DESCRIPTION
        "
        List of pm1008dcpMesrbiasMeas
         Article
        "
	::= { pm1008dcpMesrClient 32 }


pm1008dcpMesrbiasMeasEntry OBJECT-TYPE
	SYNTAX Pm1008dcpMesrbiasMeasEntry
	MAX-ACCESS not-accessible
	STATUS current
	DESCRIPTION
        "
        Row definition for the pm1008dcpMesrbiasMeas 
        table
        "
	INDEX   { pm1008dcpMesrbiasMeasIndex }
	::= { pm1008dcpMesrbiasMeasTable 1 }


Pm1008dcpMesrbiasMeasEntry ::=
	SEQUENCE {
	pm1008dcpMesrbiasMeasIndex
		INTEGER,
	pm1008dcpMesrbiasMeasPortn
		INTEGER 
	}


pm1008dcpMesrbiasMeasIndex OBJECT-TYPE
	SYNTAX  INTEGER(0..128)
	MAX-ACCESS  read-only
	STATUS current
	DESCRIPTION
        "
        Index definition for the pm1008dcpMesrbiasMeas 
        table
        "
	::= { pm1008dcpMesrbiasMeasEntry 1 }


pm1008dcpMesrbiasMeasPortn OBJECT-TYPE
	SYNTAX  INTEGER (0..65535)
	MAX-ACCESS read-only
	STATUS current
	DESCRIPTION
        "
        Client SFP Laser Bias :This OID 
        gives the bias value of the SFP 
        plugged into port, read from the 
        DDM (Digital Diagnostic Monitoring) 
         (Bias = AV/500) (Unit = mA)  <Help> 
         This measure gives the bias of 
        the client transceiver
        "
	::= { pm1008dcpMesrbiasMeasEntry 2 }


--- *********************************************************
---     TABLE for the pm1008dcpMesrtxpwrMeas articles
--- *********************************************************

pm1008dcpMesrtxpwrMeasTable OBJECT-TYPE
	SYNTAX  SEQUENCE OF Pm1008dcpMesrtxpwrMeasEntry
	MAX-ACCESS not-accessible
	STATUS current
	DESCRIPTION
        "
        List of pm1008dcpMesrtxpwrMeas 
        Article
        "
	::= { pm1008dcpMesrClient 40 }


pm1008dcpMesrtxpwrMeasEntry OBJECT-TYPE
	SYNTAX Pm1008dcpMesrtxpwrMeasEntry
	MAX-ACCESS not-accessible
	STATUS current
	DESCRIPTION
        "
        Row definition for the pm1008dcpMesrtxpwrMeas 
        table
        "
	INDEX   { pm1008dcpMesrtxpwrMeasIndex }
	::= { pm1008dcpMesrtxpwrMeasTable 1 }


Pm1008dcpMesrtxpwrMeasEntry ::=
	SEQUENCE {
	pm1008dcpMesrtxpwrMeasIndex
		INTEGER,
	pm1008dcpMesrtxpwrMeasPortn
		INTEGER 
	}


pm1008dcpMesrtxpwrMeasIndex OBJECT-TYPE
	SYNTAX  INTEGER(0..128)
	MAX-ACCESS  read-only
	STATUS current
	DESCRIPTION
        "
        Index definition for the pm1008dcpMesrtxpwrMeas 
        table
        "
	::= { pm1008dcpMesrtxpwrMeasEntry 1 }


pm1008dcpMesrtxpwrMeasPortn OBJECT-TYPE
	SYNTAX  INTEGER (0..65535)
	MAX-ACCESS read-only
	STATUS current
	DESCRIPTION
        "
        Client SFP Tx Power :This OID
         gives the transmit power value 
        of the SFP plugged into port, read 
        from the DDM (Digital Diagnostic 
        Monitoring) (Power = 10*log(AV)-40) 
        (Unit = dBm)  <Help>  This measure 
        gives the Tx optical power of the 
        client transceiver
        "
	::= { pm1008dcpMesrtxpwrMeasEntry 2 }


--- *********************************************************
---     TABLE for the pm1008dcpMesrrxpwrMeas articles
--- *********************************************************

pm1008dcpMesrrxpwrMeasTable OBJECT-TYPE
	SYNTAX  SEQUENCE OF Pm1008dcpMesrrxpwrMeasEntry
	MAX-ACCESS not-accessible
	STATUS current
	DESCRIPTION
        "
        List of pm1008dcpMesrrxpwrMeas 
        Article
        "
	::= { pm1008dcpMesrClient 48 }


pm1008dcpMesrrxpwrMeasEntry OBJECT-TYPE
	SYNTAX Pm1008dcpMesrrxpwrMeasEntry
	MAX-ACCESS not-accessible
	STATUS current
	DESCRIPTION
        "
        Row definition for the pm1008dcpMesrrxpwrMeas 
        table
        "
	INDEX   { pm1008dcpMesrrxpwrMeasIndex }
	::= { pm1008dcpMesrrxpwrMeasTable 1 }


Pm1008dcpMesrrxpwrMeasEntry ::=
	SEQUENCE {
	pm1008dcpMesrrxpwrMeasIndex
		INTEGER,
	pm1008dcpMesrrxpwrMeasPortn
		INTEGER 
	}


pm1008dcpMesrrxpwrMeasIndex OBJECT-TYPE
	SYNTAX  INTEGER(0..128)
	MAX-ACCESS  read-only
	STATUS current
	DESCRIPTION
        "
        Index definition for the pm1008dcpMesrrxpwrMeas 
        table
        "
	::= { pm1008dcpMesrrxpwrMeasEntry 1 }


pm1008dcpMesrrxpwrMeasPortn OBJECT-TYPE
	SYNTAX  INTEGER (0..65535)
	MAX-ACCESS read-only
	STATUS current
	DESCRIPTION
        "
        Client SFP Rx Power :This OID
         gives the receive power value
         of the SFP plugged into port,
         read in the DDM (Digital Diagnostic 
        Monitoring) (Power = 10*log(AV)-40) 
        (Unit = dBm)  <Help>  This measure 
        gives the Rx optical power of the 
        client transceiver
        "
	::= { pm1008dcpMesrrxpwrMeasEntry 2 }


--- *********************************************************
---     TABLE for the pm1008dcpMesrxfp1LxModTempMeas articles
--- *********************************************************

pm1008dcpMesrxfp1LxModTempMeasTable OBJECT-TYPE
	SYNTAX  SEQUENCE OF Pm1008dcpMesrxfp1LxModTempMeasEntry
	MAX-ACCESS not-accessible
	STATUS current
	DESCRIPTION
        "
        List of pm1008dcpMesrxfp1LxModTempMeas 
        Article
        "
	::= { pm1008dcpMesrLine 208 }


pm1008dcpMesrxfp1LxModTempMeasEntry OBJECT-TYPE
	SYNTAX Pm1008dcpMesrxfp1LxModTempMeasEntry
	MAX-ACCESS not-accessible
	STATUS current
	DESCRIPTION
        "
        Row definition for the pm1008dcpMesrxfp1LxModTempMeas 
        table
        "
	INDEX   { pm1008dcpMesrxfp1LxModTempMeasIndex }
	::= { pm1008dcpMesrxfp1LxModTempMeasTable 1 }


Pm1008dcpMesrxfp1LxModTempMeasEntry ::=
	SEQUENCE {
	pm1008dcpMesrxfp1LxModTempMeasIndex
		INTEGER,
	pm1008dcpMesrxfp1LxModTempMeasPortn
		INTEGER 
	}


pm1008dcpMesrxfp1LxModTempMeasIndex OBJECT-TYPE
	SYNTAX  INTEGER(0..128)
	MAX-ACCESS  read-only
	STATUS current
	DESCRIPTION
        "
        Index definition for the pm1008dcpMesrxfp1LxModTempMeas 
        table
        "
	::= { pm1008dcpMesrxfp1LxModTempMeasEntry 1 }


pm1008dcpMesrxfp1LxModTempMeasPortn OBJECT-TYPE
	SYNTAX  INTEGER (0..65535)
	MAX-ACCESS read-only
	STATUS current
	DESCRIPTION
        "
        Line Optical Module Temperature 
        :This OID gives the temperature 
        of the XFP or OTX plugged in line, 
        read from the DDM (Digital Diagnostic 
        Monitoring) (Temperature = AV/256) 
        (Unit = C)  <Help>  This measure 
        gives the temperature of the line 
        transceiver
        "
	::= { pm1008dcpMesrxfp1LxModTempMeasEntry 2 }


--- *********************************************************
---     TABLE for the pm1008dcpMesrxfp1Reserved articles
--- *********************************************************

pm1008dcpMesrxfp1ReservedTable OBJECT-TYPE
	SYNTAX  SEQUENCE OF Pm1008dcpMesrxfp1ReservedEntry
	MAX-ACCESS not-accessible
	STATUS deprecated
	DESCRIPTION
        "
        List of pm1008dcpMesrxfp1Reserved 
        Article
        "
	::= { pm1008dcpMesrLine 209 }


pm1008dcpMesrxfp1ReservedEntry OBJECT-TYPE
	SYNTAX Pm1008dcpMesrxfp1ReservedEntry
	MAX-ACCESS not-accessible
	STATUS deprecated
	DESCRIPTION
        "
        Row definition for the pm1008dcpMesrxfp1Reserved 
        table
        "
	INDEX   { pm1008dcpMesrxfp1ReservedIndex }
	::= { pm1008dcpMesrxfp1ReservedTable 1 }


Pm1008dcpMesrxfp1ReservedEntry ::=
	SEQUENCE {
	pm1008dcpMesrxfp1ReservedIndex
		INTEGER,
	pm1008dcpMesrxfp1ReservedPortn
		INTEGER 
	}


pm1008dcpMesrxfp1ReservedIndex OBJECT-TYPE
	SYNTAX  INTEGER(0..128)
	MAX-ACCESS  read-only
	STATUS deprecated
	DESCRIPTION
        "
        Index definition for the pm1008dcpMesrxfp1Reserved 
        table
        "
	::= { pm1008dcpMesrxfp1ReservedEntry 1 }


pm1008dcpMesrxfp1ReservedPortn OBJECT-TYPE
	SYNTAX  INTEGER (0..65535)
	MAX-ACCESS read-only
	STATUS deprecated
	DESCRIPTION
        "
        Not Used :Reserved
        "
	::= { pm1008dcpMesrxfp1ReservedEntry 2 }


--- *********************************************************
---     TABLE for the pm1008dcpMesrxfp1LoBiasCurrentMeas articles
--- *********************************************************

pm1008dcpMesrxfp1LoBiasCurrentMeasTable OBJECT-TYPE
	SYNTAX  SEQUENCE OF Pm1008dcpMesrxfp1LoBiasCurrentMeasEntry
	MAX-ACCESS not-accessible
	STATUS current
	DESCRIPTION
        "
        List of pm1008dcpMesrxfp1LoBiasCurrentMeas 
        Article
        "
	::= { pm1008dcpMesrLine 210 }


pm1008dcpMesrxfp1LoBiasCurrentMeasEntry OBJECT-TYPE
	SYNTAX Pm1008dcpMesrxfp1LoBiasCurrentMeasEntry
	MAX-ACCESS not-accessible
	STATUS current
	DESCRIPTION
        "
        Row definition for the pm1008dcpMesrxfp1LoBiasCurrentMeas 
        table
        "
	INDEX   { pm1008dcpMesrxfp1LoBiasCurrentMeasIndex }
	::= { pm1008dcpMesrxfp1LoBiasCurrentMeasTable 1 }


Pm1008dcpMesrxfp1LoBiasCurrentMeasEntry ::=
	SEQUENCE {
	pm1008dcpMesrxfp1LoBiasCurrentMeasIndex
		INTEGER,
	pm1008dcpMesrxfp1LoBiasCurrentMeasPortn
		INTEGER 
	}


pm1008dcpMesrxfp1LoBiasCurrentMeasIndex OBJECT-TYPE
	SYNTAX  INTEGER(0..128)
	MAX-ACCESS  read-only
	STATUS current
	DESCRIPTION
        "
        Index definition for the pm1008dcpMesrxfp1LoBiasCurrentMeas 
        table
        "
	::= { pm1008dcpMesrxfp1LoBiasCurrentMeasEntry 1 }


pm1008dcpMesrxfp1LoBiasCurrentMeasPortn OBJECT-TYPE
	SYNTAX  INTEGER (0..65535)
	MAX-ACCESS read-only
	STATUS current
	DESCRIPTION
        "
        Line Optical Module Laser Bias 
        :This OID gives the bias value
         of the XFP or OTX plugged in line 
        , read from the DDM (Digital Diagnostic 
        Monitoring) (Bias = AV/500) (Unit 
        = mA)  <Help>  This measure gives 
        the bias of the line transceiver
        "
	::= { pm1008dcpMesrxfp1LoBiasCurrentMeasEntry 2 }


--- *********************************************************
---     TABLE for the pm1008dcpMesrxfp1LoTxPowerMeas articles
--- *********************************************************

pm1008dcpMesrxfp1LoTxPowerMeasTable OBJECT-TYPE
	SYNTAX  SEQUENCE OF Pm1008dcpMesrxfp1LoTxPowerMeasEntry
	MAX-ACCESS not-accessible
	STATUS current
	DESCRIPTION
        "
        List of pm1008dcpMesrxfp1LoTxPowerMeas 
        Article
        "
	::= { pm1008dcpMesrLine 211 }


pm1008dcpMesrxfp1LoTxPowerMeasEntry OBJECT-TYPE
	SYNTAX Pm1008dcpMesrxfp1LoTxPowerMeasEntry
	MAX-ACCESS not-accessible
	STATUS current
	DESCRIPTION
        "
        Row definition for the pm1008dcpMesrxfp1LoTxPowerMeas 
        table
        "
	INDEX   { pm1008dcpMesrxfp1LoTxPowerMeasIndex }
	::= { pm1008dcpMesrxfp1LoTxPowerMeasTable 1 }


Pm1008dcpMesrxfp1LoTxPowerMeasEntry ::=
	SEQUENCE {
	pm1008dcpMesrxfp1LoTxPowerMeasIndex
		INTEGER,
	pm1008dcpMesrxfp1LoTxPowerMeasPortn
		INTEGER 
	}


pm1008dcpMesrxfp1LoTxPowerMeasIndex OBJECT-TYPE
	SYNTAX  INTEGER(0..128)
	MAX-ACCESS  read-only
	STATUS current
	DESCRIPTION
        "
        Index definition for the pm1008dcpMesrxfp1LoTxPowerMeas 
        table
        "
	::= { pm1008dcpMesrxfp1LoTxPowerMeasEntry 1 }


pm1008dcpMesrxfp1LoTxPowerMeasPortn OBJECT-TYPE
	SYNTAX  INTEGER (0..65535)
	MAX-ACCESS read-only
	STATUS current
	DESCRIPTION
        "
        Line Optical Module Tx Power :This 
        OID gives the transmit power value 
        of the XFP or OTX plugged in line 
        , read from the DDM (Digital  
         Diagnostic Monitoring) (Power
         = 10*log(AV)-40) (Unit = dBm)
          <Help>  This measure gives the 
        Tx optical power of the line transceiver
        "
	::= { pm1008dcpMesrxfp1LoTxPowerMeasEntry 2 }


--- *********************************************************
---     TABLE for the pm1008dcpMesrxfp1LiRxPowerMeas articles
--- *********************************************************

pm1008dcpMesrxfp1LiRxPowerMeasTable OBJECT-TYPE
	SYNTAX  SEQUENCE OF Pm1008dcpMesrxfp1LiRxPowerMeasEntry
	MAX-ACCESS not-accessible
	STATUS current
	DESCRIPTION
        "
        List of pm1008dcpMesrxfp1LiRxPowerMeas 
        Article
        "
	::= { pm1008dcpMesrLine 212 }


pm1008dcpMesrxfp1LiRxPowerMeasEntry OBJECT-TYPE
	SYNTAX Pm1008dcpMesrxfp1LiRxPowerMeasEntry
	MAX-ACCESS not-accessible
	STATUS current
	DESCRIPTION
        "
        Row definition for the pm1008dcpMesrxfp1LiRxPowerMeas 
        table
        "
	INDEX   { pm1008dcpMesrxfp1LiRxPowerMeasIndex }
	::= { pm1008dcpMesrxfp1LiRxPowerMeasTable 1 }


Pm1008dcpMesrxfp1LiRxPowerMeasEntry ::=
	SEQUENCE {
	pm1008dcpMesrxfp1LiRxPowerMeasIndex
		INTEGER,
	pm1008dcpMesrxfp1LiRxPowerMeasPortn
		INTEGER 
	}


pm1008dcpMesrxfp1LiRxPowerMeasIndex OBJECT-TYPE
	SYNTAX  INTEGER(0..128)
	MAX-ACCESS  read-only
	STATUS current
	DESCRIPTION
        "
        Index definition for the pm1008dcpMesrxfp1LiRxPowerMeas 
        table
        "
	::= { pm1008dcpMesrxfp1LiRxPowerMeasEntry 1 }


pm1008dcpMesrxfp1LiRxPowerMeasPortn OBJECT-TYPE
	SYNTAX  INTEGER (0..65535)
	MAX-ACCESS read-only
	STATUS current
	DESCRIPTION
        "
        Line Optical Module Rx Power :This 
        OID gives the receive power value 
        of the XFP or OTX plugged in line 
        , read from the DDM (Digital Diagnostic 
        Monitoring) (Power = 10*log(AV)-40) 
        (Unit = dBm)  <Help>  This measure 
        gives the Rx optical power of the 
        line transceiver
        "
	::= { pm1008dcpMesrxfp1LiRxPowerMeasEntry 2 }


--- *********************************************************
---     TABLE for the pm1008dcpMesrxfp1LxAux1Meas articles
--- *********************************************************

pm1008dcpMesrxfp1LxAux1MeasTable OBJECT-TYPE
	SYNTAX  SEQUENCE OF Pm1008dcpMesrxfp1LxAux1MeasEntry
	MAX-ACCESS not-accessible
	STATUS deprecated
	DESCRIPTION
        "
        List of pm1008dcpMesrxfp1LxAux1Meas 
        Article
        "
	::= { pm1008dcpMesrLine 213 }


pm1008dcpMesrxfp1LxAux1MeasEntry OBJECT-TYPE
	SYNTAX Pm1008dcpMesrxfp1LxAux1MeasEntry
	MAX-ACCESS not-accessible
	STATUS deprecated
	DESCRIPTION
        "
        Row definition for the pm1008dcpMesrxfp1LxAux1Meas 
        table
        "
	INDEX   { pm1008dcpMesrxfp1LxAux1MeasIndex }
	::= { pm1008dcpMesrxfp1LxAux1MeasTable 1 }


Pm1008dcpMesrxfp1LxAux1MeasEntry ::=
	SEQUENCE {
	pm1008dcpMesrxfp1LxAux1MeasIndex
		INTEGER,
	pm1008dcpMesrxfp1LxAux1MeasPortn
		INTEGER 
	}


pm1008dcpMesrxfp1LxAux1MeasIndex OBJECT-TYPE
	SYNTAX  INTEGER(0..128)
	MAX-ACCESS  read-only
	STATUS deprecated
	DESCRIPTION
        "
        Index definition for the pm1008dcpMesrxfp1LxAux1Meas 
        table
        "
	::= { pm1008dcpMesrxfp1LxAux1MeasEntry 1 }


pm1008dcpMesrxfp1LxAux1MeasPortn OBJECT-TYPE
	SYNTAX  INTEGER (0..65535)
	MAX-ACCESS read-only
	STATUS deprecated
	DESCRIPTION
        "
        Not Used :This OID gives the receive 
        power value read in the DDM (Digital 
        Diagnostic Monitoring) of the XFP 
        or OTX plugged in line  (Unit = 
        ?)
        "
	::= { pm1008dcpMesrxfp1LxAux1MeasEntry 2 }


--- *********************************************************
---     TABLE for the pm1008dcpMesrxfp1LxAux2Meas articles
--- *********************************************************

pm1008dcpMesrxfp1LxAux2MeasTable OBJECT-TYPE
	SYNTAX  SEQUENCE OF Pm1008dcpMesrxfp1LxAux2MeasEntry
	MAX-ACCESS not-accessible
	STATUS deprecated
	DESCRIPTION
        "
        List of pm1008dcpMesrxfp1LxAux2Meas 
        Article
        "
	::= { pm1008dcpMesrLine 214 }


pm1008dcpMesrxfp1LxAux2MeasEntry OBJECT-TYPE
	SYNTAX Pm1008dcpMesrxfp1LxAux2MeasEntry
	MAX-ACCESS not-accessible
	STATUS deprecated
	DESCRIPTION
        "
        Row definition for the pm1008dcpMesrxfp1LxAux2Meas 
        table
        "
	INDEX   { pm1008dcpMesrxfp1LxAux2MeasIndex }
	::= { pm1008dcpMesrxfp1LxAux2MeasTable 1 }


Pm1008dcpMesrxfp1LxAux2MeasEntry ::=
	SEQUENCE {
	pm1008dcpMesrxfp1LxAux2MeasIndex
		INTEGER,
	pm1008dcpMesrxfp1LxAux2MeasPortn
		INTEGER 
	}


pm1008dcpMesrxfp1LxAux2MeasIndex OBJECT-TYPE
	SYNTAX  INTEGER(0..128)
	MAX-ACCESS  read-only
	STATUS deprecated
	DESCRIPTION
        "
        Index definition for the pm1008dcpMesrxfp1LxAux2Meas 
        table
        "
	::= { pm1008dcpMesrxfp1LxAux2MeasEntry 1 }


pm1008dcpMesrxfp1LxAux2MeasPortn OBJECT-TYPE
	SYNTAX  INTEGER (0..65535)
	MAX-ACCESS read-only
	STATUS deprecated
	DESCRIPTION
        "
        Not Used :This OID gives the receive 
        power value read in the DDM (Digital 
        Diagnostic Monitoring) of the XFP 
        or OTX plugged in line  (Unit = 
        ?)
        "
	::= { pm1008dcpMesrxfp1LxAux2MeasEntry 2 }


--- *********************************************************
---     TABLE for the pm1008dcpMesrotx1Aging articles
--- *********************************************************

pm1008dcpMesrotx1AgingTable OBJECT-TYPE
	SYNTAX  SEQUENCE OF Pm1008dcpMesrotx1AgingEntry
	MAX-ACCESS not-accessible
	STATUS current
	DESCRIPTION
        "
        List of pm1008dcpMesrotx1Aging 
        Article
        "
	::= { pm1008dcpMesrLine 224 }


pm1008dcpMesrotx1AgingEntry OBJECT-TYPE
	SYNTAX Pm1008dcpMesrotx1AgingEntry
	MAX-ACCESS not-accessible
	STATUS current
	DESCRIPTION
        "
        Row definition for the pm1008dcpMesrotx1Aging 
        table
        "
	INDEX   { pm1008dcpMesrotx1AgingIndex }
	::= { pm1008dcpMesrotx1AgingTable 1 }


Pm1008dcpMesrotx1AgingEntry ::=
	SEQUENCE {
	pm1008dcpMesrotx1AgingIndex
		INTEGER,
	pm1008dcpMesrotx1AgingPortn
		INTEGER 
	}


pm1008dcpMesrotx1AgingIndex OBJECT-TYPE
	SYNTAX  INTEGER(0..128)
	MAX-ACCESS  read-only
	STATUS current
	DESCRIPTION
        "
        Index definition for the pm1008dcpMesrotx1Aging 
        table
        "
	::= { pm1008dcpMesrotx1AgingEntry 1 }


pm1008dcpMesrotx1AgingPortn OBJECT-TYPE
	SYNTAX  INTEGER (0..65535)
	MAX-ACCESS read-only
	STATUS current
	DESCRIPTION
        "
        Line OTX TLH Aging :This OID gives 
        the aging of the Line OTX TLH,
         read from the DDM (Digital Diagnostic 
        Monitoring) (Aging = AV) (Unit
         = %)  <Help>  This measure gives 
        the aging of the Line OTX TLH
        "
	::= { pm1008dcpMesrotx1AgingEntry 2 }


--- *********************************************************
---     TABLE for the pm1008dcpMesrotx1LaserTemperature articles
--- *********************************************************

pm1008dcpMesrotx1LaserTemperatureTable OBJECT-TYPE
	SYNTAX  SEQUENCE OF Pm1008dcpMesrotx1LaserTemperatureEntry
	MAX-ACCESS not-accessible
	STATUS deprecated
	DESCRIPTION
        "
        List of pm1008dcpMesrotx1LaserTemperature 
        Article
        "
	::= { pm1008dcpMesrLine 225 }


pm1008dcpMesrotx1LaserTemperatureEntry OBJECT-TYPE
	SYNTAX Pm1008dcpMesrotx1LaserTemperatureEntry
	MAX-ACCESS not-accessible
	STATUS deprecated
	DESCRIPTION
        "
        Row definition for the pm1008dcpMesrotx1LaserTemperature 
        table
        "
	INDEX   { pm1008dcpMesrotx1LaserTemperatureIndex }
	::= { pm1008dcpMesrotx1LaserTemperatureTable 1 }


Pm1008dcpMesrotx1LaserTemperatureEntry ::=
	SEQUENCE {
	pm1008dcpMesrotx1LaserTemperatureIndex
		INTEGER,
	pm1008dcpMesrotx1LaserTemperaturePortn
		INTEGER 
	}


pm1008dcpMesrotx1LaserTemperatureIndex OBJECT-TYPE
	SYNTAX  INTEGER(0..128)
	MAX-ACCESS  read-only
	STATUS deprecated
	DESCRIPTION
        "
        Index definition for the pm1008dcpMesrotx1LaserTemperature 
        table
        "
	::= { pm1008dcpMesrotx1LaserTemperatureEntry 1 }


pm1008dcpMesrotx1LaserTemperaturePortn OBJECT-TYPE
	SYNTAX  INTEGER (0..65535)
	MAX-ACCESS read-only
	STATUS deprecated
	DESCRIPTION
        "
        Line OTX TLH Laser Temperature 
        :This OID gives the laser temperature 
        of the Line OTX TLH, read from
         the DDM (Digital Diagnostic Monitoring) 
        (Temperature = AV/256) (Unit =
         C)  <Help>  This measure gives 
        the laser temperature of the Line 
        OTX TLH
        "
	::= { pm1008dcpMesrotx1LaserTemperatureEntry 2 }


--- *********************************************************
---     TABLE for the pm1008dcpMesrotx1FreqDeviation articles
--- *********************************************************

pm1008dcpMesrotx1FreqDeviationTable OBJECT-TYPE
	SYNTAX  SEQUENCE OF Pm1008dcpMesrotx1FreqDeviationEntry
	MAX-ACCESS not-accessible
	STATUS current
	DESCRIPTION
        "
        List of pm1008dcpMesrotx1FreqDeviation 
        Article
        "
	::= { pm1008dcpMesrLine 226 }


pm1008dcpMesrotx1FreqDeviationEntry OBJECT-TYPE
	SYNTAX Pm1008dcpMesrotx1FreqDeviationEntry
	MAX-ACCESS not-accessible
	STATUS current
	DESCRIPTION
        "
        Row definition for the pm1008dcpMesrotx1FreqDeviation 
        table
        "
	INDEX   { pm1008dcpMesrotx1FreqDeviationIndex }
	::= { pm1008dcpMesrotx1FreqDeviationTable 1 }


Pm1008dcpMesrotx1FreqDeviationEntry ::=
	SEQUENCE {
	pm1008dcpMesrotx1FreqDeviationIndex
		INTEGER,
	pm1008dcpMesrotx1FreqDeviationPortn
		INTEGER 
	}


pm1008dcpMesrotx1FreqDeviationIndex OBJECT-TYPE
	SYNTAX  INTEGER(0..128)
	MAX-ACCESS  read-only
	STATUS current
	DESCRIPTION
        "
        Index definition for the pm1008dcpMesrotx1FreqDeviation 
        table
        "
	::= { pm1008dcpMesrotx1FreqDeviationEntry 1 }


pm1008dcpMesrotx1FreqDeviationPortn OBJECT-TYPE
	SYNTAX  INTEGER (0..65535)
	MAX-ACCESS read-only
	STATUS current
	DESCRIPTION
        "
        Line OTX TLH Frequency Deviation 
        :This OID gives the frequency deviation 
        of the Line OTX TLH, read from
         the DDM (Digital Diagnostic Monitoring) 
        (Deviation = (AV-32768)*100) (Unit 
        = MHz)  <Help>  This measure gives 
        the frequency deviation of the
         Line OTX TLH
        "
	::= { pm1008dcpMesrotx1FreqDeviationEntry 2 }


--- *********************************************************
---     TABLE for the pm1008dcpMesrotx1LaserWvlength articles
--- *********************************************************

pm1008dcpMesrotx1LaserWvlengthTable OBJECT-TYPE
	SYNTAX  SEQUENCE OF Pm1008dcpMesrotx1LaserWvlengthEntry
	MAX-ACCESS not-accessible
	STATUS current
	DESCRIPTION
        "
        List of pm1008dcpMesrotx1LaserWvlength 
        Article
        "
	::= { pm1008dcpMesrLine 227 }


pm1008dcpMesrotx1LaserWvlengthEntry OBJECT-TYPE
	SYNTAX Pm1008dcpMesrotx1LaserWvlengthEntry
	MAX-ACCESS not-accessible
	STATUS current
	DESCRIPTION
        "
        Row definition for the pm1008dcpMesrotx1LaserWvlength 
        table
        "
	INDEX   { pm1008dcpMesrotx1LaserWvlengthIndex }
	::= { pm1008dcpMesrotx1LaserWvlengthTable 1 }


Pm1008dcpMesrotx1LaserWvlengthEntry ::=
	SEQUENCE {
	pm1008dcpMesrotx1LaserWvlengthIndex
		INTEGER,
	pm1008dcpMesrotx1LaserWvlengthPortn
		INTEGER 
	}


pm1008dcpMesrotx1LaserWvlengthIndex OBJECT-TYPE
	SYNTAX  INTEGER(0..128)
	MAX-ACCESS  read-only
	STATUS current
	DESCRIPTION
        "
        Index definition for the pm1008dcpMesrotx1LaserWvlength 
        table
        "
	::= { pm1008dcpMesrotx1LaserWvlengthEntry 1 }


pm1008dcpMesrotx1LaserWvlengthPortn OBJECT-TYPE
	SYNTAX  INTEGER (0..65535)
	MAX-ACCESS read-only
	STATUS current
	DESCRIPTION
        "
        Line Optical Module Wavelength 
        :This OID gives the laser wavelength 
        of the Line OTX TLH, read from
         the DDM (Digital Diagnostic Monitoring) 
        (Wavelength=299792458/((193,100+(AV-32768 
        )*12,5)*10 3))  (Unit = nm)  <Help> 
         This measure gives the laser wavelength 
        of the Line OTX TLH
        "
	::= { pm1008dcpMesrotx1LaserWvlengthEntry 2 }







--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm1008dcpDwlrestartProcess OBJECT IDENTIFIER ::= { pm1008dcpDwlOther 0 }




pm1008dcpDwlColdRestartProcessed OBJECT-TYPE
	  SYNTAX EkiOnOff
	  MAX-ACCESS read-only
	  STATUS current
	  DESCRIPTION
        "
        Cold Restart :This OID indicates 
        that the module last restart was 
        a Cold RESTART
        "
	  ::= { pm1008dcpDwlrestartProcess 2 }



pm1008dcpDwlWarmRestartProcessed OBJECT-TYPE
	  SYNTAX EkiOnOff
	  MAX-ACCESS read-only
	  STATUS current
	  DESCRIPTION
        "
        Warm Restart :This OID indicates 
        that the module last restart was 
        a Warm RESTART
        "
	  ::= { pm1008dcpDwlrestartProcess 1 }



--- *****************************************************
---     LEAF for the swBanksUsed article
--- *****************************************************
pm1008dcpDwlswBanksUsed OBJECT IDENTIFIER ::= { pm1008dcpDwlOther 1 }




pm1008dcpDwlSwBank2Notempty OBJECT-TYPE
	  SYNTAX EkiOnOff
	  MAX-ACCESS read-only
	  STATUS current
	  DESCRIPTION
        "
        SW bank 2 loaded :This OID indicates 
        a software is loaded in SW bank 
        2  <Help>  This status indicates 
        if the SW bank 2 contains SW package
        "
	  ::= { pm1008dcpDwlswBanksUsed 6 }



pm1008dcpDwlSwBank1Notempty OBJECT-TYPE
	  SYNTAX EkiOnOff
	  MAX-ACCESS read-only
	  STATUS current
	  DESCRIPTION
        "
        SW bank 1 loaded :This OID indicates 
        a software is loaded in SW bank 
        1  <Help>  This status indicates 
        if the SW bank 1 contains SW package
        "
	  ::= { pm1008dcpDwlswBanksUsed 5 }



pm1008dcpDwlSwBank2Used OBJECT-TYPE
	  SYNTAX EkiOnOff
	  MAX-ACCESS read-only
	  STATUS current
	  DESCRIPTION
        "
        SW bank 2 active :This OID indicates 
        the module is working on SW bank 
        2  <Help>  This status indicates 
        if the SW bank 2 is active or standby
        "
	  ::= { pm1008dcpDwlswBanksUsed 2 }



pm1008dcpDwlSwBank1Used OBJECT-TYPE
	  SYNTAX EkiOnOff
	  MAX-ACCESS read-only
	  STATUS current
	  DESCRIPTION
        "
        SW bank 1 active :This OID indicates 
        the module is working on SW bank 
        1  <Help>  This status indicates 
        if the SW bank 1 is active or standby
        "
	  ::= { pm1008dcpDwlswBanksUsed 1 }



--- *****************************************************
---     LEAF for the gwBanksUsed article
--- *****************************************************
pm1008dcpDwlgwBanksUsed OBJECT IDENTIFIER ::= { pm1008dcpDwlOther 2 }




pm1008dcpDwlGwBank4Notempty OBJECT-TYPE
	  SYNTAX EkiOnOff
	  MAX-ACCESS read-only
	  STATUS current
	  DESCRIPTION
        "
        GW bank 4 loaded :This OID indicates 
        a gateware is loaded in GW bank 
        4
        "
	  ::= { pm1008dcpDwlgwBanksUsed 8 }



pm1008dcpDwlGwBank3Notempty OBJECT-TYPE
	  SYNTAX EkiOnOff
	  MAX-ACCESS read-only
	  STATUS current
	  DESCRIPTION
        "
        GW bank 3 loaded :This OID indicates 
        a gateware is loaded in GW bank 
        3  <Help>  This status indicates 
        if the GW bank 3 contains GW package
        "
	  ::= { pm1008dcpDwlgwBanksUsed 7 }



pm1008dcpDwlGwBank2Notempty OBJECT-TYPE
	  SYNTAX EkiOnOff
	  MAX-ACCESS read-only
	  STATUS current
	  DESCRIPTION
        "
        GW bank 2 loaded :This OID indicates 
        a gateware is loaded in GW bank 
        2
        "
	  ::= { pm1008dcpDwlgwBanksUsed 6 }



pm1008dcpDwlGwBank1Notempty OBJECT-TYPE
	  SYNTAX EkiOnOff
	  MAX-ACCESS read-only
	  STATUS current
	  DESCRIPTION
        "
        GW bank 1 loaded  :This OID indicates 
        a gateware is loaded in GW bank 
        1  <Help>  This status indicates 
        if the GW bank 1 contains GW package
        "
	  ::= { pm1008dcpDwlgwBanksUsed 5 }



pm1008dcpDwlGwBank4Used OBJECT-TYPE
	  SYNTAX EkiOnOff
	  MAX-ACCESS read-only
	  STATUS current
	  DESCRIPTION
        "
        GW bank 4 active  :This OID indicates 
        the module is working on GW bank 
        4
        "
	  ::= { pm1008dcpDwlgwBanksUsed 4 }



pm1008dcpDwlGwBank3Used OBJECT-TYPE
	  SYNTAX EkiOnOff
	  MAX-ACCESS read-only
	  STATUS current
	  DESCRIPTION
        "
        GW bank 3 active :This OID indicates 
        the module is working on GW bank 
        3  <Help>  This status indicates 
        if the GW bank 3 is active or standby
        "
	  ::= { pm1008dcpDwlgwBanksUsed 3 }



pm1008dcpDwlGwBank2Used OBJECT-TYPE
	  SYNTAX EkiOnOff
	  MAX-ACCESS read-only
	  STATUS current
	  DESCRIPTION
        "
        GW bank 2 active :This OID indicates 
        the module is working on GW bank 
        2
        "
	  ::= { pm1008dcpDwlgwBanksUsed 2 }



pm1008dcpDwlGwBank1Used OBJECT-TYPE
	  SYNTAX EkiOnOff
	  MAX-ACCESS read-only
	  STATUS current
	  DESCRIPTION
        "
        GW bank 1 active  :This OID indicates 
        the module is working on GW bank 
        1  <Help>  This status indicates 
        if the GW bank 1 is active or standby
        "
	  ::= { pm1008dcpDwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm1008dcpCfgAccessCAisCsf OBJECT IDENTIFIER ::= { pm1008dcpConfig 1 }



--- *****************************************************
---     LEAF for the table 0012
--- *****************************************************

pm1008dcpCfgClientcaiscsfTable OBJECT-TYPE
	SYNTAX  SEQUENCE OF Pm1008dcpCfgClientcaiscsfEntry
	MAX-ACCESS not-accessible
	STATUS current
	DESCRIPTION
        "
        List of  Article
        "
	::= { pm1008dcpCfgAccessCAisCsf 1 }


pm1008dcpCfgClientcaiscsfEntry OBJECT-TYPE
	SYNTAX Pm1008dcpCfgClientcaiscsfEntry
	MAX-ACCESS not-accessible
	STATUS current
	DESCRIPTION
        "
        Row definition for the accessCAisCsf 
        table
        "
	INDEX   { pm1008dcpCfgClientcaiscsfIndex }
	::= { pm1008dcpCfgClientcaiscsfTable 1 }


Pm1008dcpCfgClientcaiscsfEntry ::=
	SEQUENCE {
	pm1008dcpCfgClientcaiscsfIndex
		INTEGER,
	pm1008dcpCfgCAisModePortn
		Unsigned32,
	pm1008dcpCfgUpAccessioAlmPortn
		Unsigned32,
	pm1008dcpCfgUpMapperDeAlmPortn
		Unsigned32,
	pm1008dcpCfgDownAccessioAlmPortn
		Unsigned32,
	pm1008dcpCfgDownMapperDeAlmPortn
		Unsigned32,
	pm1008dcpCfgDownDfrmAlmPortn
		Unsigned32,
	pm1008dcpCfgDownLineSyncAlarmsPortn
		Unsigned32
	}


pm1008dcpCfgClientcaiscsfIndex OBJECT-TYPE
	SYNTAX  INTEGER(0..128)
	MAX-ACCESS  read-only
	STATUS current
	DESCRIPTION
        "
        Index definition for the clientcaiscsf 
        table
        "
	::= { pm1008dcpCfgClientcaiscsfEntry 1 }


pm1008dcpCfgCAisModePortn OBJECT-TYPE
	SYNTAX  Unsigned32 (0..65536)
	MAX-ACCESS read-write
	STATUS current
	DESCRIPTION
        "
        CAIS mode  on Client Port :This 
        register enables/disables port
          laser shutdown on CAIS insertion 
        condition
        "
	::= { pm1008dcpCfgClientcaiscsfEntry 3 }


pm1008dcpCfgUpAccessioAlmPortn OBJECT-TYPE
	SYNTAX  Unsigned32 (0..65536)
	MAX-ACCESS read-write
	STATUS current
	DESCRIPTION
        "
        CSF contributors on Client Port 
        :This register configures the contributors 
        to upstream CSF insertion on the 
        port.
        "
	::= { pm1008dcpCfgClientcaiscsfEntry 9 }


pm1008dcpCfgUpMapperDeAlmPortn OBJECT-TYPE
	SYNTAX  Unsigned32 (0..65536)
	MAX-ACCESS read-write
	STATUS current
	DESCRIPTION
        "
        CSF contributors on Client Port 
        :This register configures the contributors 
        to upstream CSF insertion on the 
        port.
        "
	::= { pm1008dcpCfgClientcaiscsfEntry 10 }


pm1008dcpCfgDownAccessioAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pm1008dcpCfgClientcaiscsfEntry 17 }


pm1008dcpCfgDownMapperDeAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pm1008dcpCfgClientcaiscsfEntry 18 }


pm1008dcpCfgDownDfrmAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pm1008dcpCfgClientcaiscsfEntry 19 }


pm1008dcpCfgDownLineSyncAlarmsPortn OBJECT-TYPE
	SYNTAX  Unsigned32 (0..65536)
	MAX-ACCESS read-write
	STATUS deprecated
	DESCRIPTION
        "
        CAIS contributors on Client Port 
        :This register configures the contributors 
        to downstream CAIS insertion on 
         port.
        "
	::= { pm1008dcpCfgClientcaiscsfEntry 20 }


--- *****************************************************
---     LEAF for the table Group startup
--- *****************************************************

pm1008dcpCfgStartup OBJECT IDENTIFIER ::= { pm1008dcpConfig 2 }



--- *****************************************************
---     LEAF for the table 2111
--- *****************************************************

pm1008dcpCfgClientStartupTable OBJECT-TYPE
	SYNTAX  SEQUENCE OF Pm1008dcpCfgClientStartupEntry
	MAX-ACCESS not-accessible
	STATUS current
	DESCRIPTION
        "
        List of  Article
        "
	::= { pm1008dcpCfgStartup 1 }


pm1008dcpCfgClientStartupEntry OBJECT-TYPE
	SYNTAX Pm1008dcpCfgClientStartupEntry
	MAX-ACCESS not-accessible
	STATUS current
	DESCRIPTION
        "
        Row definition for the startup 
        table
        "
	INDEX   { pm1008dcpCfgClientStartupIndex }
	::= { pm1008dcpCfgClientStartupTable 1 }


Pm1008dcpCfgClientStartupEntry ::=
	SEQUENCE {
	pm1008dcpCfgClientStartupIndex
		INTEGER,
	pm1008dcpCfgSystConfPortPortn
		Unsigned32,
	pm1008dcpCfgNetConfPortPortn
		Unsigned32,
	pm1008dcpCfgAdddropConfPortPortn
		Unsigned32
	}


pm1008dcpCfgClientStartupIndex OBJECT-TYPE
	SYNTAX  INTEGER(0..128)
	MAX-ACCESS  read-only
	STATUS current
	DESCRIPTION
        "
        Index definition for the clientStartup 
        table
        "
	::= { pm1008dcpCfgClientStartupEntry 1 }


pm1008dcpCfgSystConfPortPortn OBJECT-TYPE
	SYNTAX  Unsigned32 (0..65536)
	MAX-ACCESS read-write
	STATUS current
	DESCRIPTION
        "
        Default Settings on Client Port 
        :This  register configures the
         default initialisation settings 
        on the port.
        "
	::= { pm1008dcpCfgClientStartupEntry 3 }


pm1008dcpCfgNetConfPortPortn OBJECT-TYPE
	SYNTAX  Unsigned32 (0..65536)
	MAX-ACCESS read-write
	STATUS current
	DESCRIPTION
        "
        Default Protocol on Client Port 
        :This register configures the default 
        initialisation protocol on the
         port.
        "
	::= { pm1008dcpCfgClientStartupEntry 4 }


pm1008dcpCfgAdddropConfPortPortn OBJECT-TYPE
	SYNTAX  Unsigned32 (0..65536)
	MAX-ACCESS read-write
	STATUS deprecated
	DESCRIPTION
        "
        Default Add&Drop mode on Client 
        Port :This register configures
         the default Add&Drop mode on the 
        port.
        "
	::= { pm1008dcpCfgClientStartupEntry 5 }


--- *****************************************************
---     LEAF for the table 2191
--- *****************************************************

pm1008dcptablelineStartup OBJECT IDENTIFIER ::= { pm1008dcpCfgStartup 2 }



pm1008dcpCfgsystConfLine1 OBJECT-TYPE
	  SYNTAX Unsigned32 (0..65536)
	  MAX-ACCESS read-write
	  STATUS current
	  DESCRIPTION
        "
        Default Settings on Line 1 :This 
        register configures the default 
        initialisation settings on Line 
        port 1.
        "
	  ::= { pm1008dcptablelineStartup 2 }



pm1008dcpCfglineOptions1 OBJECT-TYPE
	  SYNTAX Unsigned32 (0..65536)
	  MAX-ACCESS read-write
	  STATUS current
	  DESCRIPTION
        "
        Default Options on Active Line 
        Port :This register configures
         the default options on the active 
        line port
        "
	  ::= { pm1008dcptablelineStartup 5 }



pm1008dcpCfgsystConfLine2 OBJECT-TYPE
	  SYNTAX Unsigned32 (0..65536)
	  MAX-ACCESS read-write
	  STATUS current
	  DESCRIPTION
        "
        Default Settings on Line 2 :This 
        register configures the default 
        initialisation settings on Line 
        port 2.
        "
	  ::= { pm1008dcptablelineStartup 6 }



pm1008dcpCfglineSelection OBJECT-TYPE
	  SYNTAX Unsigned32 (0..65536)
	  MAX-ACCESS read-write
	  STATUS current
	  DESCRIPTION
        "
        Default Settings of active line 
        :This  register configures the
         start up active line.
        "
	  ::= { pm1008dcptablelineStartup 7 }



pm1008dcpCfglineOptions2 OBJECT-TYPE
	  SYNTAX Unsigned32 (0..65536)
	  MAX-ACCESS read-write
	  STATUS deprecated
	  DESCRIPTION
        "
        Default Options on Active Line 
        Port :This register configures
         the default options on the active 
        line port
        "
	  ::= { pm1008dcptablelineStartup 9 }



--- *****************************************************
---     LEAF for the table 21AB
--- *****************************************************

pm1008dcpCfgXfpTable OBJECT-TYPE
	SYNTAX  SEQUENCE OF Pm1008dcpCfgXfpEntry
	MAX-ACCESS not-accessible
	STATUS current
	DESCRIPTION
        "
        List of  Article
        "
	::= { pm1008dcpCfgStartup 3 }


pm1008dcpCfgXfpEntry OBJECT-TYPE
	SYNTAX Pm1008dcpCfgXfpEntry
	MAX-ACCESS not-accessible
	STATUS current
	DESCRIPTION
        "
        Row definition for the startup 
        table
        "
	INDEX   { pm1008dcpCfgXfpIndex }
	::= { pm1008dcpCfgXfpTable 1 }


Pm1008dcpCfgXfpEntry ::=
	SEQUENCE {
	pm1008dcpCfgXfpIndex
		INTEGER,
	pm1008dcpCfgSystConfXfpPortn
		Unsigned32,
	pm1008dcpCfgDataRateConfXfpPortn
		Unsigned32
	}


pm1008dcpCfgXfpIndex OBJECT-TYPE
	SYNTAX  INTEGER(0..128)
	MAX-ACCESS  read-only
	STATUS current
	DESCRIPTION
        "
        Index definition for the xfp table
        "
	::= { pm1008dcpCfgXfpEntry 1 }


pm1008dcpCfgSystConfXfpPortn OBJECT-TYPE
	SYNTAX  Unsigned32 (0..65536)
	MAX-ACCESS read-write
	STATUS current
	DESCRIPTION
        "
        Default settings on XFP Port :This 
        register configures the default 
        initialisation settings on XFP
         port.
        "
	::= { pm1008dcpCfgXfpEntry 3 }


pm1008dcpCfgDataRateConfXfpPortn OBJECT-TYPE
	SYNTAX  Unsigned32 (0..65536)
	MAX-ACCESS read-write
	STATUS deprecated
	DESCRIPTION
        "
        :
        "
	::= { pm1008dcpCfgXfpEntry 4 }


--- *****************************************************
---     LEAF for the table 25A8
--- *****************************************************

pm1008dcpCfgOtxtlhTable OBJECT-TYPE
	SYNTAX  SEQUENCE OF Pm1008dcpCfgOtxtlhEntry
	MAX-ACCESS not-accessible
	STATUS current
	DESCRIPTION
        "
        List of  Article
        "
	::= { pm1008dcpCfgStartup 4 }


pm1008dcpCfgOtxtlhEntry OBJECT-TYPE
	SYNTAX Pm1008dcpCfgOtxtlhEntry
	MAX-ACCESS not-accessible
	STATUS current
	DESCRIPTION
        "
        Row definition for the startup 
        table
        "
	INDEX   { pm1008dcpCfgOtxtlhIndex }
	::= { pm1008dcpCfgOtxtlhTable 1 }


Pm1008dcpCfgOtxtlhEntry ::=
	SEQUENCE {
	pm1008dcpCfgOtxtlhIndex
		INTEGER,
	pm1008dcpCfgNuPortn
		Unsigned32,
	pm1008dcpCfgLineDitherRatePortn
		Unsigned32,
	pm1008dcpCfgLineDitherFhzPortn
		Unsigned32,
	pm1008dcpCfgLinePwrLaserPortn
		Unsigned32,
	pm1008dcpCfgLineFCurrentPortn
		Unsigned32,
	pm1008dcpCfgLineGridCurrentPortn
		Unsigned32,
	pm1008dcpCfgFPortn
		Unsigned32,
	pm1008dcpCfgReservedPortn
		Unsigned32,
	pm1008dcpCfgLinePhotodiodeModePortn
		Unsigned32,
	pm1008dcpCfgLinePhotodiodeValuePortn
		Unsigned32
	}


pm1008dcpCfgOtxtlhIndex OBJECT-TYPE
	SYNTAX  INTEGER(0..128)
	MAX-ACCESS  read-only
	STATUS current
	DESCRIPTION
        "
        Index definition for the otxtlh 
        table
        "
	::= { pm1008dcpCfgOtxtlhEntry 1 }


pm1008dcpCfgNuPortn OBJECT-TYPE
	SYNTAX  Unsigned32 (0..65536)
	MAX-ACCESS read-write
	STATUS deprecated
	DESCRIPTION
        "
        :
        "
	::= { pm1008dcpCfgOtxtlhEntry 3 }


pm1008dcpCfgLineDitherRatePortn OBJECT-TYPE
	SYNTAX  Unsigned32 (0..65536)
	MAX-ACCESS read-write
	STATUS current
	DESCRIPTION
        "
        Default Line OTX TLH FM amplitude 
        :This register configures the start-up 
        width of the frequency modulation 
        of the Line OTX TLH
        "
	::= { pm1008dcpCfgOtxtlhEntry 4 }


pm1008dcpCfgLineDitherFhzPortn OBJECT-TYPE
	SYNTAX  Unsigned32 (0..65536)
	MAX-ACCESS read-write
	STATUS current
	DESCRIPTION
        "
        Default Line OTX TLH FM frequency 
        :This register configures the start-up 
        frequency of the frequency modulation 
        of the Line OTX TLH
        "
	::= { pm1008dcpCfgOtxtlhEntry 5 }


pm1008dcpCfgLinePwrLaserPortn OBJECT-TYPE
	SYNTAX  Unsigned32 (0..65536)
	MAX-ACCESS read-write
	STATUS current
	DESCRIPTION
        "
        Defaut Line OTX TLH output Power 
        :This register configures the start-up 
        output power of the Line OTX TLH 
         (Unit = dBm)
        "
	::= { pm1008dcpCfgOtxtlhEntry 6 }


pm1008dcpCfgLineFCurrentPortn OBJECT-TYPE
	SYNTAX  Unsigned32 (0..65536)
	MAX-ACCESS read-write
	STATUS current
	DESCRIPTION
        "
        Default Line OTX TLH Channel :This 
        register configures the start-up 
        laser channel of the Line OTX TLH
        "
	::= { pm1008dcpCfgOtxtlhEntry 7 }


pm1008dcpCfgLineGridCurrentPortn OBJECT-TYPE
	SYNTAX  Unsigned32 (0..65536)
	MAX-ACCESS read-write
	STATUS current
	DESCRIPTION
        "
        Default Line OTX TLH Grid :This 
        register configures the start-up 
        laser grid of the Line OTX TLH
        "
	::= { pm1008dcpCfgOtxtlhEntry 8 }


pm1008dcpCfgFPortn OBJECT-TYPE
	SYNTAX  Unsigned32 (0..65536)
	MAX-ACCESS read-write
	STATUS current
	DESCRIPTION
        "
        Default Line OTX TLH lowest Freq 
        :This register configures the start-up 
        lowest frequency supported on the 
        Line OTX TLH
        "
	::= { pm1008dcpCfgOtxtlhEntry 9 }


pm1008dcpCfgReservedPortn OBJECT-TYPE
	SYNTAX  Unsigned32 (0..65536)
	MAX-ACCESS read-write
	STATUS deprecated
	DESCRIPTION
        "
        :
        "
	::= { pm1008dcpCfgOtxtlhEntry 10 }


pm1008dcpCfgLinePhotodiodeModePortn OBJECT-TYPE
	SYNTAX  Unsigned32 (0..65536)
	MAX-ACCESS read-write
	STATUS current
	DESCRIPTION
        "
        Default Line OTX TLH APD mode
         :This register configures the
         start-up APD mode of the Line
         OTX TLH
        "
	::= { pm1008dcpCfgOtxtlhEntry 11 }


pm1008dcpCfgLinePhotodiodeValuePortn OBJECT-TYPE
	SYNTAX  Unsigned32 (0..65536)
	MAX-ACCESS read-write
	STATUS current
	DESCRIPTION
        "
        Default Line OTX TLH APD atten. 
        :This register configures the start-up 
        APD attenuation on the Line OTX 
        TLH
        "
	::= { pm1008dcpCfgOtxtlhEntry 12 }


--- *****************************************************
---     LEAF for the table Group other
--- *****************************************************

pm1008dcpCfgOther OBJECT IDENTIFIER ::= { pm1008dcpConfig 3 }



--- *****************************************************
---     LEAF for the table 2300
--- *****************************************************

pm1008dcptablemoduleOther OBJECT IDENTIFIER ::= { pm1008dcpCfgOther 1 }



pm1008dcpCfgmode OBJECT-TYPE
	  SYNTAX Unsigned32 (0..65536)
	  MAX-ACCESS read-write
	  STATUS current
	  DESCRIPTION
        "
        Default settings on Module :This 
        register selects the DCC  configuration 
        of the PM
        "
	  ::= { pm1008dcptablemoduleOther 2 }



pm1008dcpCfgadddropTsPairMode1 OBJECT-TYPE
	  SYNTAX Unsigned32 (0..65536)
	  MAX-ACCESS read-write
	  STATUS current
	  DESCRIPTION
        "
        Default settings on TS Group Mode 
        :This register selects selects
         the mode on the group of clients
        "
	  ::= { pm1008dcptablemoduleOther 3 }



pm1008dcpCfgadddropTsPairMode2 OBJECT-TYPE
	  SYNTAX Unsigned32 (0..65536)
	  MAX-ACCESS read-write
	  STATUS current
	  DESCRIPTION
        "
        Default settings on TS Group Mode 
        :This register selects selects
         the mode on the group of clients
        "
	  ::= { pm1008dcptablemoduleOther 4 }



pm1008dcpCfgadddropTsPairMode3 OBJECT-TYPE
	  SYNTAX Unsigned32 (0..65536)
	  MAX-ACCESS read-write
	  STATUS current
	  DESCRIPTION
        "
        Default settings on TS Group Mode 
        :This register selects selects
         the mode on the group of clients
        "
	  ::= { pm1008dcptablemoduleOther 5 }



pm1008dcpCfgadddropTsPairMode4 OBJECT-TYPE
	  SYNTAX Unsigned32 (0..65536)
	  MAX-ACCESS read-write
	  STATUS current
	  DESCRIPTION
        "
        Default settings on TS Group Mode 
        :This register selects selects
         the mode on the group of clients
        "
	  ::= { pm1008dcptablemoduleOther 6 }



--- *****************************************************
---     LEAF for the table Group labels
--- *****************************************************

pm1008dcpCfgLabels OBJECT IDENTIFIER ::= { pm1008dcpConfig 4 }



--- *****************************************************
---     LEAF for the table NO_VALUE
--- *****************************************************

pm1008dcpCfgLabelclientTable OBJECT-TYPE
	SYNTAX  SEQUENCE OF Pm1008dcpCfgLabelclientEntry
	MAX-ACCESS not-accessible
	STATUS current
	DESCRIPTION
        "
        List of  Article
        "
	::= { pm1008dcpCfgLabels 1 }


pm1008dcpCfgLabelclientEntry OBJECT-TYPE
	SYNTAX Pm1008dcpCfgLabelclientEntry
	MAX-ACCESS not-accessible
	STATUS current
	DESCRIPTION
        "
        Row definition for the labels
         table
        "
	INDEX   { pm1008dcpCfgLabelclientIndex }
	::= { pm1008dcpCfgLabelclientTable 1 }


Pm1008dcpCfgLabelclientEntry ::=
	SEQUENCE {
	pm1008dcpCfgLabelclientIndex
		INTEGER,
	pm1008dcpCfgLabelclientPortn
		DisplayString
	}


pm1008dcpCfgLabelclientIndex OBJECT-TYPE
	SYNTAX  INTEGER(0..128)
	MAX-ACCESS  read-only
	STATUS current
	DESCRIPTION
        "
        Index definition for the labelclient 
        table
        "
	::= { pm1008dcpCfgLabelclientEntry 1 }


pm1008dcpCfgLabelclientPortn OBJECT-TYPE
	SYNTAX  DisplayString( SIZE(1..16))
	MAX-ACCESS read-write
	STATUS current
	DESCRIPTION
        "
        Default settings on the label
         of the Ports :These registers
         configures the default initialisation 
        settings of the labels of the ports.
        "
	::= { pm1008dcpCfgLabelclientEntry 3 }


--- *****************************************************
---     LEAF for the table NO_VALUE
--- *****************************************************

pm1008dcpCfgLabellineTable OBJECT-TYPE
	SYNTAX  SEQUENCE OF Pm1008dcpCfgLabellineEntry
	MAX-ACCESS not-accessible
	STATUS current
	DESCRIPTION
        "
        List of  Article
        "
	::= { pm1008dcpCfgLabels 2 }


pm1008dcpCfgLabellineEntry OBJECT-TYPE
	SYNTAX Pm1008dcpCfgLabellineEntry
	MAX-ACCESS not-accessible
	STATUS current
	DESCRIPTION
        "
        Row definition for the labels
         table
        "
	INDEX   { pm1008dcpCfgLabellineIndex }
	::= { pm1008dcpCfgLabellineTable 1 }


Pm1008dcpCfgLabellineEntry ::=
	SEQUENCE {
	pm1008dcpCfgLabellineIndex
		INTEGER,
	pm1008dcpCfgLabellinePortn
		DisplayString
	}


pm1008dcpCfgLabellineIndex OBJECT-TYPE
	SYNTAX  INTEGER(0..128)
	MAX-ACCESS  read-only
	STATUS current
	DESCRIPTION
        "
        Index definition for the labelline 
        table
        "
	::= { pm1008dcpCfgLabellineEntry 1 }


pm1008dcpCfgLabellinePortn OBJECT-TYPE
	SYNTAX  DisplayString( SIZE(1..16))
	MAX-ACCESS read-write
	STATUS current
	DESCRIPTION
        "
        Default settings on the label
         of the lines :These registers
         configures the default initialisation 
        settings of the labels of the lines.
        "
	::= { pm1008dcpCfgLabellineEntry 3 }


--- *****************************************************
---     LEAF for the table Group startuptablefive
--- *****************************************************

pm1008dcpCfgStartuptablefive OBJECT IDENTIFIER ::= { pm1008dcpConfig 5 }



--- *****************************************************
---     LEAF for the table 0005
--- *****************************************************

pm1008dcpCfgOtxtlhcapabilitiesTable OBJECT-TYPE
	SYNTAX  SEQUENCE OF Pm1008dcpCfgOtxtlhcapabilitiesEntry
	MAX-ACCESS not-accessible
	STATUS current
	DESCRIPTION
        "
        List of  Article
        "
	::= { pm1008dcpCfgStartuptablefive 1 }


pm1008dcpCfgOtxtlhcapabilitiesEntry OBJECT-TYPE
	SYNTAX Pm1008dcpCfgOtxtlhcapabilitiesEntry
	MAX-ACCESS not-accessible
	STATUS current
	DESCRIPTION
        "
        Row definition for the startuptablefive 
        table
        "
	INDEX   { pm1008dcpCfgOtxtlhcapabilitiesIndex }
	::= { pm1008dcpCfgOtxtlhcapabilitiesTable 1 }


Pm1008dcpCfgOtxtlhcapabilitiesEntry ::=
	SEQUENCE {
	pm1008dcpCfgOtxtlhcapabilitiesIndex
		INTEGER,
	pm1008dcpCfgComponentTypePortn
		Unsigned32,
	pm1008dcpCfgMiscellaneousPortn
		Unsigned32,
	pm1008dcpCfgFirstChannelPortn
		Unsigned32,
	pm1008dcpCfgLastChannelPortn
		Unsigned32,
	pm1008dcpCfgGridPortn
		Unsigned32
	}


pm1008dcpCfgOtxtlhcapabilitiesIndex OBJECT-TYPE
	SYNTAX  INTEGER(0..128)
	MAX-ACCESS  read-only
	STATUS current
	DESCRIPTION
        "
        Index definition for the otxtlhcapabilities 
        table
        "
	::= { pm1008dcpCfgOtxtlhcapabilitiesEntry 1 }


pm1008dcpCfgComponentTypePortn OBJECT-TYPE
	SYNTAX  Unsigned32 (0..65536)
	MAX-ACCESS read-only
	STATUS current
	DESCRIPTION
        "
        Component parameters :This OID 
        defines the component parameters
        "
	::= { pm1008dcpCfgOtxtlhcapabilitiesEntry 3 }


pm1008dcpCfgMiscellaneousPortn OBJECT-TYPE
	SYNTAX  Unsigned32 (0..65536)
	MAX-ACCESS read-only
	STATUS current
	DESCRIPTION
        "
        Miscellaneous default settings 
        :This OID defines the miscellaneous 
        parameters
        "
	::= { pm1008dcpCfgOtxtlhcapabilitiesEntry 4 }


pm1008dcpCfgFirstChannelPortn OBJECT-TYPE
	SYNTAX  Unsigned32 (0..65536)
	MAX-ACCESS read-only
	STATUS current
	DESCRIPTION
        "
        Number of the first channel of 
        the component :This OID defines 
        the first channel number of the 
        PM
        "
	::= { pm1008dcpCfgOtxtlhcapabilitiesEntry 5 }


pm1008dcpCfgLastChannelPortn OBJECT-TYPE
	SYNTAX  Unsigned32 (0..65536)
	MAX-ACCESS read-only
	STATUS current
	DESCRIPTION
        "
        Number of the last channel of
         the component :This OID defines 
        the last channel number of the
         PM
        "
	::= { pm1008dcpCfgOtxtlhcapabilitiesEntry 6 }


pm1008dcpCfgGridPortn OBJECT-TYPE
	SYNTAX  Unsigned32 (0..65536)
	MAX-ACCESS read-only
	STATUS current
	DESCRIPTION
        "
        Grid value of the component :This 
        OID defines the grid of the PM
        "
	::= { pm1008dcpCfgOtxtlhcapabilitiesEntry 7 }



pm1008dcpCfgWriteConfiguration  OBJECT-TYPE
	SYNTAX EkiOnOff
	MAX-ACCESS read-write
	STATUS current
	DESCRIPTION
	"Write configuration to module:This OID 
	 writes the complete configuration to the module"
	::= { pm1008dcpConfig 257 }






--- *****************************************************
---     TRAP OBJECTS
--- *****************************************************

pm1008dcptrapPortNumber OBJECT-TYPE
	SYNTAX INTEGER(1..64)
	MAX-ACCESS read-only
	STATUS current
	DESCRIPTION
	"Last port which generates a trap"
	::= { pm1008dcptraps 2 }

pm1008dcptrapLineNumber OBJECT-TYPE
	SYNTAX INTEGER(1..64)
	MAX-ACCESS read-only
	STATUS current
	DESCRIPTION
	"Last Line which generates a trap"
	::= { pm1008dcptraps 3 }

pm1008dcptrapBoardNumber OBJECT-TYPE
	SYNTAX INTEGER(1..64)
	MAX-ACCESS read-only
	STATUS current
	DESCRIPTION
	"Last module which generates a trap"
	::= { pm1008dcptraps 4 }







--- *****************************************************
---     LINE TRAPS
--- *****************************************************

pm1008dcpLineTrapNotUrgentGoesOn NOTIFICATION-TYPE
	OBJECTS {pm1008dcpAlmLineDdmWarningPortn, pm1008dcptrapLineNumber, pm1008dcptrapBoardNumber}
	STATUS current
	--&FILTNAME    "PM1008DC Line Not Urgent ON"
	--&ACTIONS     { log, minor }
	--&MATCH       { pm1008dcpAlmLineDdmWarningPortn "on", pm1008dcptrapLineNumber "$2", pm1008dcptrapBoardNumber "$3"}
	--&MESG        "DDM Warning appears on Line Port $2 of PM1008DC in Slot $3 ($A)"
	DESCRIPTION "Not urgent Line default is activated"
	::= { pm1008dcptraps 30 }

pm1008dcpLineTrapNotUrgentGoesOff NOTIFICATION-TYPE
	OBJECTS {pm1008dcpAlmLineDdmWarningPortn, pm1008dcptrapLineNumber, pm1008dcptrapBoardNumber}
	STATUS current
	--&FILTNAME    "PM1008DC Line Not Urgent OFF"
	--&ACTIONS     { log, normal }
	--&CLEARS      { "PM1008DC Line Not Urgent ON" }
	--&MATCH       { pm1008dcpAlmLineDdmWarningPortn "on", pm1008dcptrapLineNumber "$2", pm1008dcptrapBoardNumber "$3"}
	--&MESG        "DDM Warning disappears on Line Port $2 of PM1008DC in Slot $3 ($A)"
	DESCRIPTION "Not urgent Line default disappeared"
	::= { pm1008dcptraps 31 }

pm1008dcpLineTrapUrgentGoesOn NOTIFICATION-TYPE
	OBJECTS {pm1008dcpAlmLineDdmAlmPortn, pm1008dcptrapLineNumber, pm1008dcptrapBoardNumber}
	STATUS current
	--&FILTNAME    "PM1008DC Line Urgent ON"
	--&ACTIONS     { log, major }
	--&MATCH       { pm1008dcpAlmLineDdmAlmPortn "on", pm1008dcptrapLineNumber "$2", pm1008dcptrapBoardNumber "$3"}
	--&MESG        "DDM Alarm appears on Line Port $2 of PM1008DC in Slot $3 ($A)"
	DESCRIPTION "Urgent Line default is activated"
	::= { pm1008dcptraps 32 }

pm1008dcpLineTrapUrgentGoesOff NOTIFICATION-TYPE
	OBJECTS {pm1008dcpAlmLineDdmAlmPortn, pm1008dcptrapLineNumber, pm1008dcptrapBoardNumber}
	STATUS current
	--&FILTNAME    "PM1008DC Line Urgent OFF"
	--&ACTIONS     { log, normal }
	--&CLEARS      { "PM1008DC Line Urgent ON" }
	--&MATCH       { pm1008dcpAlmLineDdmAlmPortn "on", pm1008dcptrapLineNumber "$2", pm1008dcptrapBoardNumber "$3"}
	--&MESG        "DDM Alarm disappears on Line Port $2 of PM1008DC in Slot $3 ($A)"
	DESCRIPTION "Urgent Line default disappeared"
	::= { pm1008dcptraps 33 }

pm1008dcpLineTrapCritGoesOn NOTIFICATION-TYPE
	OBJECTS {pm1008dcpAlmLineFailPortn , pm1008dcpAlmLineHwFailPortn , pm1008dcptrapLineNumber, pm1008dcptrapBoardNumber}
	STATUS current
	--&FILTNAME    "PM1008DC Line Fail ON"
	--&ACTIONS     { log, critical }
	--&MATCH       { pm1008dcpAlmLineFailPortn "on", pm1008dcpAlmLineHwFailPortn "*", pm1008dcptrapLineNumber "$3", pm1008dcptrapBoardNumber "$4"}
	--&MESG        "Line Port $3 Down on PM1008DC in Slot $4 ($A)"
	
	--&FILTNAME    "PM1008DC Line HW Fail ON (Hidden)"
	--&ACTIONS     { info }
	--&MATCH       { pm1008dcpAlmLineFailPortn "*", pm1008dcpAlmLineHwFailPortn "on", pm1008dcptrapLineNumber "$3", pm1008dcptrapBoardNumber "$4"}
	--&MESG        "Line Port $3 Down on PM1008DC in Slot $4 ($A)"
	DESCRIPTION "Critical Line default is activated"
	::= { pm1008dcptraps 34 }

pm1008dcpLineTrapCritGoesOff NOTIFICATION-TYPE
	OBJECTS {pm1008dcpAlmLineFailPortn , pm1008dcpAlmLineHwFailPortn , pm1008dcptrapLineNumber, pm1008dcptrapBoardNumber}
	STATUS current
	--&FILTNAME    "PM1008DC Line Fail OFF"
	--&ACTIONS     { log,  normal }
	--&CLEARS      { "PM1008DC Line Fail ON" }
	--&MATCH       { pm1008dcpAlmLineFailPortn "on", pm1008dcpAlmLineHwFailPortn "*", pm1008dcptrapLineNumber "$3", pm1008dcptrapBoardNumber "$4"}
	--&MESG        "Line Port $3 Up on PM1008DC in Slot $4 ($A)"

	--&FILTNAME    "PM1008DC Line HW Fail OFF (Hidden)"
	--&ACTIONS     { info }
	--&MATCH       { pm1008dcpAlmLineFailPortn "*", pm1008dcpAlmLineHwFailPortn "on", pm1008dcptrapLineNumber "$3", pm1008dcptrapBoardNumber "$4"}
	--&MESG        "Line Port $3 Up on PM1008DC in Slot $4 ($A)"
	DESCRIPTION "Critical Line default disappeared"
	::= { pm1008dcptraps 35 }






--- *****************************************************
---     CLIENT TRAPS
--- *****************************************************

pm1008dcpClientTrapNotUrgentGoesOn NOTIFICATION-TYPE
	OBJECTS {pm1008dcpAlmSfpDdmWarningPortn, pm1008dcptrapPortNumber, pm1008dcptrapBoardNumber}
	STATUS current
	--&FILTNAME    "PM1008DC Client Not Urgent ON"
	--&ACTIONS     { log, minor }
	--&MATCH       { pm1008dcpAlmSfpDdmWarningPortn "on", pm1008dcptrapPortNumber "$2", pm1008dcptrapBoardNumber "$3"}
	--&MESG        "DDM Warning appears on Client Port $2 of PM1008DC in Slot $3 ($A)"
	DESCRIPTION "Not urgent client default is activated"
	::= { pm1008dcptraps 40 }

pm1008dcpClientTrapNotUrgentGoesOff NOTIFICATION-TYPE
	OBJECTS {pm1008dcpAlmSfpDdmWarningPortn, pm1008dcptrapPortNumber, pm1008dcptrapBoardNumber}
	STATUS current
	--&FILTNAME    "PM1008DC Client Not Urgent OFF"
	--&ACTIONS     { log, normal }
	--&CLEARS      { "PM1008DC Client Not Urgent ON" }
	--&MATCH       { pm1008dcpAlmSfpDdmWarningPortn "on", pm1008dcptrapPortNumber "$2", pm1008dcptrapBoardNumber "$3"}
	--&MESG        "DDM Warning appears on Client Port $2 of PM1008DC in Slot $3 ($A)"
	DESCRIPTION "Not urgent client default disappeared"
	::= { pm1008dcptraps 41 }

pm1008dcpClientTrapUrgentGoesOn NOTIFICATION-TYPE
	OBJECTS {pm1008dcpAlmSfpDdmAlmPortn, pm1008dcptrapPortNumber, pm1008dcptrapBoardNumber}
	STATUS current
	--&FILTNAME    "PM1008DC Client Urgent ON"
	--&ACTIONS     { log, major }
	--&MATCH       { pm1008dcpAlmSfpDdmAlmPortn "on", pm1008dcptrapPortNumber "$2", pm1008dcptrapBoardNumber "$3"}
	--&MESG        "DDM Alarm appears on Client Port $2 of PM1008DC in Slot $3 ($A)"
	DESCRIPTION "Urgent client default is activated"
	::= { pm1008dcptraps 42 }

pm1008dcpClientTrapUrgentGoesOff NOTIFICATION-TYPE
	OBJECTS {pm1008dcpAlmSfpDdmAlmPortn, pm1008dcptrapPortNumber, pm1008dcptrapBoardNumber}
	STATUS current
	--&FILTNAME    "PM1008DC Client Urgent OFF"
	--&ACTIONS     { log, normal }
	--&CLEARS      { "PM1008DC Client Urgent ON" }
	--&MATCH       { pm1008dcpAlmSfpDdmAlmPortn "on", pm1008dcptrapPortNumber "$2", pm1008dcptrapBoardNumber "$3"}
	--&MESG        "DDM Alarm disappears on Client Port $2 of PM1008DC in Slot $3 ($A)"
	DESCRIPTION "Urgent client default disappeared"
	::= { pm1008dcptraps 43 }

pm1008dcpClientTrapCritGoesOn NOTIFICATION-TYPE
	OBJECTS {pm1008dcpAlmFailAccPortn, pm1008dcpAlmHwFailAccPortn, pm1008dcptrapPortNumber, pm1008dcptrapBoardNumber}
	STATUS current
	--&FILTNAME    "PM1008DC Client Fail ON"
	--&ACTIONS     { log, critical }
	--&MATCH       { pm1008dcpAlmFailAccPortn "on", pm1008dcpAlmHwFailAccPortn "*", pm1008dcptrapPortNumber "$3", pm1008dcptrapBoardNumber "$4"}
	--&MESG        "Client Port $3 Down on PM1008DC in Slot $4 ($A)"
	
	--&FILTNAME    "PM1008DC Client HW Fail ON (Hidden)"
	--&ACTIONS     { info }
	--&MATCH       { pm1008dcpAlmFailAccPortn "*", pm1008dcpAlmHwFailAccPortn "on", pm1008dcptrapPortNumber "$3", pm1008dcptrapBoardNumber "$4"}
	--&MESG        "Client Port $3 Down on PM1008DC in Slot $4 ($A)"
	DESCRIPTION "Critical client default is activated"
	::= { pm1008dcptraps 44 }

pm1008dcpClientTrapCritGoesOff NOTIFICATION-TYPE
	OBJECTS {pm1008dcpAlmFailAccPortn, pm1008dcpAlmHwFailAccPortn, pm1008dcptrapPortNumber, pm1008dcptrapBoardNumber}
	STATUS current
	--&FILTNAME    "PM1008DC Client Fail OFF"
	--&ACTIONS     { log, normal }
	--&CLEARS      { "PM1008DC Client Fail ON" }
	--&MATCH       { pm1008dcpAlmFailAccPortn "on", pm1008dcpAlmHwFailAccPortn "*", pm1008dcptrapPortNumber "$3", pm1008dcptrapBoardNumber "$4"}
	--&MESG        "Client Port $3 Up on PM1008DC in Slot $4 ($A)"
	
	--&FILTNAME    "PM1008DC Client HW Fail OFF (Hidden)"
	--&ACTIONS     { info }
	--&MATCH       { pm1008dcpAlmFailAccPortn "*", pm1008dcpAlmHwFailAccPortn "on", pm1008dcptrapPortNumber "$3", pm1008dcptrapBoardNumber "$4"}
	--&MESG        "Client Port $3 Up on PM1008DC in Slot $4 ($A)"
	DESCRIPTION "Critical client default disappeared"
	::= { pm1008dcptraps 45 }






--- *****************************************************
---     HW TRAPS
--- *****************************************************

pm1008dcpPowerTrapUrgentGoesOn NOTIFICATION-TYPE
	OBJECTS {pm1008dcpAlmDefFuseB, pm1008dcpAlmDefFuseA , pm1008dcptrapBoardNumber}
	STATUS current
	--&FILTNAME    "PM1008DC Fuse A Fail ON"
	--&ACTIONS     { log, major }
	--&MATCH       { pm1008dcpAlmDefFuseB "*", pm1008dcpAlmDefFuseA "on", pm1008dcptrapBoardNumber "$3"}
	--&MESG        "Power Input A Fail on PM1008DC in Slot $3 ($A)"

	--&FILTNAME    "PM1008DC Fuse B Fail ON"
	--&ACTIONS     { log, major }
	--&MATCH       { pm1008dcpAlmDefFuseB "on", pm1008dcpAlmDefFuseA "*", pm1008dcptrapBoardNumber "$3"}
	--&MESG        "Power Input B Fail on PM1008DC in Slot $3 ($A)"
	DESCRIPTION "Urgent power supply default is activated"
	::= { pm1008dcptraps 50 }

pm1008dcpPowerTrapUrgentGoesOff NOTIFICATION-TYPE
	OBJECTS {pm1008dcpAlmDefFuseB, pm1008dcpAlmDefFuseA , pm1008dcptrapBoardNumber}
	STATUS current
	--&FILTNAME    "PM1008DC Fuse A&B Fail OFF"
	--&ACTIONS     { log, normal}
	--&CLEARS      { "PM1008DC Fuse A Fail ON", "PM1008DC Fuse B Fail ON" }
	--&MATCH       { pm1008dcpAlmDefFuseB "on", pm1008dcpAlmDefFuseA "on", pm1008dcptrapBoardNumber "$3"}
	--&MESG        "Power Inputs A and B Present on PM1008DC in Slot $3 ($A)"
	DESCRIPTION "Urgent power supply default disappeared"
	::= { pm1008dcptraps 51 }






END
