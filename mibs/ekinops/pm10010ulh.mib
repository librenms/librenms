-- *****************************************************************
-- EKINOPS-Pm10010ulh.TXT:  MIB
--
--MIB Part Number:3MI00042AAAB
--MIB Version:01
--
-- Copyright (c) 2017 by Ekinops
-- All rights reserved.
-- 
-- *****************************************************************

EKINOPS-Pm10010ulh-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress                
        		FROM SNMPv2-SMI
 	TEXTUAL-CONVENTION,
	DisplayString
                FROM SNMPv2-TC;

modulePm10010ulh MODULE-IDENTITY
        LAST-UPDATED "201703310000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.fr"
        DESCRIPTION
          "Creation."

	REVISION "201610100000Z"
	DESCRIPTION
	  "Creation for PM10010ULH"
	REVISION "201703310000Z"
	DESCRIPTION
	  "Module modes"
        ::= { ekinops 80 }



--- *****************************************************
---     LEAF LEVEL 2
--- *****************************************************


pm10010ulhalarms OBJECT IDENTIFIER ::= { modulePm10010ulh 2 }	
pm10010ulhAlmOther OBJECT IDENTIFIER ::= { pm10010ulhalarms 1 }
pm10010ulhAlmOtherNurg OBJECT IDENTIFIER ::= { pm10010ulhAlmOther 1 }
pm10010ulhAlmOtherUrg OBJECT IDENTIFIER ::= { pm10010ulhAlmOther 2 }
pm10010ulhAlmOtherCrit OBJECT IDENTIFIER ::= { pm10010ulhAlmOther 3 }

pm10010ulhAlmClient OBJECT IDENTIFIER ::= { pm10010ulhalarms 2 }
pm10010ulhAlmClientNurg OBJECT IDENTIFIER ::= { pm10010ulhAlmClient 1 }
pm10010ulhAlmClientUrg OBJECT IDENTIFIER ::= { pm10010ulhAlmClient 2 }
pm10010ulhAlmClientCrit OBJECT IDENTIFIER ::= { pm10010ulhAlmClient 3 }
	
pm10010ulhAlmLine OBJECT IDENTIFIER ::= { pm10010ulhalarms 3 }
pm10010ulhAlmLineNurg OBJECT IDENTIFIER ::= { pm10010ulhAlmLine 1 }
pm10010ulhAlmLineUrg OBJECT IDENTIFIER ::= { pm10010ulhAlmLine 2 }
pm10010ulhAlmLineCrit OBJECT IDENTIFIER ::= { pm10010ulhAlmLine 3 }





pm10010ulhmeasures OBJECT IDENTIFIER ::= { modulePm10010ulh 3 }	
pm10010ulhMesrOther OBJECT IDENTIFIER ::= { pm10010ulhmeasures 1 }	
pm10010ulhMesrClient OBJECT IDENTIFIER ::= { pm10010ulhmeasures 2 }	
pm10010ulhMesrLine OBJECT IDENTIFIER ::= { pm10010ulhmeasures 3 }	




pm10010ulhcounters OBJECT IDENTIFIER ::= { modulePm10010ulh 4 }
pm10010ulhCntOther OBJECT IDENTIFIER ::= { pm10010ulhcounters 1 }
pm10010ulhCntClient OBJECT IDENTIFIER ::= { pm10010ulhcounters 2 }
pm10010ulhCntLine OBJECT IDENTIFIER ::= { pm10010ulhcounters 3 }


pm10010ulhcontrolsWrite OBJECT IDENTIFIER ::= { modulePm10010ulh 6 }
pm10010ulhCtrlOther OBJECT IDENTIFIER ::= { pm10010ulhcontrolsWrite 1 }
pm10010ulhCtrlClient OBJECT IDENTIFIER ::= { pm10010ulhcontrolsWrite 2 }
pm10010ulhCtrlLine OBJECT IDENTIFIER ::= { pm10010ulhcontrolsWrite 3 }

pm10010ulhri OBJECT IDENTIFIER ::= { modulePm10010ulh 7 }
pm10010ulhriTable OBJECT IDENTIFIER ::= { pm10010ulhri 1 }

pm10010ulhdownload OBJECT IDENTIFIER ::= { modulePm10010ulh 8 }
pm10010ulhDwlOther OBJECT IDENTIFIER ::= { pm10010ulhdownload 1 }
pm10010ulhDwlClient OBJECT IDENTIFIER ::= { pm10010ulhdownload 2 }
pm10010ulhDwlLine OBJECT IDENTIFIER ::= { pm10010ulhdownload 3 }


pm10010ulhConfig OBJECT IDENTIFIER ::= { modulePm10010ulh 9 }

pm10010ulhtraps OBJECT IDENTIFIER ::= { modulePm10010ulh 10 }



pm10010ulhMonitoring OBJECT IDENTIFIER ::= { modulePm10010ulh 11}

pm10010ulhMonOther OBJECT IDENTIFIER ::= { pm10010ulhMonitoring 1 }
pm10010ulhMonRmon OBJECT IDENTIFIER ::= { pm10010ulhMonOther 3 }

pm10010ulhMonClient OBJECT IDENTIFIER ::= { pm10010ulhMonitoring 2 }
pm10010ulhMonClientRmonCounter OBJECT IDENTIFIER ::= { pm10010ulhMonClient 4 }


pm10010ulhMonPerfOther OBJECT IDENTIFIER ::= { pm10010ulhMonitoring 5 }
pm10010ulhMonPerfSync OBJECT IDENTIFIER ::= { pm10010ulhMonPerfOther 1 }
pm10010ulhMonPerfTimeStamp OBJECT IDENTIFIER ::= { pm10010ulhMonPerfOther 2 }


pm10010ulhMonPerfClient OBJECT IDENTIFIER ::= { pm10010ulhMonitoring 6 }

pm10010ulhMonPerfLine OBJECT IDENTIFIER ::= { pm10010ulhMonitoring 7 }



--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pm10010ulhMultiRate ::= TEXTUAL-CONVENTION
    STATUS      current
    DESCRIPTION "different rate for a client port"
    SYNTAX INTEGER {
		rate100Mhz(0),
		rate250Mhz(1),
		rate500Mhz(2),
		rate1Ghz(3)
           }

Pm10010ulhOtxMode ::= TEXTUAL-CONVENTION
    STATUS      current
    DESCRIPTION "Different modes on OTX-TLH on client and line ports"
    SYNTAX INTEGER {
		otx80mode(1),
		otx60mode(2),
		otxadjustmode(4)
           }

Pm10010ulhOtxGrid ::= TEXTUAL-CONVENTION
    STATUS      current
    DESCRIPTION "Different grids on OTX-TLH on client and line ports"
    SYNTAX INTEGER {
		otxgrid200(200),
		otxgrid100(100),
		otxgrid50(50)
           }

Pm10010ulhAdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm10010ulhClientProtocol ::= TEXTUAL-CONVENTION
    STATUS      current
    DESCRIPTION "Different values on the protocol on the client ports"
    SYNTAX INTEGER {
		protocolclientvalue0(0),
		protocolclientvalue1(1),
		protocolclientvalue2(2),
		protocolclientvalue3(3),
		protocolclientvalue4(4),
		protocolclientvalue5(5),
		protocolclientvalue6(6),
		protocolclientvalue7(7),
		protocolclientvalue8(8)
           }

Pm10010ulhProtocolMode ::= TEXTUAL-CONVENTION
    STATUS      current
    DESCRIPTION "Different values on the protocol mode"
    SYNTAX INTEGER {
		protocolmodevalue0(0),
		protocolmodevalue1(1),
		protocolmodevalue2(2),
		protocolmodevalue3(3)
           }

Pm10010ulhOtxChannel ::= TEXTUAL-CONVENTION
    STATUS      current
    DESCRIPTION "Channel selection on transceiver Tx line ports"
    SYNTAX INTEGER

Pm10010ulhOrxChannel ::= TEXTUAL-CONVENTION
    STATUS      current
    DESCRIPTION "Channel selection on transceiver Rx line ports"
    SYNTAX INTEGER

Pm10010ulhDccMode ::= TEXTUAL-CONVENTION
    STATUS      current
    DESCRIPTION "Mode for DCC"
    SYNTAX INTEGER {
		dccNo(0),
		dccLine1(1),
		dccLine2(2)
           }

Pm10010ulhModuleMode ::= TEXTUAL-CONVENTION
    STATUS      current
    DESCRIPTION "Mode for the  module"
    SYNTAX INTEGER {
		unusedmode(0),
		mode200gma(1),
		mode200gmr(2),
		mode100gulh(3)
           }

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm10010ulhRinvReloadInventory OBJECT-TYPE
  SYNTAX EkiOnOff
  MAX-ACCESS read-write
  STATUS current
  DESCRIPTION
        "Reload the inventory: This OID triggers an 
         inventory reload."
  ::= { pm10010ulhri 2 }

pm10010ulhRinvHwPlatform OBJECT-TYPE
  SYNTAX DisplayString
  MAX-ACCESS read-only
  STATUS current
  DESCRIPTION
        "HW platform description: This OID contains the 
         description of the Hardware platform."
  ::= { pm10010ulhri 3 }
  
pm10010ulhRinvModulePlatform OBJECT-TYPE
  SYNTAX DisplayString
  MAX-ACCESS read-only
  STATUS current
  DESCRIPTION
        "Module platform description: This OID contains the 
         description of the Module."
  ::= { pm10010ulhri 4 }
  
pm10010ulhRinvSwPlatform OBJECT-TYPE
  SYNTAX DisplayString
  MAX-ACCESS read-only
  STATUS current
  DESCRIPTION
        "SW platform description: This OID contains the 
         description of the Software platform."
  ::= { pm10010ulhri 5 }
  
pm10010ulhRinvGwPlatform OBJECT-TYPE
  SYNTAX DisplayString
  MAX-ACCESS read-only
  STATUS current
  DESCRIPTION
        "GW platform description: This OID contains the 
         description of the Gateware platform."
  ::= { pm10010ulhri 6 }


pm10010ulhRinvSfpTable OBJECT-TYPE
      SYNTAX  SEQUENCE OF Pm10010ulhRinvSfpEntry
      MAX-ACCESS  not-accessible
      STATUS  current
      DESCRIPTION
              "List of the SFPs on the selected module"
      ::= { pm10010ulhriTable 1 }

pm10010ulhRinvSfpEntry OBJECT-TYPE
        SYNTAX  Pm10010ulhRinvSfpEntry
        MAX-ACCESS  not-accessible
        STATUS  current
        DESCRIPTION
              "Row definition for the SFP table"
        INDEX   { pm10010ulhRinvSfpIndex }
        ::= { pm10010ulhRinvSfpTable 1 }
    


Pm10010ulhRinvSfpEntry::=
        SEQUENCE {
          pm10010ulhRinvSfpIndex 
              Integer32,
          pm10010ulhRinvsfp
              DisplayString
        }


    pm10010ulhRinvSfpIndex OBJECT-TYPE
        SYNTAX  Integer32(1..16)
        MAX-ACCESS  read-only
        STATUS  current
        DESCRIPTION
              "Index for SFP table"
        ::= { pm10010ulhRinvSfpEntry 1 }


    pm10010ulhRinvsfp OBJECT-TYPE
        SYNTAX  DisplayString
        MAX-ACCESS  read-only
        STATUS  current
        DESCRIPTION
              "Inventory for the SFP: This OID contains the inventory for the SFP"
        ::= { pm10010ulhRinvSfpEntry 2 }




pm10010ulhRinvLineTable OBJECT-TYPE
      SYNTAX  SEQUENCE OF Pm10010ulhRinvLineEntry
      MAX-ACCESS  not-accessible
      STATUS  current
      DESCRIPTION
              "List of the XFPs on the selected module"
      ::= { pm10010ulhriTable 2 }

pm10010ulhRinvLineEntry OBJECT-TYPE
        SYNTAX  Pm10010ulhRinvLineEntry
        MAX-ACCESS  not-accessible
        STATUS  current
        DESCRIPTION
              "Row definition for the XFP table"
        INDEX   { pm10010ulhRinvLineIndex }
        ::= { pm10010ulhRinvLineTable 1 }
    


Pm10010ulhRinvLineEntry::=
        SEQUENCE {
          pm10010ulhRinvLineIndex 
              Integer32,
          pm10010ulhRinvxfpLine
              DisplayString
        }


    pm10010ulhRinvLineIndex OBJECT-TYPE
        SYNTAX  Integer32(1..16)
        MAX-ACCESS  read-only
        STATUS  current
        DESCRIPTION
              "Index for XFP table"
        ::= { pm10010ulhRinvLineEntry 1 }


    pm10010ulhRinvxfpLine OBJECT-TYPE
        SYNTAX  DisplayString
        MAX-ACCESS  read-only
        STATUS  current
        DESCRIPTION
              "Inventory for the XFP: This OID contains the inventory for the XFP"
        ::= { pm10010ulhRinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm10010ulhAlmsynthAlm0 OBJECT IDENTIFIER ::= { pm10010ulhAlmOtherCrit 0 }




pm10010ulhAlmDefFuseB OBJECT-TYPE
	  SYNTAX EkiOnOff
	  MAX-ACCESS read-only
	  STATUS current
	  DESCRIPTION
        "
        Fuse B Fail :This OID indicates 
        that the fuse of the power input 
        B is in fail condition <Help> Status 
        of the Fuse B <Condtype> DEF_FUSE_B 
        <Probcause> powerProblem (36) <Alarmtype> 
        equipmentAlarm (5) <Polarity> (2) 
        "
	  ::= { pm10010ulhAlmsynthAlm0 16 }



pm10010ulhAlmDefFuseA OBJECT-TYPE
	  SYNTAX EkiOnOff
	  MAX-ACCESS read-only
	  STATUS current
	  DESCRIPTION
        "
        Fuse A Fail :This OID indicates 
        that the fuse of the power input 
        A is in fail condition <Help> Status 
        of the Fuse A <Condtype> DEF_FUSE_A 
        <Probcause> powerProblem (36) <Alarmtype> 
        equipmentAlarm (5) <Polarity> (2) 
        "
	  ::= { pm10010ulhAlmsynthAlm0 15 }



pm10010ulhAlmModGlobFail OBJECT-TYPE
	  SYNTAX EkiOnOff
	  MAX-ACCESS read-only
	  STATUS current
	  DESCRIPTION
        "
        Module Failure :This OID is set 
        on detection of a failure originating 
        from the RM <Help> This alarm is 
        set on detection of a failure originating 
        from the equipment <Condtype> MOD_GLOB_FAIL 
        <Probcause> other (1) <Alarmtype> 
        synthesisAlarm (12)  <Polarity> 
        (2) 
        "
	  ::= { pm10010ulhAlmsynthAlm0 9 }



pm10010ulhAlmFailFan OBJECT-TYPE
	  SYNTAX EkiOnOff
	  MAX-ACCESS read-only
	  STATUS current
	  DESCRIPTION
        "
        Fan Fail :This OID is at 1 when 
        any fail occurs on the fan tray 
        <Help> This alarm indicates that 
        the Fan tray module is in a failure 
        condition <Condtype> FAIL_FAN <Probcause> 
        equipmentMalfunction (16) <Alarmtype> 
        equipmentAlarm (5) <Polarity> (2) 
        "
	  ::= { pm10010ulhAlmsynthAlm0 2 }



--- *****************************************************
---     LEAF for the synthAlm2 article
--- *****************************************************
pm10010ulhAlmsynthAlm2 OBJECT IDENTIFIER ::= { pm10010ulhAlmOtherNurg 2 }




pm10010ulhAlmMaintenanceOn OBJECT-TYPE
	  SYNTAX EkiOnOff
	  MAX-ACCESS read-only
	  STATUS current
	  DESCRIPTION
        "
        Maintenance Mode :This OID indicates 
        that the RM is in maintenance mode. 
        <Help> This alarm indicates that 
        the maintenance mode is enabled 
        on the PM <Condtype> MAINTENANCE_ON 
        <Probcause> informationalStatus(1000) 
        <Alarmtype> other (1) <Polarity> 
        (2) 
        "
	  ::= { pm10010ulhAlmsynthAlm2 5 }



pm10010ulhAlmCorrelatOff OBJECT-TYPE
	  SYNTAX EkiOnOff
	  MAX-ACCESS read-only
	  STATUS current
	  DESCRIPTION
        "
        Not Used :This OID, when set,
         indicates that alarm correlation 
        is not being performed. <Condtype> 
        CORRELAT_OFF <Probcause> informationalStatus(1000) 
        <Alarmtype> other (1) <Polarity> 
        (2) 
        "
	  ::= { pm10010ulhAlmsynthAlm2 4 }



pm10010ulhAlmConfTableLoad OBJECT-TYPE
	  SYNTAX EkiOnOff
	  MAX-ACCESS read-only
	  STATUS current
	  DESCRIPTION
        "
        PM Configuration Load :This OID 
         is at 1 during the loading of
         configuration tables in the modules 
        RAM. <Condtype> CONF_TABLE_LOAD 
        <Probcause> informationalStatus(1000) 
        <Alarmtype> other (1) <Polarity> 
        (2) 
        "
	  ::= { pm10010ulhAlmsynthAlm2 3 }



pm10010ulhAlmInvUpload OBJECT-TYPE
	  SYNTAX EkiOnOff
	  MAX-ACCESS read-only
	  STATUS current
	  DESCRIPTION
        "
        Inventory Upload :This OID is
         at 1 during the uploading of PM 
        inventory information. <Condtype> 
        INV_UPLOAD <Probcause> informationalStatus(1000) 
        <Alarmtype> other (1) <Polarity> 
        (2) 
        "
	  ::= { pm10010ulhAlmsynthAlm2 2 }



pm10010ulhAlmConfTableSave OBJECT-TYPE
	  SYNTAX EkiOnOff
	  MAX-ACCESS read-only
	  STATUS current
	  DESCRIPTION
        "
        PM Configuration Save :This OID 
        is at 1 during the saving of a
         new configuration table in the 
        module Flash memory. <Condtype> 
        CONF_TABLE_SAVE <Probcause> informationalStatus(1000) 
        <Alarmtype> other (1) <Polarity> 
        (2) 
        "
	  ::= { pm10010ulhAlmsynthAlm2 1 }



--- *********************************************************
---     TABLE for the pm10010ulhAlmsynthAlmPort articles
--- *********************************************************

pm10010ulhAlmsynthAlmPortTable OBJECT-TYPE
	SYNTAX  SEQUENCE OF Pm10010ulhAlmsynthAlmPortEntry
	MAX-ACCESS not-accessible
	STATUS current
	DESCRIPTION
        "
        List of pm10010ulhAlmsynthAlmPort 
        Article
        "
	::= { pm10010ulhAlmClientCrit 8 }


pm10010ulhAlmsynthAlmPortEntry OBJECT-TYPE
	SYNTAX Pm10010ulhAlmsynthAlmPortEntry
	MAX-ACCESS not-accessible
	STATUS current
	DESCRIPTION
        "
        Row definition for the pm10010ulhAlmsynthAlmPort 
        table
        "
	INDEX   { pm10010ulhAlmsynthAlmPortIndex }
	::= { pm10010ulhAlmsynthAlmPortTable 1 }


Pm10010ulhAlmsynthAlmPortEntry ::=
	SEQUENCE {
	pm10010ulhAlmsynthAlmPortIndex
		INTEGER,
	pm10010ulhAlmUpCsfPortn
		EkiOnOff,
	pm10010ulhAlmFailAccPortn
		EkiOnOff,
	pm10010ulhAlmSfpDdmAlmPortn
		EkiOnOff,
	pm10010ulhAlmSfpDdmWarningPortn
		EkiOnOff,
	pm10010ulhAlmDwCaisPortn
		EkiOnOff,
	pm10010ulhAlmClientRemoteOosPortn
		EkiOnOff,
	pm10010ulhAlmClientLocalOosPortn
		EkiOnOff,
	pm10010ulhAlmDwLsdPortn
		EkiOnOff,
	pm10010ulhAlmHwFailAccPortn
		EkiOnOff,
	pm10010ulhAlmDdmAbsentPortn
		EkiOnOff,
	pm10010ulhAlmSfpAbsentPortn
		EkiOnOff
	}


pm10010ulhAlmsynthAlmPortIndex OBJECT-TYPE
	SYNTAX  INTEGER(0..128)
	MAX-ACCESS  read-only
	STATUS current
	DESCRIPTION
        "
        Index definition for the pm10010ulhAlmsynthAlmPort 
        table
        "
	::= { pm10010ulhAlmsynthAlmPortEntry 1 }


pm10010ulhAlmUpCsfPortn OBJECT-TYPE
	SYNTAX  EkiOnOff
	MAX-ACCESS read-only
	STATUS current
	DESCRIPTION
        "
        Client Signal Fail Inserted :This 
        OID indicates a CSF has been inserted 
        in the upstream client port. <Help> 
        This status indicates if a Client 
        Signal Fail is currently inserted 
        on the line signal for this client 
        port <Condtype> UP_CSF_1 <Probcause> 
        informationalStatus(1000) <Alarmtype> 
        other (1) <Polarity> (2) 
        "
	::= { pm10010ulhAlmsynthAlmPortEntry 17 }


pm10010ulhAlmFailAccPortn OBJECT-TYPE
	SYNTAX  EkiOnOff
	MAX-ACCESS read-only
	STATUS current
	DESCRIPTION
        "
        Client Access Fail :This OID indicates 
        a failure on the Client port <Help> 
        This alarm indicates a failure
         on the Client port <Condtype>
         FAIL_ACC_1 <Probcause> equipmentMalfunction 
        (16) <Alarmtype> synthesisAlarm 
        (12)  <Polarity> (2) 
        "
	::= { pm10010ulhAlmsynthAlmPortEntry 13 }


pm10010ulhAlmSfpDdmAlmPortn OBJECT-TYPE
	SYNTAX  EkiOnOff
	MAX-ACCESS read-only
	STATUS current
	DESCRIPTION
        "
        Alarm On Client Trscv DDM :This 
        OID indicates an alarm is being 
        received from the Client Transceiver 
        DDM <Help> This alarm indicates 
        if a DDM Alarm has been detected 
        on the client transceiver <Condtype> 
        SFP_DDM_ALM_1 <Probcause> inputOutputDeviceError 
        (24) <Alarmtype> synthesisAlarm 
        (12)  <Polarity> (2) 
        "
	::= { pm10010ulhAlmsynthAlmPortEntry 11 }


pm10010ulhAlmSfpDdmWarningPortn OBJECT-TYPE
	SYNTAX  EkiOnOff
	MAX-ACCESS read-only
	STATUS current
	DESCRIPTION
        "
        Warning On Client Trscv DDM :This 
        OID indicates a warning is being 
        received from the Client Transceiver 
        DDM <Help> This alarm indicates 
        if a DDM Warning has been detected 
        on the client transceiver <Condtype> 
        SFP_DDM_WARNING_1 <Probcause> inputOutputDeviceError 
        (24) <Alarmtype> synthesisAlarm 
        (12)  <Polarity> (2) 
        "
	::= { pm10010ulhAlmsynthAlmPortEntry 10 }


pm10010ulhAlmDwCaisPortn OBJECT-TYPE
	SYNTAX  EkiOnOff
	MAX-ACCESS read-only
	STATUS current
	DESCRIPTION
        "
        Client AIS Inserted :This OID
         indicates a CAIS has been inserted 
        on the output client port. <Help> 
        This status indicates if a Client 
        Alarm Indication Signal is currently 
        inserted on the client interface 
        <Condtype> DW_CAIS_1 <Probcause> 
        informationalStatus(1000) <Alarmtype> 
        other (1) <Polarity> (2) 
        "
	::= { pm10010ulhAlmsynthAlmPortEntry 9 }


pm10010ulhAlmClientRemoteOosPortn OBJECT-TYPE
	SYNTAX  EkiOnOff
	MAX-ACCESS read-only
	STATUS current
	DESCRIPTION
        "
        Remote Client Port In Service
         :This OID indicates that the remote 
        Client port is In Service (1) or 
        Out of Service (2) <Help> This
         status indicates if the remote 
        client port is in service <Condtype> 
        CLIENT_REMOTE_OOS <Probcause> informationalStatus(1000) 
        <Alarmtype> other (1) <Polarity> 
        (2) 
        "
	::= { pm10010ulhAlmsynthAlmPortEntry 8 }


pm10010ulhAlmClientLocalOosPortn OBJECT-TYPE
	SYNTAX  EkiOnOff
	MAX-ACCESS read-only
	STATUS current
	DESCRIPTION
        "
        Local Client Port In Service :This 
        OID indicates that the local Client 
        port is In Service (1) or Out of 
        Service (2) <Help> This status
         indicates if the local client
         port is in service <Condtype>
         CLIENT_LOCAL_OOS <Probcause> informationalStatus(1000) 
        <Alarmtype> other (1) <Polarity> 
        (2)
        "
	::= { pm10010ulhAlmsynthAlmPortEntry 7 }


pm10010ulhAlmDwLsdPortn OBJECT-TYPE
	SYNTAX  EkiOnOff
	MAX-ACCESS read-only
	STATUS current
	DESCRIPTION
        "
        Client Trscv Laser Shutdown :This 
        OID indicates the Client transceiver 
        laser is shutdown <Help> This status 
        indicates if the client transceiver 
        laser is shutdown <Condtype> DW_LSD_1 
        <Probcause> other (1) <Alarmtype> 
        equipmentAlarm (5) <Polarity> (2) 
        "
	::= { pm10010ulhAlmsynthAlmPortEntry 6 }


pm10010ulhAlmHwFailAccPortn OBJECT-TYPE
	SYNTAX  EkiOnOff
	MAX-ACCESS read-only
	STATUS current
	DESCRIPTION
        "
        Client HW Fail :This OID indicates 
        a failure on client port, most
         probably caused by a HW issue. 
        <Help> This alarm indicates a failure 
        on client port, most probably caused 
        by a HW issue. <Condtype> HW_FAIL_ACC_1 
        <Probcause> equipmentMalfunction 
        (16) <Alarmtype> synthesisAlarm 
        (12)  <Polarity> (2) 
        "
	::= { pm10010ulhAlmsynthAlmPortEntry 5 }


pm10010ulhAlmDdmAbsentPortn OBJECT-TYPE
	SYNTAX  EkiOnOff
	MAX-ACCESS read-only
	STATUS current
	DESCRIPTION
        "
        DDM Supported On Client Trscv
         :This OID indicates that the Client 
        transceiver supports the Digital 
        Diagnostic Monitoring function
         <Help> This status indicates if 
        the client transceiver includes 
        the DDM feature <Condtype> DDM_ABSENT_1 
        <Probcause> informationalStatus(1000) 
        <Alarmtype> other (1) <Polarity> 
        (2) 
        "
	::= { pm10010ulhAlmsynthAlmPortEntry 3 }


pm10010ulhAlmSfpAbsentPortn OBJECT-TYPE
	SYNTAX  EkiOnOff
	MAX-ACCESS read-only
	STATUS current
	DESCRIPTION
        "
        Client Optical Module Absent :This 
        OID indicates that the Transceiver 
        is not present in the client port. 
        <Help> This alarm indicates if
         the client transceiver is not
         plugged <Condtype> SFP_ABSENT_1 
        <Probcause> inputOutputDeviceError 
        (24) <Alarmtype> equipmentAlarm 
        (5) <Polarity> (2) <Event> ObjectCDSingleClientInv
        "
	::= { pm10010ulhAlmsynthAlmPortEntry 2 }


--- *********************************************************
---     TABLE for the pm10010ulhAlmsynthAlmLine articles
--- *********************************************************

pm10010ulhAlmsynthAlmLineTable OBJECT-TYPE
	SYNTAX  SEQUENCE OF Pm10010ulhAlmsynthAlmLineEntry
	MAX-ACCESS not-accessible
	STATUS current
	DESCRIPTION
        "
        List of pm10010ulhAlmsynthAlmLine 
        Article
        "
	::= { pm10010ulhAlmLineCrit 40 }


pm10010ulhAlmsynthAlmLineEntry OBJECT-TYPE
	SYNTAX Pm10010ulhAlmsynthAlmLineEntry
	MAX-ACCESS not-accessible
	STATUS current
	DESCRIPTION
        "
        Row definition for the pm10010ulhAlmsynthAlmLine 
        table
        "
	INDEX   { pm10010ulhAlmsynthAlmLineIndex }
	::= { pm10010ulhAlmsynthAlmLineTable 1 }


Pm10010ulhAlmsynthAlmLineEntry ::=
	SEQUENCE {
	pm10010ulhAlmsynthAlmLineIndex
		INTEGER,
	pm10010ulhAlmLineActivePortn
		EkiOnOff,
	pm10010ulhAlmLineFailPortn
		EkiOnOff,
	pm10010ulhAlmLineDdmAlmPortn
		EkiOnOff,
	pm10010ulhAlmLineDdmWarningPortn
		EkiOnOff,
	pm10010ulhAlmUpRdiInsPortn
		EkiOnOff,
	pm10010ulhAlmLineLocalOosPortn
		EkiOnOff,
	pm10010ulhAlmXfpTxOffPortn
		EkiOnOff,
	pm10010ulhAlmLineHwFailPortn
		EkiOnOff,
	pm10010ulhAlmXfpInitNotComplPortn
		EkiOnOff,
	pm10010ulhAlmXfpAbsentPortn
		EkiOnOff
	}


pm10010ulhAlmsynthAlmLineIndex OBJECT-TYPE
	SYNTAX  INTEGER(0..128)
	MAX-ACCESS  read-only
	STATUS current
	DESCRIPTION
        "
        Index definition for the pm10010ulhAlmsynthAlmLine 
        table
        "
	::= { pm10010ulhAlmsynthAlmLineEntry 1 }


pm10010ulhAlmLineActivePortn OBJECT-TYPE
	SYNTAX  EkiOnOff
	MAX-ACCESS read-only
	STATUS current
	DESCRIPTION
        "
        Line Active :This OID indicates 
        whether the line is active or standby. 
        <Help> This status indicates whether 
        the line is active or standby.
         <Condtype> LINE_ACTIVE <Probcause> 
        informationalStatus(1000) <Alarmtype> 
        other (1) <Polarity> (2) 
        "
	::= { pm10010ulhAlmsynthAlmLineEntry 17 }


pm10010ulhAlmLineFailPortn OBJECT-TYPE
	SYNTAX  EkiOnOff
	MAX-ACCESS read-only
	STATUS current
	DESCRIPTION
        "
        Line Port Failure :This OID indicates 
        a failure on the line port <Help> 
        This alarm indicates a failure
         on the line port <Condtype> LINE_FAIL 
        <Probcause> equipmentMalfunction 
        (16) <Alarmtype> synthesisAlarm 
        (12)  <Polarity> (2) 
        "
	::= { pm10010ulhAlmsynthAlmLineEntry 13 }


pm10010ulhAlmLineDdmAlmPortn OBJECT-TYPE
	SYNTAX  EkiOnOff
	MAX-ACCESS read-only
	STATUS current
	DESCRIPTION
        "
        Alarm On Line Optical Module DDM 
        :This OID indicates an alarm is 
        present coming out of Line transceiver 
        DDM <Help> This alarm indicates 
        if a DDM Alarm has been detected 
        on the line transceiver <Condtype> 
        LINE_DDM_ALM <Probcause> inputOutputDeviceError 
        (24) <Alarmtype> synthesisAlarm 
        (12)  <Polarity> (2) 
        "
	::= { pm10010ulhAlmsynthAlmLineEntry 11 }


pm10010ulhAlmLineDdmWarningPortn OBJECT-TYPE
	SYNTAX  EkiOnOff
	MAX-ACCESS read-only
	STATUS current
	DESCRIPTION
        "
        Warning On Line Optical Module 
        DDM :This OID indicates a warning 
        is present coming out of Line transceiver 
        DDM <Help> This alarm indicates 
        if a DDM Warning has been detected 
        on the line transceiver <Condtype> 
        LINE_DDM_WARNING <Probcause> inputOutputDeviceError 
        (24) <Alarmtype> synthesisAlarm 
        (12)  <Polarity> (2) 
        "
	::= { pm10010ulhAlmsynthAlmLineEntry 10 }


pm10010ulhAlmUpRdiInsPortn OBJECT-TYPE
	SYNTAX  EkiOnOff
	MAX-ACCESS read-only
	STATUS current
	DESCRIPTION
        "
        MS-RDI/L-RDI Inserted On Line
         :This OID indicates an upstream 
        MS-RDI/L-RDI has been inserted
         in the outgoing 10 Gb/s SDH/SONET 
        signal. <Help> This status indicates 
        if a MS-RDI/L-RDI is currently
         inserted on the line interface. 
        <Condtype> UP_RDI_INS <Probcause> 
        informationalStatus(1000) <Alarmtype> 
        other (1) <Polarity> (2) 
        "
	::= { pm10010ulhAlmsynthAlmLineEntry 9 }


pm10010ulhAlmLineLocalOosPortn OBJECT-TYPE
	SYNTAX  EkiOnOff
	MAX-ACCESS read-only
	STATUS current
	DESCRIPTION
        "
        Line Port In Service :This OID 
        indicates that the Line port is 
        In Service (1) of Out or Service 
        (2) <Help> This status indicates 
        if the line port is in service
         <Condtype> LINE_LOCAL_OOS <Probcause> 
        informationalStatus(1000) <Alarmtype> 
        other (1) <Polarity> (2) 
        "
	::= { pm10010ulhAlmsynthAlmLineEntry 7 }


pm10010ulhAlmXfpTxOffPortn OBJECT-TYPE
	SYNTAX  EkiOnOff
	MAX-ACCESS read-only
	STATUS current
	DESCRIPTION
        "
        Line Trscv Laser Shutdown :This 
        OID indicates the Line transceiver 
        laser is shutdown <Help> This status 
        indicates if the Line transceiver 
        laser is shutdown <Condtype> XFP_TX_OFF 
        <Probcause> other (1) <Alarmtype> 
        equipmentAlarm (5) <Polarity> (2) 
        "
	::= { pm10010ulhAlmsynthAlmLineEntry 6 }


pm10010ulhAlmLineHwFailPortn OBJECT-TYPE
	SYNTAX  EkiOnOff
	MAX-ACCESS read-only
	STATUS current
	DESCRIPTION
        "
        Line Port HW Failure :This OID 
        indicates a failure on line port, 
        most probably caused by a HW issue 
        <Help> This alarm indicates a failure 
        on line port, most probably caused 
        by a HW issue <Condtype> LINE_HW_FAIL 
        <Probcause> equipmentMalfunction 
        (16) <Alarmtype> synthesisAlarm 
        (12)  <Polarity> (2) 
        "
	::= { pm10010ulhAlmsynthAlmLineEntry 5 }


pm10010ulhAlmXfpInitNotComplPortn OBJECT-TYPE
	SYNTAX  EkiOnOff
	MAX-ACCESS read-only
	STATUS current
	DESCRIPTION
        "
        Line Optical Module Ready :This 
        OID indicates that the optical
         interface is not operational.
         <Help> This status indicates if 
        the line transceiver has been correctly 
        initialized <Condtype> XFP_INIT_NOT_COMPL 
        <Probcause> equipmentMalfunction 
        (16) <Alarmtype> equipmentAlarm 
        (5) <Polarity> (2) 
        "
	::= { pm10010ulhAlmsynthAlmLineEntry 3 }


pm10010ulhAlmXfpAbsentPortn OBJECT-TYPE
	SYNTAX  EkiOnOff
	MAX-ACCESS read-only
	STATUS current
	DESCRIPTION
        "
        Line Optical Module Absent :This 
        OID indicates that the line optical 
        interface is not present. <Help> 
        This alarm indicates if the line 
        transceiver is not plugged <Condtype> 
        XFP_ABSENT <Probcause> inputOutputDeviceError 
        (24) <Alarmtype> equipmentAlarm 
        (5) <Polarity> (2) 
        "
	::= { pm10010ulhAlmsynthAlmLineEntry 2 }


--- *****************************************************
---     LEAF for the clientModuleState article
--- *****************************************************
pm10010ulhAlmclientModuleState OBJECT IDENTIFIER ::= { pm10010ulhAlmOtherCrit 72 }




pm10010ulhAlmCfpHighPowerDown OBJECT-TYPE
	  SYNTAX EkiOnOff
	  MAX-ACCESS read-only
	  STATUS current
	  DESCRIPTION
        "
        Client Trscv High Power Down :This 
        OID indicates the Client Trscv
         is entering Low Power state <Help> 
        Status indicating the Client Trscv 
        is entering Low Power state <Condtype> 
        CFP_HIGH_POWER_DOWN <Probcause> 
        informationalStatus(1000) <Alarmtype> 
        other (1) <Polarity> (2) 
        "
	  ::= { pm10010ulhAlmclientModuleState 9 }



pm10010ulhAlmCfpTxTurnOff OBJECT-TYPE
	  SYNTAX EkiOnOff
	  MAX-ACCESS read-only
	  STATUS current
	  DESCRIPTION
        "
        Client Trscv Laser Turn Off :This 
        OID indicates the Client Trscv
         is turning off its laser <Help> 
        Status indicating the Client Trscv 
        is turning off its laser <Condtype> 
        CFP_TX_TURN_OFF <Probcause> informationalStatus(1000) 
        <Alarmtype> other (1) <Polarity> 
        (2) 
        "
	  ::= { pm10010ulhAlmclientModuleState 8 }



pm10010ulhAlmCfpFault OBJECT-TYPE
	  SYNTAX EkiOnOff
	  MAX-ACCESS read-only
	  STATUS current
	  DESCRIPTION
        "
        Client Trscv Fault :This OID indicates 
        the Client Trscv is in Fault state 
        <Help> Status indicating the Client 
        Trscv is in Fault state <Condtype> 
        CFP_FAULT <Probcause> informationalStatus(1000) 
        <Alarmtype> other (1) <Polarity> 
        (2) 
        "
	  ::= { pm10010ulhAlmclientModuleState 7 }



pm10010ulhAlmCfpReady OBJECT-TYPE
	  SYNTAX EkiOnOff
	  MAX-ACCESS read-only
	  STATUS current
	  DESCRIPTION
        "
        Client Trscv Ready :This OID indicates 
        the Client Trscv is ready to operate 
        <Help> Status indicating the Client 
        Trscv is ready to operate <Condtype> 
        CFP_READY <Probcause> informationalStatus(1000) 
        <Alarmtype> other (1) <Polarity> 
        (2) 
        "
	  ::= { pm10010ulhAlmclientModuleState 6 }



pm10010ulhAlmCfpTxTurnOn OBJECT-TYPE
	  SYNTAX EkiOnOff
	  MAX-ACCESS read-only
	  STATUS current
	  DESCRIPTION
        "
        Client Trscv Laser Turn On :This 
        OID indicates the Client Trscv
         is turning on its laser <Help> 
        Status indicating the Client Trscv 
        is turning on its laser <Condtype> 
        CFP_TX_TURN_ON <Probcause> informationalStatus(1000) 
        <Alarmtype> other (1) <Polarity> 
        (2) 
        "
	  ::= { pm10010ulhAlmclientModuleState 5 }



pm10010ulhAlmCfpTxOff OBJECT-TYPE
	  SYNTAX EkiOnOff
	  MAX-ACCESS read-only
	  STATUS current
	  DESCRIPTION
        "
        Client Trscv Laser Shutdown :This 
        OID indicates the Client Trscv
         Laser is OFF <Help> Status indicating 
        the Client Trscv Laser is OFF <Condtype> 
        CFP_TX_OFF <Probcause> informationalStatus(1000) 
        <Alarmtype> other (1) <Polarity> 
        (2) 
        "
	  ::= { pm10010ulhAlmclientModuleState 4 }



pm10010ulhAlmCfpHighPowerUp OBJECT-TYPE
	  SYNTAX EkiOnOff
	  MAX-ACCESS read-only
	  STATUS current
	  DESCRIPTION
        "
        Client Trscv High Power Up :This 
        OID indicates the Client Trscv
         is leaving Low Power state <Help> 
        Status indicating the Client Trscv 
        is leaving Low Power state <Condtype> 
        CFP_HIGH_POWER_UP <Probcause> informationalStatus(1000) 
        <Alarmtype> other (1) <Polarity> 
        (2) 
        "
	  ::= { pm10010ulhAlmclientModuleState 3 }



pm10010ulhAlmCfpLowPower OBJECT-TYPE
	  SYNTAX EkiOnOff
	  MAX-ACCESS read-only
	  STATUS current
	  DESCRIPTION
        "
        Client Trscv Low Power :This OID 
        indicates the Client Trscv is in 
        low power state <Help> Status indicating 
        the Client Trscv is in low power 
        state <Condtype> CFP_LOW_POWER
         <Probcause> informationalStatus(1000) 
        <Alarmtype> other (1) <Polarity> 
        (2) 
        "
	  ::= { pm10010ulhAlmclientModuleState 2 }



pm10010ulhAlmCfpInitialize OBJECT-TYPE
	  SYNTAX EkiOnOff
	  MAX-ACCESS read-only
	  STATUS current
	  DESCRIPTION
        "
        Client Trscv Initialize :This
         OID indicates the Client Trscv 
        initialization is in progress <Help> 
        Status indicating the Client Trscv 
        initialization is in progress <Condtype> 
        CFP_INITIALIZE <Probcause> informationalStatus(1000) 
        <Alarmtype> other (1) <Polarity> 
        (2) 
        "
	  ::= { pm10010ulhAlmclientModuleState 1 }



--- *****************************************************
---     LEAF for the clientModuleGeneralStatus article
--- *****************************************************
pm10010ulhAlmclientModuleGeneralStatus OBJECT IDENTIFIER ::= { pm10010ulhAlmOtherCrit 73 }




pm10010ulhAlmCfpHwInterlock OBJECT-TYPE
	  SYNTAX EkiOnOff
	  MAX-ACCESS read-only
	  STATUS current
	  DESCRIPTION
        "
        Client Trscv Hardware Interlock 
        :This OID indicates the Client
         Trscv power is higher than the 
        cooling capacity <Help> Alarm indicating 
        the Client Trscv power is higher 
        than the cooling capacity <Condtype> 
        CFP_HW_INTERLOCK <Probcause> temperatureUnacceptable 
        (51) <Alarmtype> equipmentAlarm 
        (5) <Polarity> (2) 
        "
	  ::= { pm10010ulhAlmclientModuleGeneralStatus 14 }



pm10010ulhAlmCfpLossOfRefclk OBJECT-TYPE
	  SYNTAX EkiOnOff
	  MAX-ACCESS read-only
	  STATUS current
	  DESCRIPTION
        "
        Client Trscv Loss Of Ref Clock 
        :This OID indicates a Loss of Reference 
        clock is detected on the Client 
        Trscv <Help> Alarm indicating a 
        Loss of Reference clock is detected 
        on the Client Trscv <Condtype>
         CFP_LOSS_OF_REFCLK <Probcause> 
        inputOutputDeviceError (24) <Alarmtype> 
        equipmentAlarm (5) <Polarity> (2) 
        "
	  ::= { pm10010ulhAlmclientModuleGeneralStatus 11 }



pm10010ulhAlmCfpTxJitterPllLol OBJECT-TYPE
	  SYNTAX EkiOnOff
	  MAX-ACCESS read-only
	  STATUS current
	  DESCRIPTION
        "
        Client Trscv Tx Jitter PLL Loss 
        Of Lock :This OID indicates a Tx 
        Jitter PLL Loss of Lock is dtected 
        on the Client Trscv <Help> Alarm 
        indicating a Tx Jitter PLL Loss 
        of Lock is dtected on the Client 
        Trscv <Condtype> CFP_TX_JITTER_PLL_LOL 
        <Probcause> inputOutputDeviceError 
        (24) <Alarmtype> equipmentAlarm 
        (5) <Polarity> (2) 
        "
	  ::= { pm10010ulhAlmclientModuleGeneralStatus 10 }



pm10010ulhAlmCfpTxCmuLol OBJECT-TYPE
	  SYNTAX EkiOnOff
	  MAX-ACCESS read-only
	  STATUS current
	  DESCRIPTION
        "
        Client Trscv CMU Loss Of Lock
         :This OID indicates a Clock Multiplier 
        Unit Loss of Lock is detected on 
        the Client Trscv <Help> Alarm indicating 
        a Clock Multiplier Unit Loss of 
        Lock is detected on the Client
         Trscv <Condtype> CFP_TX_CMU_LOL 
        <Probcause> inputOutputDeviceError 
        (24) <Alarmtype> equipmentAlarm 
        (5) <Polarity> (2) 
        "
	  ::= { pm10010ulhAlmclientModuleGeneralStatus 9 }



pm10010ulhAlmCfpTxLosf OBJECT-TYPE
	  SYNTAX EkiOnOff
	  MAX-ACCESS read-only
	  STATUS current
	  DESCRIPTION
        "
        Client Trscv Loss Of Signal Functionality 
        :This OID indicates a Loss of Signal 
        functionality is detected on the 
        Client Trscv <Help> Alarm indicating 
        a Loss of Signal functionality
         is detected on the Client Trscv 
        <Condtype> CFP_TX_LOSF <Probcause> 
        lossOfSignal (30) <Alarmtype> equipmentAlarm 
        (5) <Polarity> (2) 
        "
	  ::= { pm10010ulhAlmclientModuleGeneralStatus 8 }



pm10010ulhAlmCfpTxHostLol OBJECT-TYPE
	  SYNTAX EkiOnOff
	  MAX-ACCESS read-only
	  STATUS current
	  DESCRIPTION
        "
        Client Trscv Tx Host Loss Of Lock 
        :This OID indicates of Loss of
         Lock is detected on the Client 
        Trscv Tx Host interface <Help>
         Alarm indicating of Loss of Lock 
        is detected on the Client Trscv 
        Tx Host interface <Condtype> CFP_TX_HOST_LOL 
        <Probcause> receiverFailure (42) 
        <Alarmtype> equipmentAlarm (5)
         <Polarity> (2) 
        "
	  ::= { pm10010ulhAlmclientModuleGeneralStatus 7 }



pm10010ulhAlmCfpRxLos OBJECT-TYPE
	  SYNTAX EkiOnOff
	  MAX-ACCESS read-only
	  STATUS current
	  DESCRIPTION
        "
        Client Trscv Loss Of Signal :This 
        OID indicates a Loss of Signal
         is detected on the Client Trscv 
        <Help> Alarm indicating a Loss
         of Signal is detected on the Client 
        Trscv <Condtype> CFP_RX_LOS <Probcause> 
        lossOfSignal (30) <Alarmtype> equipmentAlarm 
        (5) <Polarity> (2) 
        "
	  ::= { pm10010ulhAlmclientModuleGeneralStatus 6 }



pm10010ulhAlmCfpRxNetworkLol OBJECT-TYPE
	  SYNTAX EkiOnOff
	  MAX-ACCESS read-only
	  STATUS current
	  DESCRIPTION
        "
        Client Trscv Rx Network Loss Of 
        Lock :This OID indicates of Loss 
        of Lock is dected on the Client 
        Trscv Rx Network interface <Help> 
        Alarm indicating of Loss of Lock 
        is dected on the Client Trscv Rx 
        Network interface <Condtype> CFP_RX_NETWORK_LOL 
        <Probcause> receiverFailure (42) 
        <Alarmtype> equipmentAlarm (5)
         <Polarity> (2) 
        "
	  ::= { pm10010ulhAlmclientModuleGeneralStatus 5 }



pm10010ulhAlmCfpOutOfAlignment OBJECT-TYPE
	  SYNTAX EkiOnOff
	  MAX-ACCESS read-only
	  STATUS current
	  DESCRIPTION
        "
        Client Trscv Out Of Alignment
         :This OID indicates an Out of
         alignment on the Client Trscv
         Host Interface <Help> Alarm indicating 
        an Out of alignment on the Client 
        Trscv Host Interface <Condtype> 
        CFP_OUT_OF_ALIGNMENT <Probcause> 
        receiverFailure (42) <Alarmtype> 
        equipmentAlarm (5) <Polarity> (2) 
        "
	  ::= { pm10010ulhAlmclientModuleGeneralStatus 4 }



--- *****************************************************
---     LEAF for the clientGlobalAlarmSummary article
--- *****************************************************
pm10010ulhAlmclientGlobalAlarmSummary OBJECT IDENTIFIER ::= { pm10010ulhAlmOtherCrit 74 }




pm10010ulhAlmCfpGlobAlarmAssertion  OBJECT-TYPE
	  SYNTAX EkiOnOff
	  MAX-ACCESS read-only
	  STATUS current
	  DESCRIPTION
        "
        Client Trscv Global Alarm :This 
        OID indicates at least one  Fault 
        or Status is detected on the Client 
        Trscv module <Help> Synthesis alarm 
        indicating at least one Alarm,
         Warning, Fault or Status is detected 
        on the Client Trscv module <Condtype> 
        CFP_GLOB_ALARM_ASSERTION  <Probcause> 
        informationalStatus(1000) <Alarmtype> 
        other (1) <Polarity> (2) 
        "
	  ::= { pm10010ulhAlmclientGlobalAlarmSummary 16 }



pm10010ulhAlmCfpHostLaneFaultStatus  OBJECT-TYPE
	  SYNTAX EkiOnOff
	  MAX-ACCESS read-only
	  STATUS current
	  DESCRIPTION
        "
        Client Trscv Host Fault And Status 
        :This OID indicates at least one 
        Fault or Status is detected on
         the Client Trscv Host Interface 
        <Help> Synthesis alarm indicating 
        at least one Fault or Status is 
        detected on the Client Trscv Host 
        Interface <Condtype> CFP_HOST_LANE_FAULT_STATUS 
         <Probcause> informationalStatus(1000) 
        <Alarmtype> other (1) <Polarity> 
        (2) 
        "
	  ::= { pm10010ulhAlmclientGlobalAlarmSummary 15 }



pm10010ulhAlmCfpNetworkLaneFaultStatus  OBJECT-TYPE
	  SYNTAX EkiOnOff
	  MAX-ACCESS read-only
	  STATUS current
	  DESCRIPTION
        "
        Client Trscv Network Fault And 
        Status :This OID indicates at least 
        one Fault or Status is detected 
        on the Client Trscv Network Interface 
        <Help> Synthesis alarm indicating 
        at least one Fault or Status is 
        detected on the Client Trscv Network 
        Interface <Condtype> CFP_NETWORK_LANE_FAULT_STATUS 
         <Probcause> informationalStatus(1000) 
        <Alarmtype> other (1) <Polarity> 
        (2) 
        "
	  ::= { pm10010ulhAlmclientGlobalAlarmSummary 14 }



pm10010ulhAlmCfpNetworkLaneAlarmWarning1 OBJECT-TYPE
	  SYNTAX EkiOnOff
	  MAX-ACCESS read-only
	  STATUS current
	  DESCRIPTION
        "
        Client Trscv Network Alarm And 
        Warning 1 :This OID indicates at 
        least one DDM  is detected on the 
        Client Trscv Network Interface
         <Help> Synthesis alarm indicating 
        at least one DDM Alarm or DDM Warning 
        is detected on the Client Trscv 
        Network Interface <Condtype> CFP_NETWORK_LANE_ALARM_WARNING_1 
        <Probcause> informationalStatus(1000) 
        <Alarmtype> other (1) <Polarity> 
        (2) 
        "
	  ::= { pm10010ulhAlmclientGlobalAlarmSummary 13 }



pm10010ulhAlmCfpModuleAlarmWarning2 OBJECT-TYPE
	  SYNTAX EkiOnOff
	  MAX-ACCESS read-only
	  STATUS current
	  DESCRIPTION
        "
        Client Trscv Module Alarm And
         Warning 2 :This OID indicates
         at least one DDM is detected on 
        the Client Trscv module <Help>
         Synthesis alarm indicating at
         least one DDM Alarm or DDM Warning 
        is detected on the Client Trscv 
        module <Condtype> CFP_MODULE_ALARM_WARNING_2 
        <Probcause> informationalStatus(1000) 
        <Alarmtype> other (1) <Polarity> 
        (2) 
        "
	  ::= { pm10010ulhAlmclientGlobalAlarmSummary 12 }



pm10010ulhAlmCfpModuleAlarmWarning1  OBJECT-TYPE
	  SYNTAX EkiOnOff
	  MAX-ACCESS read-only
	  STATUS current
	  DESCRIPTION
        "
        Client Trscv Module Alarm And
         Warning 1 :This OID indicates
         at least one DDM  This OID is
         detected on the Client Trscv module 
        <Help> Synthesis alarm indicating 
        at least one DDM Alarm or DDM Warning 
        is detected on the Client Trscv 
        module <Condtype> CFP_MODULE_ALARM_WARNING_1 
         <Probcause> informationalStatus(1000) 
        <Alarmtype> other (1) <Polarity> 
        (2) 
        "
	  ::= { pm10010ulhAlmclientGlobalAlarmSummary 11 }



pm10010ulhAlmCfpModuleFault  OBJECT-TYPE
	  SYNTAX EkiOnOff
	  MAX-ACCESS read-only
	  STATUS current
	  DESCRIPTION
        "
        Client Trscv Module Fault :This 
        OID indicates at least one Fault 
        is detected on the Client Trscv 
        module <Help> Synthesis alarm indicating 
        at least one Fault is detected
         on the Client Trscv module <Condtype> 
        CFP_MODULE_FAULT  <Probcause> informationalStatus(1000) 
        <Alarmtype> other (1) <Polarity> 
        (2) 
        "
	  ::= { pm10010ulhAlmclientGlobalAlarmSummary 10 }



pm10010ulhAlmCfpModuleGeneralStatus  OBJECT-TYPE
	  SYNTAX EkiOnOff
	  MAX-ACCESS read-only
	  STATUS current
	  DESCRIPTION
        "
        Client Trscv General Status :This 
        OID indicates the Client Trscv
         module general status <Help> Synthesis 
        alarm indicating the Client Trscv 
        module general status <Condtype> 
        CFP_MODULE_GENERAL_STATUS  <Probcause> 
        informationalStatus(1000) <Alarmtype> 
        other (1) <Polarity> (2) 
        "
	  ::= { pm10010ulhAlmclientGlobalAlarmSummary 9 }



pm10010ulhAlmCfpModuleState  OBJECT-TYPE
	  SYNTAX EkiOnOff
	  MAX-ACCESS read-only
	  STATUS current
	  DESCRIPTION
        "
        Client Trscv Module State :This 
        OID indicates the Client Trscv
         module state <Help> Synthesis
         alarm indicating the Client Trscv 
        module state <Condtype> CFP_MODULE_STATE 
         <Probcause> informationalStatus(1000) 
        <Alarmtype> other (1) <Polarity> 
        (2) 
        "
	  ::= { pm10010ulhAlmclientGlobalAlarmSummary 8 }



pm10010ulhAlmCfpNetworkLaneAlarmWarning2 OBJECT-TYPE
	  SYNTAX EkiOnOff
	  MAX-ACCESS read-only
	  STATUS current
	  DESCRIPTION
        "
        Client Trscv Network Alarm And 
        Warning 2 :This OID indicates at 
        least one DDM is detected on the 
        Client Trscv Network Interface
         <Help> Synthesis alarm indicating 
        at least one DDM Alarm or DDM Warning 
        is detected on the Client Trscv 
        Network Interface <Condtype> CFP_NETWORK_LANE_ALARM_WARNING_2 
        <Probcause> informationalStatus(1000) 
        <Alarmtype> other (1) <Polarity> 
        (2) 
        "
	  ::= { pm10010ulhAlmclientGlobalAlarmSummary 7 }



pm10010ulhAlmCfpSoftGlobAlarmTest  OBJECT-TYPE
	  SYNTAX EkiOnOff
	  MAX-ACCESS read-only
	  STATUS current
	  DESCRIPTION
        "
        Client Trscv Global Alarm SW Test 
        :This OID indicates the Client
         Trscv Global Alarm This OID is 
        raised by SW request for test purpose 
        <Help> Status indicating the Client 
        Trscv Global Alarm is raised by 
        SW request for test purpose <Condtype> 
        CFP_SOFT_GLOB_ALARM_TEST  <Probcause> 
        informationalStatus(1000) <Alarmtype> 
        other (1) <Polarity> (2) 
        "
	  ::= { pm10010ulhAlmclientGlobalAlarmSummary 1 }



--- *****************************************************
---     LEAF for the msaModuleState article
--- *****************************************************
pm10010ulhAlmmsaModuleState OBJECT IDENTIFIER ::= { pm10010ulhAlmOtherCrit 78 }




pm10010ulhAlmMsaHighPowerDown OBJECT-TYPE
	  SYNTAX EkiOnOff
	  MAX-ACCESS read-only
	  STATUS current
	  DESCRIPTION
        "
        Line Trscv High Power Down :This 
        OID indicates the Line Trscv is 
        entering Low Power state <Help> 
        Status indicating the Line Trscv 
        is entering Low Power state <Condtype> 
        MSA_HIGH_POWER_DOWN <Probcause> 
        informationalStatus(1000) <Alarmtype> 
        other (1) <Polarity> (2) 
        "
	  ::= { pm10010ulhAlmmsaModuleState 9 }



pm10010ulhAlmMsaTxTurnOff OBJECT-TYPE
	  SYNTAX EkiOnOff
	  MAX-ACCESS read-only
	  STATUS current
	  DESCRIPTION
        "
        Line Trscv Laser Turn Off :This 
        OID indicates the Line Trscv is 
        turning off its laser <Help> Status 
        indicating the Line Trscv is turning 
        off its laser <Condtype> MSA_TX_TURN_OFF 
        <Probcause> informationalStatus(1000) 
        <Alarmtype> other (1) <Polarity> 
        (2) 
        "
	  ::= { pm10010ulhAlmmsaModuleState 8 }



pm10010ulhAlmMsaFault OBJECT-TYPE
	  SYNTAX EkiOnOff
	  MAX-ACCESS read-only
	  STATUS current
	  DESCRIPTION
        "
        Line Trscv Fault :This OID indicates 
        the Line Trscv is in Fault state 
        <Help> Status indicating the Line 
        Trscv is in Fault state <Condtype> 
        MSA_FAULT <Probcause> informationalStatus(1000) 
        <Alarmtype> other (1) <Polarity> 
        (2) 
        "
	  ::= { pm10010ulhAlmmsaModuleState 7 }



pm10010ulhAlmMsaReady OBJECT-TYPE
	  SYNTAX EkiOnOff
	  MAX-ACCESS read-only
	  STATUS current
	  DESCRIPTION
        "
        Line Trscv Ready :This OID indicates 
        the Line Trscv is ready to operate 
        <Help> Status indicating the Line 
        Trscv is ready to operate <Condtype> 
        MSA_READY <Probcause> informationalStatus(1000) 
        <Alarmtype> other (1) <Polarity> 
        (2) 
        "
	  ::= { pm10010ulhAlmmsaModuleState 6 }



pm10010ulhAlmMsaTxTurnOn OBJECT-TYPE
	  SYNTAX EkiOnOff
	  MAX-ACCESS read-only
	  STATUS current
	  DESCRIPTION
        "
        Line Trscv Laser Turn On :This 
        OID indicates the Line Trscv is 
        turning on its laser <Help> Status 
        indicating the Line Trscv is turning 
        on its laser <Condtype> MSA_TX_TURN_ON 
        <Probcause> informationalStatus(1000) 
        <Alarmtype> other (1) <Polarity> 
        (2) 
        "
	  ::= { pm10010ulhAlmmsaModuleState 5 }



pm10010ulhAlmMsaTxOff OBJECT-TYPE
	  SYNTAX EkiOnOff
	  MAX-ACCESS read-only
	  STATUS current
	  DESCRIPTION
        "
        Line Trscv Laser Shutdown :This 
        OID indicates the Line Trscv Laser 
        is OFF <Help> Status indicating 
        the Line Trscv Laser is OFF <Condtype> 
        MSA_TX_OFF <Probcause> informationalStatus(1000) 
        <Alarmtype> other (1) <Polarity> 
        (2) 
        "
	  ::= { pm10010ulhAlmmsaModuleState 4 }



pm10010ulhAlmMsaHighPowerUp OBJECT-TYPE
	  SYNTAX EkiOnOff
	  MAX-ACCESS read-only
	  STATUS current
	  DESCRIPTION
        "
        Line Trscv High Power Up :This 
        OID indicates the Line Trscv is 
        leaving Low Power state <Help>
         Status indicating the Line Trscv 
        is leaving Low Power state <Condtype> 
        MSA_HIGH_POWER_UP <Probcause> informationalStatus(1000) 
        <Alarmtype> other (1) <Polarity> 
        (2) 
        "
	  ::= { pm10010ulhAlmmsaModuleState 3 }



pm10010ulhAlmMsaLowPower OBJECT-TYPE
	  SYNTAX EkiOnOff
	  MAX-ACCESS read-only
	  STATUS current
	  DESCRIPTION
        "
        Line Trscv Low Power :This OID 
        indicates the Line Trscv is in
         low power state <Help> Status
         indicating the Line Trscv is in 
        low power state <Condtype> MSA_LOW_POWER 
        <Probcause> informationalStatus(1000) 
        <Alarmtype> other (1) <Polarity> 
        (2) 
        "
	  ::= { pm10010ulhAlmmsaModuleState 2 }



pm10010ulhAlmMsaInitialize OBJECT-TYPE
	  SYNTAX EkiOnOff
	  MAX-ACCESS read-only
	  STATUS current
	  DESCRIPTION
        "
        Line Trscv Initialize :This OID 
        indicates the Line Trscv initialization 
        is in progress <Help> Status indicating 
        the Line Trscv initialization is 
        in progress <Condtype> MSA_INITIALIZE 
        <Probcause> informationalStatus(1000) 
        <Alarmtype> other (1) <Polarity> 
        (2) 
        "
	  ::= { pm10010ulhAlmmsaModuleState 1 }



--- *****************************************************
---     LEAF for the msaModuleGeneralStatus article
--- *****************************************************
pm10010ulhAlmmsaModuleGeneralStatus OBJECT IDENTIFIER ::= { pm10010ulhAlmOtherCrit 79 }




pm10010ulhAlmMsaHwInterlock OBJECT-TYPE
	  SYNTAX EkiOnOff
	  MAX-ACCESS read-only
	  STATUS current
	  DESCRIPTION
        "
        Line Trscv Hardware Interlock
         :This OID indicates the Line Trscv 
        power is higher than the cooling 
        capacity <Help> Alarm indicating 
        the Line Trscv power is higher
         than the cooling capacity <Condtype> 
        MSA_HW_INTERLOCK <Probcause> temperatureUnacceptable 
        (51) <Alarmtype> equipmentAlarm 
        (5) <Polarity> (2) 
        "
	  ::= { pm10010ulhAlmmsaModuleGeneralStatus 14 }



pm10010ulhAlmMsaLossOfRefclk OBJECT-TYPE
	  SYNTAX EkiOnOff
	  MAX-ACCESS read-only
	  STATUS current
	  DESCRIPTION
        "
        Line Trscv Loss Of Ref Clock :This 
        OID indicates a Loss of Reference 
        clock is detected on the Line Trscv 
        <Help> Alarm indicating a Loss
         of Reference clock is detected 
        on the Line Trscv <Condtype> MSA_LOSS_OF_REFCLK 
        <Probcause> inputOutputDeviceError 
        (24) <Alarmtype> equipmentAlarm 
        (5) <Polarity> (2) 
        "
	  ::= { pm10010ulhAlmmsaModuleGeneralStatus 11 }



pm10010ulhAlmMsaTxJitterPllLol OBJECT-TYPE
	  SYNTAX EkiOnOff
	  MAX-ACCESS read-only
	  STATUS current
	  DESCRIPTION
        "
        Line Trscv Tx Jitter PLL Loss
         Of Lock :This OID indicates a
         Tx Jitter PLL Loss of Lock is
         detected on the Line Trscv <Help> 
        Alarm indicating a Tx Jitter PLL 
        Loss of Lock is detected on the 
        Line Trscv <Condtype> MSA_TX_JITTER_PLL_LOL 
        <Probcause> inputOutputDeviceError 
        (24) <Alarmtype> equipmentAlarm 
        (5) <Polarity> (2) 
        "
	  ::= { pm10010ulhAlmmsaModuleGeneralStatus 10 }



pm10010ulhAlmMsaTxCmuLol OBJECT-TYPE
	  SYNTAX EkiOnOff
	  MAX-ACCESS read-only
	  STATUS current
	  DESCRIPTION
        "
        Line Trscv CMU Loss Of Lock :This 
        OID indicates a Clock Multiplier 
        Unit Loss of Lock is detected on 
        the Line Trscv <Help> Alarm indicating 
        a Clock Multiplier Unit Loss of 
        Lock is detected on the Line Trscv 
        <Condtype> MSA_TX_CMU_LOL <Probcause> 
        inputOutputDeviceError (24) <Alarmtype> 
        equipmentAlarm (5) <Polarity> (2) 
        "
	  ::= { pm10010ulhAlmmsaModuleGeneralStatus 9 }



pm10010ulhAlmMsaTxLosf OBJECT-TYPE
	  SYNTAX EkiOnOff
	  MAX-ACCESS read-only
	  STATUS current
	  DESCRIPTION
        "
        Line Trscv Loss Of Signal Functionality 
        :This OID indicates a Loss of Signal 
        functionality is detected on the 
        Line Trscv <Help> Alarm indicating 
        a Loss of Signal functionality
         is detected on the Line Trscv
         <Condtype> MSA_TX_LOSF <Probcause> 
        lossOfSignal (30) <Alarmtype> equipmentAlarm 
        (5) <Polarity> (2) 
        "
	  ::= { pm10010ulhAlmmsaModuleGeneralStatus 8 }



pm10010ulhAlmMsaTxHostLol OBJECT-TYPE
	  SYNTAX EkiOnOff
	  MAX-ACCESS read-only
	  STATUS current
	  DESCRIPTION
        "
        Line Trscv Tx Host Loss Of Lock 
        :This OID indicates of Loss of
         Lock is detected on the Line Trscv 
        Tx Host interface <Help> Alarm
         indicating of Loss of Lock is
         detected on the Line Trscv Tx
         Host interface <Condtype> MSA_TX_HOST_LOL 
        <Probcause> receiverFailure (42) 
        <Alarmtype> equipmentAlarm (5)
         <Polarity> (2) 
        "
	  ::= { pm10010ulhAlmmsaModuleGeneralStatus 7 }



pm10010ulhAlmMsaRxLos OBJECT-TYPE
	  SYNTAX EkiOnOff
	  MAX-ACCESS read-only
	  STATUS current
	  DESCRIPTION
        "
        Line Trscv Loss Of Signal :This 
        OID indicates a Loss of Signal
         is detected on the Line Trscv
         <Help> Alarm indicating a Loss 
        of Signal is detected on the Line 
        Trscv <Condtype> MSA_RX_LOS <Probcause> 
        lossOfSignal (30) <Alarmtype> equipmentAlarm 
        (5) <Polarity> (2) 
        "
	  ::= { pm10010ulhAlmmsaModuleGeneralStatus 6 }



pm10010ulhAlmMsaRxNetworkLol OBJECT-TYPE
	  SYNTAX EkiOnOff
	  MAX-ACCESS read-only
	  STATUS current
	  DESCRIPTION
        "
        Line Trscv Rx Network Loss Of
         Lock :This OID indicates of Loss 
        of Lock is detected on the Line 
        Trscv Rx Network interface <Help> 
        Alarm indicating of Loss of Lock 
        is detected on the Line Trscv Rx 
        Network interface <Condtype> MSA_RX_NETWORK_LOL 
        <Probcause> receiverFailure (42) 
        <Alarmtype> equipmentAlarm (5)
         <Polarity> (2) 
        "
	  ::= { pm10010ulhAlmmsaModuleGeneralStatus 5 }



pm10010ulhAlmMsaOutOfAlignment OBJECT-TYPE
	  SYNTAX EkiOnOff
	  MAX-ACCESS read-only
	  STATUS current
	  DESCRIPTION
        "
        Line Trscv Out Of Alignment :This 
        OID indicates an Out of alignment 
        on the Line Trscv Host Interface 
        <Help> Alarm indicating an Out
         of alignment on the Line Trscv 
        Host Interface <Condtype> MSA_OUT_OF_ALIGNMENT 
        <Probcause> receiverFailure (42) 
        <Alarmtype> equipmentAlarm (5)
         <Polarity> (2) 
        "
	  ::= { pm10010ulhAlmmsaModuleGeneralStatus 4 }



--- *****************************************************
---     LEAF for the msaGlobalAlarmSummary article
--- *****************************************************
pm10010ulhAlmmsaGlobalAlarmSummary OBJECT IDENTIFIER ::= { pm10010ulhAlmOtherCrit 80 }




pm10010ulhAlmMsaGlobAlarmAssertion  OBJECT-TYPE
	  SYNTAX EkiOnOff
	  MAX-ACCESS read-only
	  STATUS current
	  DESCRIPTION
        "
        Line Trscv Global Alarm :This
         OID indicates at least one Fault 
        or Status is detected on the Line 
        Trscv module <Help> Synthesis alarm 
        indicating at least one Alarm,
         Warning, Fault or Status is detected 
        on the Line Trscv module <Condtype> 
        MSA_GLOB_ALARM_ASSERTION  <Probcause> 
        informationalStatus(1000) <Alarmtype> 
        other (1) <Polarity> (2) 
        "
	  ::= { pm10010ulhAlmmsaGlobalAlarmSummary 16 }



pm10010ulhAlmMsaHostLaneFaultStatus  OBJECT-TYPE
	  SYNTAX EkiOnOff
	  MAX-ACCESS read-only
	  STATUS current
	  DESCRIPTION
        "
        Line Trscv Host Fault And Status 
        :This OID indicates at least one 
        Fault or Status is detected on
         the Line Trscv Host Interface
         <Help> Synthesis alarm indicating 
        at least one Fault or Status is 
        detected on the Line Trscv Host 
        Interface <Condtype> MSA_HOST_LANE_FAULT_STATUS 
         <Probcause> informationalStatus(1000) 
        <Alarmtype> other (1) <Polarity> 
        (2) 
        "
	  ::= { pm10010ulhAlmmsaGlobalAlarmSummary 15 }



pm10010ulhAlmMsaNetworkLaneFaultStatus  OBJECT-TYPE
	  SYNTAX EkiOnOff
	  MAX-ACCESS read-only
	  STATUS current
	  DESCRIPTION
        "
        Line Trscv Network Fault And Status 
        :This OID indicates at least one 
        Fault or Status is detected on
         the Line Trscv Network Interface 
        <Help> Synthesis alarm indicating 
        at least one Fault or Status is 
        detected on the Line Trscv Network 
        Interface <Condtype> MSA_NETWORK_LANE_FAULT_STATUS 
         <Probcause> informationalStatus(1000) 
        <Alarmtype> other (1) <Polarity> 
        (2) 
        "
	  ::= { pm10010ulhAlmmsaGlobalAlarmSummary 14 }



pm10010ulhAlmMsaNetworkLaneAlarmWarning1 OBJECT-TYPE
	  SYNTAX EkiOnOff
	  MAX-ACCESS read-only
	  STATUS current
	  DESCRIPTION
        "
        Line Trscv Network Alarm And Warning 
        1 :This OID indicates at least
         one DDM is detected on the Line 
        Trscv Network Interface <Help>
         Synthesis alarm indicating at
         least one DDM Alarm or DDM Warning 
        is detected on the Line Trscv Network 
        Interface <Condtype> MSA_NETWORK_LANE_ALARM_WARNING_1 
        <Probcause> informationalStatus(1000) 
        <Alarmtype> other (1) <Polarity> 
        (2) 
        "
	  ::= { pm10010ulhAlmmsaGlobalAlarmSummary 13 }



pm10010ulhAlmMsaModuleAlarmWarning2 OBJECT-TYPE
	  SYNTAX EkiOnOff
	  MAX-ACCESS read-only
	  STATUS current
	  DESCRIPTION
        "
        Line Trscv Module Alarm And Warning 
        2 :This OID indicates at least
         one DDM is detected on the Line 
        Trscv module <Help> Synthesis alarm 
        indicating at least one DDM Alarm 
        or DDM Warning is detected on the 
        Line Trscv module <Condtype> MSA_MODULE_ALARM_WARNING_2 
        <Probcause> informationalStatus(1000) 
        <Alarmtype> other (1) <Polarity> 
        (2) 
        "
	  ::= { pm10010ulhAlmmsaGlobalAlarmSummary 12 }



pm10010ulhAlmMsaModuleAlarmWarning1  OBJECT-TYPE
	  SYNTAX EkiOnOff
	  MAX-ACCESS read-only
	  STATUS current
	  DESCRIPTION
        "
        Line Trscv Module Alarm And Warning 
        1 :This OID indicates at least
         one DDM is detected on the Line 
        Trscv module <Help> Synthesis alarm 
        indicating at least one DDM Alarm 
        or DDM Warning is detected on the 
        Line Trscv module <Condtype> MSA_MODULE_ALARM_WARNING_1 
         <Probcause> informationalStatus(1000) 
        <Alarmtype> other (1) <Polarity> 
        (2) 
        "
	  ::= { pm10010ulhAlmmsaGlobalAlarmSummary 11 }



pm10010ulhAlmModuleFault  OBJECT-TYPE
	  SYNTAX EkiOnOff
	  MAX-ACCESS read-only
	  STATUS current
	  DESCRIPTION
        "
        Line Trscv Module Fault :This
         OID indicates at least one Fault 
        is detected on the Line Trscv module 
        <Help> Synthesis alarm indicating 
        at least one Fault is detected
         on the Line Trscv module <Condtype> 
        MODULE_FAULT  <Probcause> informationalStatus(1000) 
        <Alarmtype> other (1) <Polarity> 
        (2) 
        "
	  ::= { pm10010ulhAlmmsaGlobalAlarmSummary 10 }



pm10010ulhAlmMsaModuleGeneralStatus  OBJECT-TYPE
	  SYNTAX EkiOnOff
	  MAX-ACCESS read-only
	  STATUS current
	  DESCRIPTION
        "
        Line Trscv General Status :This 
        OID indicates the Line Trscv module 
        general <Help> Synthesis alarm
         indicating the Line Trscv module 
        general status <Condtype> MSA_MODULE_GENERAL_STATUS 
         <Probcause> informationalStatus(1000) 
        <Alarmtype> other (1) <Polarity> 
        (2) 
        "
	  ::= { pm10010ulhAlmmsaGlobalAlarmSummary 9 }



pm10010ulhAlmMsaModuleState  OBJECT-TYPE
	  SYNTAX EkiOnOff
	  MAX-ACCESS read-only
	  STATUS current
	  DESCRIPTION
        "
        Line Trscv Module State :This
         OID indicates the Line Trscv module 
        state <Help> Synthesis alarm indicating 
        the Line Trscv module state <Condtype> 
        MSA_MODULE_STATE  <Probcause> informationalStatus(1000) 
        <Alarmtype> other (1) <Polarity> 
        (2) 
        "
	  ::= { pm10010ulhAlmmsaGlobalAlarmSummary 8 }



pm10010ulhAlmMsaNetworkLaneAlarmWarning2 OBJECT-TYPE
	  SYNTAX EkiOnOff
	  MAX-ACCESS read-only
	  STATUS current
	  DESCRIPTION
        "
        Line Trscv Network Alarm And Warning 
        2 :This OID indicates at least
         one DDM This OID is detected on 
        the Line Trscv Network Interface 
        <Help> Synthesis alarm indicating 
        at least one DDM Alarm or DDM Warning 
        is detected on the Line Trscv Network 
        Interface <Condtype> MSA_NETWORK_LANE_ALARM_WARNING_2 
        <Probcause> informationalStatus(1000) 
        <Alarmtype> other (1) <Polarity> 
        (2) 
        "
	  ::= { pm10010ulhAlmmsaGlobalAlarmSummary 7 }



pm10010ulhAlmMsaNetworkHostAlarmStatus OBJECT-TYPE
	  SYNTAX EkiOnOff
	  MAX-ACCESS read-only
	  STATUS current
	  DESCRIPTION
        "
        Line Trscv Network/Host Alarm
         Status :This OID indicates the 
        state of the Network and Host interface 
        of the Line Trscv <Help> Synthesis 
        alarm indicating the alarm state 
        of the Network and Host interface 
        of the Line Trscv <Condtype> MSA_NETWORK_HOST_ALARM_STATUS 
        <Probcause> informationalStatus(1000) 
        <Alarmtype> other (1) <Polarity> 
        (2) 
        "
	  ::= { pm10010ulhAlmmsaGlobalAlarmSummary 6 }



pm10010ulhAlmMsaSoftGlobAlarmTest  OBJECT-TYPE
	  SYNTAX EkiOnOff
	  MAX-ACCESS read-only
	  STATUS current
	  DESCRIPTION
        "
        Line Trscv Global Alarm SW Test 
        :This OID indicates the Line Trscv 
        Global alarm This OID is raised 
        by SW request for test purpose
         <Help> Status indicating the Line 
        Trscv Global Alarm is raised by 
        SW request for test purpose <Condtype> 
        MSA_SOFT_GLOB_ALARM_TEST  <Probcause> 
        informationalStatus(1000) <Alarmtype> 
        other (1) <Polarity> (2) 
        "
	  ::= { pm10010ulhAlmmsaGlobalAlarmSummary 1 }



--- *****************************************************
---     LEAF for the msaNetworkTxAlignment article
--- *****************************************************
pm10010ulhAlmmsaNetworkTxAlignment OBJECT IDENTIFIER ::= { pm10010ulhAlmOtherCrit 81 }




pm10010ulhAlmNetTxLossOfAlignment OBJECT-TYPE
	  SYNTAX EkiOnOff
	  MAX-ACCESS read-only
	  STATUS current
	  DESCRIPTION
        "
        Line Trscv Network Tx Loss Of
         Alignment :This OID indicates
         a Tx Loss of Alignment is detected 
        on the Line Trscv Network interface 
        <Help> Alarm indicating a Tx Loss 
        of Alignment is detected on the 
        Line Trscv Network interface <Condtype> 
        NET_TX_LOSS_OF_ALIGNMENT <Probcause> 
        transmitterFailure (56) <Alarmtype> 
        equipmentAlarm (5) <Polarity> (2) 
        "
	  ::= { pm10010ulhAlmmsaNetworkTxAlignment 16 }



pm10010ulhAlmNetTxOutOfAlignment OBJECT-TYPE
	  SYNTAX EkiOnOff
	  MAX-ACCESS read-only
	  STATUS current
	  DESCRIPTION
        "
        Line Trscv Network Tx Out Of Alignment 
        :This OID indicates a Tx Out of 
        Alignment is detected on the Line 
        Trscv Network interface <Help>
         Alarm indicating a Tx Out of Alignment 
        is detected on the Line Trscv Network 
        interface <Condtype> NET_TX_OUT_OF_ALIGNMENT 
        <Probcause> transmitterFailure
         (56) <Alarmtype> equipmentAlarm 
        (5) <Polarity> (2) 
        "
	  ::= { pm10010ulhAlmmsaNetworkTxAlignment 15 }



pm10010ulhAlmNetTxCmuLockFault OBJECT-TYPE
	  SYNTAX EkiOnOff
	  MAX-ACCESS read-only
	  STATUS current
	  DESCRIPTION
        "
        Line Trscv Network Tx CMU Lock 
        Fault :This OID indicates a Tx
         Clock Multiplier Unit Lock Fault 
        is detected on the Line Trscv Network 
        interface <Help> Alarm indicating 
        a Tx Clock Multiplier Unit Lock 
        Fault is detected on the Line Trscv 
        Network interface <Condtype> NET_TX_CMU_LOCK_FAULT 
        <Probcause> transmitterFailure
         (56) <Alarmtype> equipmentAlarm 
        (5) <Polarity> (2) 
        "
	  ::= { pm10010ulhAlmmsaNetworkTxAlignment 14 }



pm10010ulhAlmNetTxReferenceClockFault OBJECT-TYPE
	  SYNTAX EkiOnOff
	  MAX-ACCESS read-only
	  STATUS current
	  DESCRIPTION
        "
        Line Trscv Network Tx Ref Clock 
        Fault :This OID indicates a Tx
         Reference Clock Fault is detected 
        on the Line Trscv Network interface 
        <Help> Alarm indicating a Tx Reference 
        Clock Fault is detected on the
         Line Trscv Network interface <Condtype> 
        NET_TX_REFERENCE_CLOCK_FAULT <Probcause> 
        transmitterFailure (56) <Alarmtype> 
        equipmentAlarm (5) <Polarity> (2) 
        "
	  ::= { pm10010ulhAlmmsaNetworkTxAlignment 13 }



pm10010ulhAlmNetTxTimingFault OBJECT-TYPE
	  SYNTAX EkiOnOff
	  MAX-ACCESS read-only
	  STATUS current
	  DESCRIPTION
        "
        Line Trscv Network Tx Timing Fault 
        :This OID indicates a Tx Timing 
        Fault is detected on the Line Trscv 
        Network interface <Help> Alarm
         indicating a Tx Timing Fault is 
        detected on the Line Trscv Network 
        interface <Condtype> NET_TX_TIMING_FAULT 
        <Probcause> transmitterFailure
         (56) <Alarmtype> equipmentAlarm 
        (5) <Polarity> (2) 
        "
	  ::= { pm10010ulhAlmmsaNetworkTxAlignment 12 }



--- *****************************************************
---     LEAF for the msaNetworkRxAlignment article
--- *****************************************************
pm10010ulhAlmmsaNetworkRxAlignment OBJECT IDENTIFIER ::= { pm10010ulhAlmOtherCrit 82 }




pm10010ulhAlmNetRxModemSyncDetectFault OBJECT-TYPE
	  SYNTAX EkiOnOff
	  MAX-ACCESS read-only
	  STATUS current
	  DESCRIPTION
        "
        Line Trscv Network Rx Modem Sync 
        Detect Fault :This OID indicates 
        a Rx Modem Synchronisation Detection 
        Fault is detected on the Line Trscv 
        Network interface <Help> Alarm
         indicating a Rx Modem Synchronisation 
        Detection Fault is detected on
         the Line Trscv Network interface 
        <Condtype> NET_RX_MODEM_SYNC_DETECT_FAULT 
        <Probcause> receiverFailure (42) 
        <Alarmtype> equipmentAlarm (5)
         <Polarity> (2) 
        "
	  ::= { pm10010ulhAlmmsaNetworkRxAlignment 16 }



pm10010ulhAlmNetRxModemLockFault OBJECT-TYPE
	  SYNTAX EkiOnOff
	  MAX-ACCESS read-only
	  STATUS current
	  DESCRIPTION
        "
        Line Trscv Network Rx Modem Lock 
        Fault :This OID indicates a Rx
         Modem Lock Fault is detected on 
        the Line Trscv Network interface 
        <Help> Alarm indicating a Rx Modem 
        Lock Fault is detected on the Line 
        Trscv Network interface <Condtype> 
        NET_RX_MODEM_LOCK_FAULT <Probcause> 
        receiverFailure (42) <Alarmtype> 
        equipmentAlarm (5) <Polarity> (2) 
        "
	  ::= { pm10010ulhAlmmsaNetworkRxAlignment 15 }



pm10010ulhAlmNetRxLossOfAlignment OBJECT-TYPE
	  SYNTAX EkiOnOff
	  MAX-ACCESS read-only
	  STATUS current
	  DESCRIPTION
        "
        Line Trscv Network Rx Loss Of
         Alignment :This OID indicates
         a Rx Loss of Alignment is detected 
        on the Line Trscv Network interface 
        <Help> Alarm indicating a Rx Loss 
        of Alignment is detected on the 
        Line Trscv Network interface <Condtype> 
        NET_RX_LOSS_OF_ALIGNMENT <Probcause> 
        receiverFailure (42) <Alarmtype> 
        equipmentAlarm (5) <Polarity> (2) 
        "
	  ::= { pm10010ulhAlmmsaNetworkRxAlignment 14 }



pm10010ulhAlmNetRxOutOfAlignment OBJECT-TYPE
	  SYNTAX EkiOnOff
	  MAX-ACCESS read-only
	  STATUS current
	  DESCRIPTION
        "
        Line Trscv Network Rx Out Of Alignment 
        :This OID indicates a Rx Out of 
        Alignment is detected on the Line 
        Trscv Network interface <Help>
         Alarm indicating a Rx Out of Alignment 
        is detected on the Line Trscv Network 
        interface <Condtype> NET_RX_OUT_OF_ALIGNMENT 
        <Probcause> receiverFailure (42) 
        <Alarmtype> equipmentAlarm (5)
         <Polarity> (2) 
        "
	  ::= { pm10010ulhAlmmsaNetworkRxAlignment 13 }



pm10010ulhAlmNetRxTimingFault OBJECT-TYPE
	  SYNTAX EkiOnOff
	  MAX-ACCESS read-only
	  STATUS current
	  DESCRIPTION
        "
        Line Trscv Network Rx Timing Fault 
        :This OID indicates a Rx Timing 
        Fault is detected on the Line Trscv 
        Network interface <Help> Alarm
         indicating a Rx Timing Fault is 
        detected on the Line Trscv Network 
        interface <Condtype> NET_RX_TIMING_FAULT 
        <Probcause> receiverFailure (42) 
        <Alarmtype> equipmentAlarm (5)
         <Polarity> (2) 
        "
	  ::= { pm10010ulhAlmmsaNetworkRxAlignment 12 }



--- *****************************************************
---     LEAF for the msaNetworkHostNetworkAlarmSummary article
--- *****************************************************
pm10010ulhAlmmsaNetworkHostNetworkAlarmSummary OBJECT IDENTIFIER ::= { pm10010ulhAlmOtherCrit 83 }




pm10010ulhAlmHostTxOtnStatus OBJECT-TYPE
	  SYNTAX EkiOnOff
	  MAX-ACCESS read-only
	  STATUS current
	  DESCRIPTION
        "
        Line Trscv Host Tx OTN :This OID 
        indicates a Tx OTN Fault is detected 
        on the Line Trscv Host interface 
        <Help> Synthesis Alarm indicating 
        a Tx OTN Fault is detected on the 
        Line Trscv Host interface <Condtype> 
        HOST_TX_OTN_STATUS <Probcause>
         informationalStatus(1000) <Alarmtype> 
        other (1) <Polarity> (2) 
        "
	  ::= { pm10010ulhAlmmsaNetworkHostNetworkAlarmSummary 16 }



pm10010ulhAlmHostTxAlignment OBJECT-TYPE
	  SYNTAX EkiOnOff
	  MAX-ACCESS read-only
	  STATUS current
	  DESCRIPTION
        "
        Line Trscv Host Tx Alignment :This 
        OID indicates a Tx Alignment Fault 
        is detected on the Line Trscv Host 
        interface <Help> Synthesis Alarm 
        indicating a Tx Alignment Fault 
        is detected on the Line Trscv Host 
        interface <Condtype> HOST_TX_ALIGNMENT 
        <Probcause> informationalStatus(1000) 
        <Alarmtype> other (1) <Polarity> 
        (2) 
        "
	  ::= { pm10010ulhAlmmsaNetworkHostNetworkAlarmSummary 15 }



pm10010ulhAlmHostRxAlignment OBJECT-TYPE
	  SYNTAX EkiOnOff
	  MAX-ACCESS read-only
	  STATUS current
	  DESCRIPTION
        "
        Line Trscv Host Rx Alignment :This 
        OID indicates a Rx Alignment Fault 
        is detected on the Line Trscv Host 
        interface <Help> Synthesis Alarm 
        indicating a Rx Alignment Fault 
        is detected on the Line Trscv Host 
        interface <Condtype> HOST_RX_ALIGNMENT 
        <Probcause> informationalStatus(1000) 
        <Alarmtype> other (1) <Polarity> 
        (2) 
        "
	  ::= { pm10010ulhAlmmsaNetworkHostNetworkAlarmSummary 14 }



pm10010ulhAlmNetworkRxOtn OBJECT-TYPE
	  SYNTAX EkiOnOff
	  MAX-ACCESS read-only
	  STATUS current
	  DESCRIPTION
        "
        Line Trscv Network Rx OTN :This 
        OID indicates a Rx OTN Fault is 
        detected on the Line Trscv Network 
        interface <Help> Synthesis Alarm 
        indicating a Rx OTN Fault is detected 
        on the Line Trscv Network interface 
        <Condtype> NETWORK_RX_OTN <Probcause> 
        informationalStatus(1000) <Alarmtype> 
        other (1) <Polarity> (2) 
        "
	  ::= { pm10010ulhAlmmsaNetworkHostNetworkAlarmSummary 13 }



pm10010ulhAlmNetworkRxAlignment OBJECT-TYPE
	  SYNTAX EkiOnOff
	  MAX-ACCESS read-only
	  STATUS current
	  DESCRIPTION
        "
        Line Trscv Network Rx Alignment 
        :This OID indicates a Rx Alignment 
        Fault is detected on the Line Trscv 
        Network interface <Help> Synthesis 
        Alarm indicating a Rx Alignment 
        Fault is detected on the Line Trscv 
        Network interface <Condtype> NETWORK_RX_ALIGNMENT 
        <Probcause> informationalStatus(1000) 
        <Alarmtype> other (1) <Polarity> 
        (2) 
        "
	  ::= { pm10010ulhAlmmsaNetworkHostNetworkAlarmSummary 12 }



pm10010ulhAlmNetworkTxAlignment OBJECT-TYPE
	  SYNTAX EkiOnOff
	  MAX-ACCESS read-only
	  STATUS current
	  DESCRIPTION
        "
        Line Trscv Network Tx Alignment 
        :This OID indicates a Tx Alignment 
        Fault is detected on the Line Trscv 
        Network interface <Help> Synthesis 
        Alarm indicating a Tx Alignment 
        Fault is detected on the Line Trscv 
        Network interface <Condtype> NETWORK_TX_ALIGNMENT 
        <Probcause> informationalStatus(1000) 
        <Alarmtype> other (1) <Polarity> 
        (2) 
        "
	  ::= { pm10010ulhAlmmsaNetworkHostNetworkAlarmSummary 11 }



--- *****************************************************
---     LEAF for the msaHostTxAlignment article
--- *****************************************************
pm10010ulhAlmmsaHostTxAlignment OBJECT IDENTIFIER ::= { pm10010ulhAlmOtherCrit 84 }




pm10010ulhAlmHostTxCdrLockFault OBJECT-TYPE
	  SYNTAX EkiOnOff
	  MAX-ACCESS read-only
	  STATUS current
	  DESCRIPTION
        "
        Line Trscv Host Tx CDR Lock Fault 
        :This OID indicates a Tx Clock
         Data Recovery Lock Fault is detected 
        on the Line Trscv Host interface 
        <Help> Alarm indicating a Tx Clock 
        Data Recovery Lock Fault is detected 
        on the Line Trscv Host interface 
        <Condtype> HOST_TX_CDR_LOCK_FAULT 
        <Probcause> receiverFailure (42) 
        <Alarmtype> equipmentAlarm (5)
         <Polarity> (2) 
        "
	  ::= { pm10010ulhAlmmsaHostTxAlignment 16 }



pm10010ulhAlmHostTxLossOfAlignment OBJECT-TYPE
	  SYNTAX EkiOnOff
	  MAX-ACCESS read-only
	  STATUS current
	  DESCRIPTION
        "
        Line Trscv Host Tx Loss Of Alignment 
        :This OID indicates a Tx Loss of 
        Alignment is detected on the Line 
        Trscv Host interface <Help> Alarm 
        indicating a Tx Loss of Alignment 
        is detected on the Line Trscv Host 
        interface <Condtype> HOST_TX_LOSS_OF_ALIGNMENT 
        <Probcause> receiverFailure (42) 
        <Alarmtype> equipmentAlarm (5)
         <Polarity> (2) 
        "
	  ::= { pm10010ulhAlmmsaHostTxAlignment 15 }



pm10010ulhAlmHostTxOutOfAlignment OBJECT-TYPE
	  SYNTAX EkiOnOff
	  MAX-ACCESS read-only
	  STATUS current
	  DESCRIPTION
        "
        Line Trscv Host Tx Out Of Alignment 
        :This OID indicates a Tx Out of 
        Alignment is detected on the Line 
        Trscv Host interface <Help> Alarm 
        indicating a Tx Out of Alignment 
        is detected on the Line Trscv Host 
        interface <Condtype> HOST_TX_OUT_OF_ALIGNMENT 
        <Probcause> receiverFailure (42) 
        <Alarmtype> equipmentAlarm (5)
         <Polarity> (2) 
        "
	  ::= { pm10010ulhAlmmsaHostTxAlignment 14 }



pm10010ulhAlmHostTxDeskewLockFault OBJECT-TYPE
	  SYNTAX EkiOnOff
	  MAX-ACCESS read-only
	  STATUS current
	  DESCRIPTION
        "
        Line Trscv Host Tx Deskew Lock 
        Fault :This OID indicates a Tx
         Deskew Lock Fault is detected
         on  the Line Trscv Host interface 
        <Help> Alarm indicating a Tx Deskew 
        Lock Fault is detected on  the
         Line Trscv Host interface <Condtype> 
        HOST_TX_DESKEW_LOCK_FAULT <Probcause> 
        receiverFailure (42) <Alarmtype> 
        equipmentAlarm (5) <Polarity> (2) 
        "
	  ::= { pm10010ulhAlmmsaHostTxAlignment 13 }



--- *****************************************************
---     LEAF for the msaHostRxAlignment article
--- *****************************************************
pm10010ulhAlmmsaHostRxAlignment OBJECT IDENTIFIER ::= { pm10010ulhAlmOtherCrit 85 }




pm10010ulhAlmHostRxLossOfAlignment OBJECT-TYPE
	  SYNTAX EkiOnOff
	  MAX-ACCESS read-only
	  STATUS current
	  DESCRIPTION
        "
        Line Trscv Host Rx Loss Of Alignment 
        :This OID indicates a Rx Loss of 
        Alignment is detected on the Line 
        Trscv Host interface <Help> Alarm 
        indicating a Rx Loss of Alignment 
        is detected on the Line Trscv Host 
        interface <Condtype> HOST_RX_LOSS_OF_ALIGNMENT 
        <Probcause> transmitterFailure
         (56) <Alarmtype> equipmentAlarm 
        (5) <Polarity> (2) 
        "
	  ::= { pm10010ulhAlmmsaHostRxAlignment 16 }



pm10010ulhAlmHostRxOutOfAlignment OBJECT-TYPE
	  SYNTAX EkiOnOff
	  MAX-ACCESS read-only
	  STATUS current
	  DESCRIPTION
        "
        Line Trscv Host Rx Out Of Alignment 
        :This OID indicates a Rx Out of 
        Alignment is detected on the Line 
        Trscv Host interface <Help> Alarm 
        indicating a Rx Out of Alignment 
        is detected on the Line Trscv Host 
        interface <Condtype> HOST_RX_OUT_OF_ALIGNMENT 
        <Probcause> transmitterFailure
         (56) <Alarmtype> equipmentAlarm 
        (5) <Polarity> (2) 
        "
	  ::= { pm10010ulhAlmmsaHostRxAlignment 15 }



pm10010ulhAlmHostRxCmuLockFault OBJECT-TYPE
	  SYNTAX EkiOnOff
	  MAX-ACCESS read-only
	  STATUS current
	  DESCRIPTION
        "
        Line Trscv Host Rx CMU Lock Fault 
        :This OID indicates a Rx Clock
         Multiplier Unit Lock Fault is
         detected on the Line Trscv Host 
        interface <Help> Alarm indicating 
        a Rx Clock Multiplier Unit Lock 
        Fault is detected on the Line Trscv 
        Host interface <Condtype> HOST_RX_CMU_LOCK_FAULT 
        <Probcause> transmitterFailure
         (56) <Alarmtype> equipmentAlarm 
        (5) <Polarity> (2) 
        "
	  ::= { pm10010ulhAlmmsaHostRxAlignment 14 }



--- *********************************************************
---     TABLE for the pm10010ulhAlmclientNetworkLaneAlarmWarning articles
--- *********************************************************

pm10010ulhAlmclientNetworkLaneAlarmWarningTable OBJECT-TYPE
	SYNTAX  SEQUENCE OF Pm10010ulhAlmclientNetworkLaneAlarmWarningEntry
	MAX-ACCESS not-accessible
	STATUS current
	DESCRIPTION
        "
        List of pm10010ulhAlmclientNetworkLaneAlarmWarning 
        Article
        "
	::= { pm10010ulhAlmClientNurg 88 }


pm10010ulhAlmclientNetworkLaneAlarmWarningEntry OBJECT-TYPE
	SYNTAX Pm10010ulhAlmclientNetworkLaneAlarmWarningEntry
	MAX-ACCESS not-accessible
	STATUS current
	DESCRIPTION
        "
        Row definition for the pm10010ulhAlmclientNetworkLaneAlarmWarning 
        table
        "
	INDEX   { pm10010ulhAlmclientNetworkLaneAlarmWarningIndex }
	::= { pm10010ulhAlmclientNetworkLaneAlarmWarningTable 1 }


Pm10010ulhAlmclientNetworkLaneAlarmWarningEntry ::=
	SEQUENCE {
	pm10010ulhAlmclientNetworkLaneAlarmWarningIndex
		INTEGER,
	pm10010ulhAlmClientBiasHighAlarmPortn
		EkiOnOff,
	pm10010ulhAlmClientBiasHighWarningPortn
		EkiOnOff,
	pm10010ulhAlmClientBiasLowWarningPortn
		EkiOnOff,
	pm10010ulhAlmClientBiasLowAlarmPortn
		EkiOnOff,
	pm10010ulhAlmClientTxPowerHighAlarmPortn
		EkiOnOff,
	pm10010ulhAlmClientTxPowerHighWarningPortn
		EkiOnOff,
	pm10010ulhAlmClientTxPowerLowWarningPortn
		EkiOnOff,
	pm10010ulhAlmClientTxPowerLowAlarmPortn
		EkiOnOff,
	pm10010ulhAlmClientLaserTempHighAlarmPortn
		EkiOnOff,
	pm10010ulhAlmClientLaserTempHighWarningPortn
		EkiOnOff,
	pm10010ulhAlmClientLaserTempLowWarningPortn
		EkiOnOff,
	pm10010ulhAlmLaserTempLowAlarmPortn
		EkiOnOff,
	pm10010ulhAlmClientRxPowerHighAlarmPortn
		EkiOnOff,
	pm10010ulhAlmClientRxPowerHighWarningPortn
		EkiOnOff,
	pm10010ulhAlmClientRxPowerLowWarningPortn
		EkiOnOff,
	pm10010ulhAlmClientRxPowerLowAlarmPortn
		EkiOnOff
	}


pm10010ulhAlmclientNetworkLaneAlarmWarningIndex OBJECT-TYPE
	SYNTAX  INTEGER(0..128)
	MAX-ACCESS  read-only
	STATUS current
	DESCRIPTION
        "
        Index definition for the pm10010ulhAlmclientNetworkLaneAlarmWarning 
        table
        "
	::= { pm10010ulhAlmclientNetworkLaneAlarmWarningEntry 1 }


pm10010ulhAlmClientBiasHighAlarmPortn OBJECT-TYPE
	SYNTAX  EkiOnOff
	MAX-ACCESS read-only
	STATUS current
	DESCRIPTION
        "
        Client Trscv Bias High Alarm :This 
        OID indicates that the Trscv laser 
        bias current is higher than the 
        threshold value written in the
         Trscv EEPROM <Help> Alarm indicating 
        that the Trscv laser bias current 
        is higher than the threshold value 
        written in the Trscv EEPROM <Condtype> 
        CLIENT_BIAS_HIGH_ALARM <Probcause> 
        transmitterFailure (56) <Alarmtype> 
        equipmentAlarm (5) <Polarity> (2) 
        "
	::= { pm10010ulhAlmclientNetworkLaneAlarmWarningEntry 17 }


pm10010ulhAlmClientBiasHighWarningPortn OBJECT-TYPE
	SYNTAX  EkiOnOff
	MAX-ACCESS read-only
	STATUS current
	DESCRIPTION
        "
        Client Trscv Bias High Warning 
        :This OID indicates that the Trscv 
        laser bias current is higher than 
        the threshold value written in
         the Trscv EEPROM <Help> Warning 
        indicating that the Trscv laser 
        bias current is higher than the 
        threshold value written in the
         Trscv EEPROM <Condtype> CLIENT_BIAS_HIGH_WARNING 
        <Probcause> transmitterFailure
         (56) <Alarmtype> equipmentAlarm 
        (5) <Polarity> (2) 
        "
	::= { pm10010ulhAlmclientNetworkLaneAlarmWarningEntry 16 }


pm10010ulhAlmClientBiasLowWarningPortn OBJECT-TYPE
	SYNTAX  EkiOnOff
	MAX-ACCESS read-only
	STATUS current
	DESCRIPTION
        "
        Client Trscv Bias Low Warning
         :This OID indicates that the Trscv 
        laser bias current is lower than 
        the threshold value written in
         the Trscv EEPROM <Help> Warning 
        indicating that the Trscv laser 
        bias current is lower than the
         threshold value written in the 
        Trscv EEPROM <Condtype> CLIENT_BIAS_LOW_WARNING 
        <Probcause> transmitterFailure
         (56) <Alarmtype> equipmentAlarm 
        (5) <Polarity> (2) 
        "
	::= { pm10010ulhAlmclientNetworkLaneAlarmWarningEntry 15 }


pm10010ulhAlmClientBiasLowAlarmPortn OBJECT-TYPE
	SYNTAX  EkiOnOff
	MAX-ACCESS read-only
	STATUS current
	DESCRIPTION
        "
        Client Trscv Bias Low Alarm :This 
        OID indicates that the Trscv laser 
        bias current is lower than the
         threshold value written in the 
        Trscv EEPROM <Help> Alarm indicating 
        that the Trscv laser bias current 
        is lower than the threshold value 
        written in the Trscv EEPROM <Condtype> 
        CLIENT_BIAS_LOW_ALARM <Probcause> 
        transmitterFailure (56) <Alarmtype> 
        equipmentAlarm (5) <Polarity> (2) 
        "
	::= { pm10010ulhAlmclientNetworkLaneAlarmWarningEntry 14 }


pm10010ulhAlmClientTxPowerHighAlarmPortn OBJECT-TYPE
	SYNTAX  EkiOnOff
	MAX-ACCESS read-only
	STATUS current
	DESCRIPTION
        "
        Client Trscv Tx Power High Alarm 
        :This OID indicates that the Trscv 
        output power is higher than the 
        threshold value written in the
         Trscv EEPROM <Help> Alarm indicating 
        that the Trscv output power is
         higher than the threshold value 
        written in the Trscv EEPROM <Condtype> 
        CLIENT_TX_POWER_HIGH_ALARM <Probcause> 
        transmitterFailure (56) <Alarmtype> 
        equipmentAlarm (5) <Polarity> (2) 
        "
	::= { pm10010ulhAlmclientNetworkLaneAlarmWarningEntry 13 }


pm10010ulhAlmClientTxPowerHighWarningPortn OBJECT-TYPE
	SYNTAX  EkiOnOff
	MAX-ACCESS read-only
	STATUS current
	DESCRIPTION
        "
        Client Trscv Tx Power High Warning 
        :This OID indicates that the Trscv 
        output power is higher than the 
        threshold value written in the
         Trscv EEPROM <Help> Warning indicating 
        that the Trscv output power is
         higher than the threshold value 
        written in the Trscv EEPROM <Condtype> 
        CLIENT_TX_POWER_HIGH_WARNING <Probcause> 
        transmitterFailure (56) <Alarmtype> 
        equipmentAlarm (5) <Polarity> (2) 
        "
	::= { pm10010ulhAlmclientNetworkLaneAlarmWarningEntry 12 }


pm10010ulhAlmClientTxPowerLowWarningPortn OBJECT-TYPE
	SYNTAX  EkiOnOff
	MAX-ACCESS read-only
	STATUS current
	DESCRIPTION
        "
        Client Trscv Tx Power Low Warning 
        :This OID indicates that the Trscv 
        output power is lower than the
         threshold value written in the 
        Trscv EEPROM <Help> Warning indicating 
        that the Trscv output power is
         lower than the threshold value 
        written in the Trscv EEPROM <Condtype> 
        CLIENT_TX_POWER_LOW_WARNING <Probcause> 
        transmitterFailure (56) <Alarmtype> 
        equipmentAlarm (5) <Polarity> (2) 
        "
	::= { pm10010ulhAlmclientNetworkLaneAlarmWarningEntry 11 }


pm10010ulhAlmClientTxPowerLowAlarmPortn OBJECT-TYPE
	SYNTAX  EkiOnOff
	MAX-ACCESS read-only
	STATUS current
	DESCRIPTION
        "
        Client Trscv Tx Power Low Alarm 
        :This OID indicates that the Trscv 
        output power is lower than the
         threshold value written in the 
        Trscv EEPROM <Help> Alarm indicating 
        that the Trscv output power is
         lower than the threshold value 
        written in the Trscv EEPROM <Condtype> 
        CLIENT_TX_POWER_LOW_ALARM <Probcause> 
        transmitterFailure (56) <Alarmtype> 
        equipmentAlarm (5) <Polarity> (2) 
        "
	::= { pm10010ulhAlmclientNetworkLaneAlarmWarningEntry 10 }


pm10010ulhAlmClientLaserTempHighAlarmPortn OBJECT-TYPE
	SYNTAX  EkiOnOff
	MAX-ACCESS read-only
	STATUS current
	DESCRIPTION
        "
        Client Trscv Laser Temp High Alarm 
        :This OID indicates that the Trscv 
        Laser Temperature is higher than 
        the threshold value written in
         the Trscv EEPROM <Help> Alarm
         indicating that the Trscv Laser 
        Temperature is higher than the
         threshold value written in the 
        Trscv EEPROM <Condtype> CLIENT_LASER_TEMP_HIGH_ALARM 
        <Probcause> temperatureUnacceptable 
        (51) <Alarmtype> equipmentAlarm 
        (5) <Polarity> (2) 
        "
	::= { pm10010ulhAlmclientNetworkLaneAlarmWarningEntry 9 }


pm10010ulhAlmClientLaserTempHighWarningPortn OBJECT-TYPE
	SYNTAX  EkiOnOff
	MAX-ACCESS read-only
	STATUS current
	DESCRIPTION
        "
        Client Trscv Laser Temp High Warning 
        :This OID indicates that the Trscv 
        Laser Temperature is higher than 
        the threshold value written in
         the Trscv EEPROM <Help> Warning 
        indicating that the Trscv Laser 
        Temperature is higher than the
         threshold value written in the 
        Trscv EEPROM <Condtype> CLIENT_LASER_TEMP_HIGH_WARNING 
        <Probcause> temperatureUnacceptable 
        (51) <Alarmtype> equipmentAlarm 
        (5) <Polarity> (2) 
        "
	::= { pm10010ulhAlmclientNetworkLaneAlarmWarningEntry 8 }


pm10010ulhAlmClientLaserTempLowWarningPortn OBJECT-TYPE
	SYNTAX  EkiOnOff
	MAX-ACCESS read-only
	STATUS current
	DESCRIPTION
        "
        Client Trscv Laser Temp Low Warning 
        :This OID indicates that the Trscv 
        Laser Temperature is lower than 
        the threshold value written in
         the Trscv EEPROM <Help> Warning 
        indicating that the Trscv Laser 
        Temperature is lower than the threshold 
        value written in the Trscv EEPROM 
        <Condtype> CLIENT_LASER_TEMP_LOW_WARNING 
        <Probcause> temperatureUnacceptable 
        (51) <Alarmtype> equipmentAlarm 
        (5) <Polarity> (2) 
        "
	::= { pm10010ulhAlmclientNetworkLaneAlarmWarningEntry 7 }


pm10010ulhAlmLaserTempLowAlarmPortn OBJECT-TYPE
	SYNTAX  EkiOnOff
	MAX-ACCESS read-only
	STATUS current
	DESCRIPTION
        "
        Client Trscv Laser Temp Low Alarm 
        :This OID indicates that the Trscv 
        Laser Temperature is lower than 
        the threshold value written in
         the Trscv EEPROM <Help> Alarm
         indicating that the Trscv Laser 
        Temperature is lower than the threshold 
        value written in the Trscv EEPROM 
        <Condtype> LASER_TEMP_LOW_ALARM 
        <Probcause> temperatureUnacceptable 
        (51) <Alarmtype> equipmentAlarm 
        (5) <Polarity> (2) 
        "
	::= { pm10010ulhAlmclientNetworkLaneAlarmWarningEntry 6 }


pm10010ulhAlmClientRxPowerHighAlarmPortn OBJECT-TYPE
	SYNTAX  EkiOnOff
	MAX-ACCESS read-only
	STATUS current
	DESCRIPTION
        "
        Client Trscv Rx Power High Alarm 
        :This OID indicates that the Trscv 
        input power is higher than the
         threshold value written in the 
        Trscv EEPROM <Help> Alarm indicating 
        that the Trscv input power is higher 
        than the threshold value written 
        in the Trscv EEPROM <Condtype>
         CLIENT_RX_POWER_HIGH_ALARM <Probcause> 
        receiveFailure (41) <Alarmtype> 
        equipmentAlarm (5) <Polarity> (2) 
        "
	::= { pm10010ulhAlmclientNetworkLaneAlarmWarningEntry 5 }


pm10010ulhAlmClientRxPowerHighWarningPortn OBJECT-TYPE
	SYNTAX  EkiOnOff
	MAX-ACCESS read-only
	STATUS current
	DESCRIPTION
        "
        Client Trscv Rx Power High Warning 
        :This OID indicates that the Trscv 
        input power is higher than the
         threshold value written in the 
        Trscv EEPROM <Help> Warning indicating 
        that the Trscv input power is higher 
        than the threshold value written 
        in the Trscv EEPROM <Condtype>
         CLIENT_RX_POWER_HIGH_WARNING <Probcause> 
        receiveFailure (41) <Alarmtype> 
        equipmentAlarm (5) <Polarity> (2) 
        "
	::= { pm10010ulhAlmclientNetworkLaneAlarmWarningEntry 4 }


pm10010ulhAlmClientRxPowerLowWarningPortn OBJECT-TYPE
	SYNTAX  EkiOnOff
	MAX-ACCESS read-only
	STATUS current
	DESCRIPTION
        "
        Client Trscv Rx Power Low Warning 
        :This OID indicates that the Trscv 
        input power is lower than the threshold 
        value written in the Trscv EEPROM 
        <Help> Warning indicating that
         the Trscv input power is lower 
        than the threshold value written 
        in the Trscv EEPROM <Condtype>
         CLIENT_RX_POWER_LOW_WARNING <Probcause> 
        receiveFailure (41) <Alarmtype> 
        equipmentAlarm (5) <Polarity> (2) 
        "
	::= { pm10010ulhAlmclientNetworkLaneAlarmWarningEntry 3 }


pm10010ulhAlmClientRxPowerLowAlarmPortn OBJECT-TYPE
	SYNTAX  EkiOnOff
	MAX-ACCESS read-only
	STATUS current
	DESCRIPTION
        "
        Client Trscv Rx Power Low Alarm 
        :This OID indicates that the Trscv 
        input power is lower than the threshold 
        value written in the Trscv EEPROM 
        <Help> Alarm indicating that the 
        Trscv input power is lower than 
        the threshold value written in
         the Trscv EEPROM <Condtype> CLIENT_RX_POWER_LOW_ALARM 
        <Probcause> receiveFailure (41) 
        <Alarmtype> equipmentAlarm (5)
         <Polarity> (2) 
        "
	::= { pm10010ulhAlmclientNetworkLaneAlarmWarningEntry 2 }


--- *********************************************************
---     TABLE for the pm10010ulhAlmclientNetworkLaneFault articles
--- *********************************************************

pm10010ulhAlmclientNetworkLaneFaultTable OBJECT-TYPE
	SYNTAX  SEQUENCE OF Pm10010ulhAlmclientNetworkLaneFaultEntry
	MAX-ACCESS not-accessible
	STATUS current
	DESCRIPTION
        "
        List of pm10010ulhAlmclientNetworkLaneFault 
        Article
        "
	::= { pm10010ulhAlmClientUrg 120 }


pm10010ulhAlmclientNetworkLaneFaultEntry OBJECT-TYPE
	SYNTAX Pm10010ulhAlmclientNetworkLaneFaultEntry
	MAX-ACCESS not-accessible
	STATUS current
	DESCRIPTION
        "
        Row definition for the pm10010ulhAlmclientNetworkLaneFault 
        table
        "
	INDEX   { pm10010ulhAlmclientNetworkLaneFaultIndex }
	::= { pm10010ulhAlmclientNetworkLaneFaultTable 1 }


Pm10010ulhAlmclientNetworkLaneFaultEntry ::=
	SEQUENCE {
	pm10010ulhAlmclientNetworkLaneFaultIndex
		INTEGER,
	pm10010ulhAlmClientLaneTecFaultPortn
		EkiOnOff,
	pm10010ulhAlmClientLaneWavelengthUnlockedPortn
		EkiOnOff,
	pm10010ulhAlmClientLaneApdPowerSupplyPortn
		EkiOnOff,
	pm10010ulhAlmClientLaneTxLosfPortn
		EkiOnOff,
	pm10010ulhAlmClientLaneTxLolPortn
		EkiOnOff,
	pm10010ulhAlmClientLaneRxLosPortn
		EkiOnOff,
	pm10010ulhAlmClientLaneRxLolPortn
		EkiOnOff,
	pm10010ulhAlmClientLaneRxFifoErrorPortn
		EkiOnOff
	}


pm10010ulhAlmclientNetworkLaneFaultIndex OBJECT-TYPE
	SYNTAX  INTEGER(0..128)
	MAX-ACCESS  read-only
	STATUS current
	DESCRIPTION
        "
        Index definition for the pm10010ulhAlmclientNetworkLaneFault 
        table
        "
	::= { pm10010ulhAlmclientNetworkLaneFaultEntry 1 }


pm10010ulhAlmClientLaneTecFaultPortn OBJECT-TYPE
	SYNTAX  EkiOnOff
	MAX-ACCESS read-only
	STATUS current
	DESCRIPTION
        "
        Client Network Lane TEC Fault
         :This OID indicates a TEC Fault 
        on the Client Trscv Network Lane 
        <Help> Alarm indicating a TEC Fault 
        on the Client Trscv Network Lane 
        <Condtype> CLIENT_LANE_TEC_FAULT 
        <Probcause> transmitterFailure
         (56) <Alarmtype> equipmentAlarm 
        (5) <Polarity> (2) 
        "
	::= { pm10010ulhAlmclientNetworkLaneFaultEntry 17 }


pm10010ulhAlmClientLaneWavelengthUnlockedPortn OBJECT-TYPE
	SYNTAX  EkiOnOff
	MAX-ACCESS read-only
	STATUS current
	DESCRIPTION
        "
        Client Network Lane Wavelength 
        Unlock :This OID indicates a Wavelength 
        unlock on the Client Trscv Network 
        Lane <Help> Alarm indicating a
         Wavelength unlock on the Client 
        Trscv Network Lane <Condtype> CLIENT_LANE_WAVELENGTH_UNLOCKED 
        <Probcause> transmitterFailure
         (56) <Alarmtype> equipmentAlarm 
        (5) <Polarity> (2) 
        "
	::= { pm10010ulhAlmclientNetworkLaneFaultEntry 16 }


pm10010ulhAlmClientLaneApdPowerSupplyPortn OBJECT-TYPE
	SYNTAX  EkiOnOff
	MAX-ACCESS read-only
	STATUS current
	DESCRIPTION
        "
        Client Network Lane APD Power
         Supply :This OID indicates an
         APD Power supply failure on the 
        Client Trscv Network Lane <Help> 
        Alarm indicating an APD Power supply 
        failure on the Client Trscv Network 
        Lane <Condtype> CLIENT_LANE_APD_POWER_SUPPLY 
        <Probcause> transmitterFailure
         (56) <Alarmtype> equipmentAlarm 
        (5) <Polarity> (2) 
        "
	::= { pm10010ulhAlmclientNetworkLaneFaultEntry 15 }


pm10010ulhAlmClientLaneTxLosfPortn OBJECT-TYPE
	SYNTAX  EkiOnOff
	MAX-ACCESS read-only
	STATUS current
	DESCRIPTION
        "
        Client Network Lane Tx Loss Of 
        Signal Functionality :This OID
         indicates a Tx Loss of Signal
         Functionality on the Client Trscv 
        Network Lane <Help> Alarm indicating 
        a Tx Loss of Signal Functionality 
        on the Client Trscv Network Lane 
        <Condtype> CLIENT_LANE_TX_LOSF
         <Probcause> transmitterFailure 
        (56) <Alarmtype> equipmentAlarm 
        (5) <Polarity> (2) 
        "
	::= { pm10010ulhAlmclientNetworkLaneFaultEntry 9 }


pm10010ulhAlmClientLaneTxLolPortn OBJECT-TYPE
	SYNTAX  EkiOnOff
	MAX-ACCESS read-only
	STATUS current
	DESCRIPTION
        "
        Client Network Lane Tx Loss Of 
        Lock :This OID indicates a Tx Loss 
        of Lock on the Client Trscv Network 
        Lane <Help> Alarm indicating a
         Tx Loss of Lock on the Client
         Trscv Network Lane <Condtype>
         CLIENT_LANE_TX_LOL <Probcause> 
        transmitterFailure (56) <Alarmtype> 
        equipmentAlarm (5) <Polarity> (2) 
        "
	::= { pm10010ulhAlmclientNetworkLaneFaultEntry 8 }


pm10010ulhAlmClientLaneRxLosPortn OBJECT-TYPE
	SYNTAX  EkiOnOff
	MAX-ACCESS read-only
	STATUS current
	DESCRIPTION
        "
        Client Network Lane Rx Loss Of 
        Signal :This OID indicates a Rx 
        Loss of Signal on the Client Trscv 
        Network Lane <Help> Alarm indicating 
        a Rx Loss of Signal on the Client 
        Trscv Network Lane <Condtype> CLIENT_LANE_RX_LOS 
        <Probcause> receiveFailure (41) 
        <Alarmtype> physicalViolation (9) 
        <Polarity> (2) 
        "
	::= { pm10010ulhAlmclientNetworkLaneFaultEntry 6 }


pm10010ulhAlmClientLaneRxLolPortn OBJECT-TYPE
	SYNTAX  EkiOnOff
	MAX-ACCESS read-only
	STATUS current
	DESCRIPTION
        "
        Client Network Lane Rx Loss Of 
        Lock :This OID indicates a Rx Loss 
        of Lock on the Client Trscv Network 
        Lane <Help> Alarm indicating a
         Rx Loss of Lock on the Client
         Trscv Network Lane <Condtype>
         CLIENT_LANE_RX_LOL <Probcause> 
        receiverFailure (42) <Alarmtype> 
        equipmentAlarm (5) <Polarity> (2) 
        "
	::= { pm10010ulhAlmclientNetworkLaneFaultEntry 5 }


pm10010ulhAlmClientLaneRxFifoErrorPortn OBJECT-TYPE
	SYNTAX  EkiOnOff
	MAX-ACCESS read-only
	STATUS current
	DESCRIPTION
        "
        Client Network Lane Rx FIFO Error 
        :This OID indicates a Rx FIFO Error 
        on the Client Trscv Network Lane 
        <Help> Alarm indicating a Rx FIFO 
        Error on the Client Trscv Network 
        Lane <Condtype> CLIENT_LANE_RX_FIFO_ERROR 
        <Probcause> receiverFailure (42) 
        <Alarmtype> equipmentAlarm (5)
         <Polarity> (2) 
        "
	::= { pm10010ulhAlmclientNetworkLaneFaultEntry 4 }


--- *********************************************************
---     TABLE for the pm10010ulhAlmclientHostLaneFault articles
--- *********************************************************

pm10010ulhAlmclientHostLaneFaultTable OBJECT-TYPE
	SYNTAX  SEQUENCE OF Pm10010ulhAlmclientHostLaneFaultEntry
	MAX-ACCESS not-accessible
	STATUS current
	DESCRIPTION
        "
        List of pm10010ulhAlmclientHostLaneFault 
        Article
        "
	::= { pm10010ulhAlmClientUrg 152 }


pm10010ulhAlmclientHostLaneFaultEntry OBJECT-TYPE
	SYNTAX Pm10010ulhAlmclientHostLaneFaultEntry
	MAX-ACCESS not-accessible
	STATUS current
	DESCRIPTION
        "
        Row definition for the pm10010ulhAlmclientHostLaneFault 
        table
        "
	INDEX   { pm10010ulhAlmclientHostLaneFaultIndex }
	::= { pm10010ulhAlmclientHostLaneFaultTable 1 }


Pm10010ulhAlmclientHostLaneFaultEntry ::=
	SEQUENCE {
	pm10010ulhAlmclientHostLaneFaultIndex
		INTEGER,
	pm10010ulhAlmClientLaneTxFifoErrorPortn
		EkiOnOff,
	pm10010ulhAlmClientTxHostLolPortn
		EkiOnOff,
	pm10010ulhAlmClientCsfDetectedPortn
		EkiOnOff,
	pm10010ulhAlmClientLanesNotAlignedPortn
		EkiOnOff,
	pm10010ulhAlmClientLanes6466UnlockPortn
		EkiOnOff,
	pm10010ulhAlmClientLanesMarkerUnlockPortn
		EkiOnOff,
	pm10010ulhAlmClientInputLossOfSigPortn
		EkiOnOff,
	pm10010ulhAlmClientLossOfSyncPortn
		EkiOnOff
	}


pm10010ulhAlmclientHostLaneFaultIndex OBJECT-TYPE
	SYNTAX  INTEGER(0..128)
	MAX-ACCESS  read-only
	STATUS current
	DESCRIPTION
        "
        Index definition for the pm10010ulhAlmclientHostLaneFault 
        table
        "
	::= { pm10010ulhAlmclientHostLaneFaultEntry 1 }


pm10010ulhAlmClientLaneTxFifoErrorPortn OBJECT-TYPE
	SYNTAX  EkiOnOff
	MAX-ACCESS read-only
	STATUS current
	DESCRIPTION
        "
        Client Host Lane Tx FIFO Error 
        :This OID indicates a Tx FIFO Error 
        on the Client Trscv Host Lane <Help> 
        Alarm indicating a Tx FIFO Error 
        on the Client Trscv Host Lane <Condtype> 
        CLIENT_LANE_TX_FIFO_ERROR <Probcause> 
        receiverFailure (42) <Alarmtype> 
        equipmentAlarm (5) <Polarity> (2) 
        "
	::= { pm10010ulhAlmclientHostLaneFaultEntry 11 }


pm10010ulhAlmClientTxHostLolPortn OBJECT-TYPE
	SYNTAX  EkiOnOff
	MAX-ACCESS read-only
	STATUS current
	DESCRIPTION
        "
        Client Host Lane Tx Loss Of Lock 
        :This OID indicates a Tx Loss of 
        Lock on the Client Trscv Host Lane 
        <Help> Alarm indicating a Tx Loss 
        of Lock on the Client Trscv Host 
        Lane <Condtype> CLIENT_TX_HOST_LOL 
        <Probcause> receiverFailure (42) 
        <Alarmtype> equipmentAlarm (5)
         <Polarity> (2) 
        "
	::= { pm10010ulhAlmclientHostLaneFaultEntry 10 }


pm10010ulhAlmClientCsfDetectedPortn OBJECT-TYPE
	SYNTAX  EkiOnOff
	MAX-ACCESS read-only
	STATUS current
	DESCRIPTION
        "
        Client Signal Fail Detected :This 
        OID indicates that a CSF has been 
        detected on client port in the
         downstream direction   <Help>
          This alarm indicates if a Client 
        Signal Fail has been detected in 
        the incoming line frame for this 
        client port <Condtype> CLIENT_CSF_DETECTED 
        <Probcause> receiveFailure (41) 
        <Alarmtype> other(1) <Polarity> 
        (2)
        "
	::= { pm10010ulhAlmclientHostLaneFaultEntry 7 }


pm10010ulhAlmClientLanesNotAlignedPortn OBJECT-TYPE
	SYNTAX  EkiOnOff
	MAX-ACCESS read-only
	STATUS current
	DESCRIPTION
        "
        Client Lanes Not Aligned :This 
        OID indicates the Client lanes
         are not aligned <Help> Alarm indicating 
        the Client lanes are not aligned 
        <Condtype> CLIENT_LANES_NOT_ALIGNED 
        <Probcause> receiveFailure (41) 
        <Alarmtype> integrityViolation
         (7) <Polarity> (2) 
        "
	::= { pm10010ulhAlmclientHostLaneFaultEntry 6 }


pm10010ulhAlmClientLanes6466UnlockPortn OBJECT-TYPE
	SYNTAX  EkiOnOff
	MAX-ACCESS read-only
	STATUS current
	DESCRIPTION
        "
        Client Lanes 64/66b Unlock :This 
        OID indicates the Client 64/66b 
        decoder is not lock <Help> Alarm 
        indicating the Client 64/66b decoder 
        is not lock <Condtype> CLIENT_LANES_64_66_UNLOCK 
        <Probcause> receiveFailure (41) 
        <Alarmtype> integrityViolation
         (7) <Polarity> (2) 
        "
	::= { pm10010ulhAlmclientHostLaneFaultEntry 5 }


pm10010ulhAlmClientLanesMarkerUnlockPortn OBJECT-TYPE
	SYNTAX  EkiOnOff
	MAX-ACCESS read-only
	STATUS current
	DESCRIPTION
        "
        Client Lanes Marker Unlock :This 
        OID indicates the Client lanes
         marker alignment is not lock <Help> 
        Alarm indicating the Client lanes 
        marker alignment is not lock <Condtype> 
        CLIENT_LANES_MARKER_UNLOCK <Probcause> 
        receiveFailure (41) <Alarmtype> 
        integrityViolation (7) <Polarity> 
        (2) 
        "
	::= { pm10010ulhAlmclientHostLaneFaultEntry 4 }


pm10010ulhAlmClientInputLossOfSigPortn OBJECT-TYPE
	SYNTAX  EkiOnOff
	MAX-ACCESS read-only
	STATUS current
	DESCRIPTION
        "
        Client Input Loss Of Signal :This 
        OID indicates a Loss of Signal
         is detected on the Client Trscv 
        <Help> Alarm indicating a Loss
         of Signal is detected on the Client 
        Trscv <Condtype> CLIENT_INPUT_LOSS_OF_SIG 
        <Probcause> receiveFailure (41) 
        <Alarmtype> physicalViolation (9) 
        <Polarity> (2) 
        "
	::= { pm10010ulhAlmclientHostLaneFaultEntry 3 }


pm10010ulhAlmClientLossOfSyncPortn OBJECT-TYPE
	SYNTAX  EkiOnOff
	MAX-ACCESS read-only
	STATUS current
	DESCRIPTION
        "
        Client Frame Alignment Loss :This 
        OID indicates the module is not 
        aligned with the incoming Client 
        signal <Help> Alarm indicating
         the module is not aligned with 
        the incoming client signal <Condtype> 
        CLIENT_LOSS_OF_SYNC <Probcause> 
        receiveFailure (41) <Alarmtype> 
        integrityViolation (7) <Polarity> 
        (2) 
        "
	::= { pm10010ulhAlmclientHostLaneFaultEntry 2 }


--- *********************************************************
---     TABLE for the pm10010ulhAlmlineNetworkLaneAlarmWarning1 articles
--- *********************************************************

pm10010ulhAlmlineNetworkLaneAlarmWarning1Table OBJECT-TYPE
	SYNTAX  SEQUENCE OF Pm10010ulhAlmlineNetworkLaneAlarmWarning1Entry
	MAX-ACCESS not-accessible
	STATUS current
	DESCRIPTION
        "
        List of pm10010ulhAlmlineNetworkLaneAlarmWarning1 
        Article
        "
	::= { pm10010ulhAlmLineNurg 184 }


pm10010ulhAlmlineNetworkLaneAlarmWarning1Entry OBJECT-TYPE
	SYNTAX Pm10010ulhAlmlineNetworkLaneAlarmWarning1Entry
	MAX-ACCESS not-accessible
	STATUS current
	DESCRIPTION
        "
        Row definition for the pm10010ulhAlmlineNetworkLaneAlarmWarning1 
        table
        "
	INDEX   { pm10010ulhAlmlineNetworkLaneAlarmWarning1Index }
	::= { pm10010ulhAlmlineNetworkLaneAlarmWarning1Table 1 }


Pm10010ulhAlmlineNetworkLaneAlarmWarning1Entry ::=
	SEQUENCE {
	pm10010ulhAlmlineNetworkLaneAlarmWarning1Index
		INTEGER,
	pm10010ulhAlmLineBiasHighAlarmPortn
		EkiOnOff,
	pm10010ulhAlmLineBiasHighWarningPortn
		EkiOnOff,
	pm10010ulhAlmLineBiasLowWarningPortn
		EkiOnOff,
	pm10010ulhAlmLineBiasLowAlarmPortn
		EkiOnOff,
	pm10010ulhAlmLineTxPowerHighAlarmPortn
		EkiOnOff,
	pm10010ulhAlmLineTxPowerHighWarningPortn
		EkiOnOff,
	pm10010ulhAlmLineTxPowerLowWarningPortn
		EkiOnOff,
	pm10010ulhAlmLineTxPowerLowAlarmPortn
		EkiOnOff,
	pm10010ulhAlmLineLaserTempHighAlarmPortn
		EkiOnOff,
	pm10010ulhAlmLineLaserTempHighWarningPortn
		EkiOnOff,
	pm10010ulhAlmLineLaserTempLowWarningPortn
		EkiOnOff,
	pm10010ulhAlmLineLaserTempLowAlarmPortn
		EkiOnOff,
	pm10010ulhAlmLineRxPowerHighAlarmPortn
		EkiOnOff,
	pm10010ulhAlmLineRxPowerHighWarningPortn
		EkiOnOff,
	pm10010ulhAlmLineRxPowerLowWarningPortn
		EkiOnOff,
	pm10010ulhAlmLineRxPowerLowAlarmPortn
		EkiOnOff
	}


pm10010ulhAlmlineNetworkLaneAlarmWarning1Index OBJECT-TYPE
	SYNTAX  INTEGER(0..128)
	MAX-ACCESS  read-only
	STATUS current
	DESCRIPTION
        "
        Index definition for the pm10010ulhAlmlineNetworkLaneAlarmWarning1 
        table
        "
	::= { pm10010ulhAlmlineNetworkLaneAlarmWarning1Entry 1 }


pm10010ulhAlmLineBiasHighAlarmPortn OBJECT-TYPE
	SYNTAX  EkiOnOff
	MAX-ACCESS read-only
	STATUS current
	DESCRIPTION
        "
        Line Trscv Tx Bias High Alarm
         :This OID indicates that the Trscv 
        laser bias current is higher than 
        the threshold value written in
         the Trscv EEPROM <Help> Alarm
         indicating that the Trscv laser 
        bias current is higher than the 
        threshold value written in the
         Trscv EEPROM <Condtype> LINE_BIAS_HIGH_ALARM 
        <Probcause> transmitterFailure
         (56) <Alarmtype> equipmentAlarm 
        (5) <Polarity> (2) 
        "
	::= { pm10010ulhAlmlineNetworkLaneAlarmWarning1Entry 17 }


pm10010ulhAlmLineBiasHighWarningPortn OBJECT-TYPE
	SYNTAX  EkiOnOff
	MAX-ACCESS read-only
	STATUS current
	DESCRIPTION
        "
        Line Trscv Tx Bias High Warning 
        :This OID indicates that the Trscv 
        laser bias current is higher than 
        the threshold value written in
         the Trscv EEPROM <Help> Warning 
        indicating that the Trscv laser 
        bias current is higher than the 
        threshold value written in the
         Trscv EEPROM <Condtype> LINE_BIAS_HIGH_WARNING 
        <Probcause> transmitterFailure
         (56) <Alarmtype> equipmentAlarm 
        (5) <Polarity> (2) 
        "
	::= { pm10010ulhAlmlineNetworkLaneAlarmWarning1Entry 16 }


pm10010ulhAlmLineBiasLowWarningPortn OBJECT-TYPE
	SYNTAX  EkiOnOff
	MAX-ACCESS read-only
	STATUS current
	DESCRIPTION
        "
        Line Trscv Tx Bias Low Warning 
        :This OID indicates that the Trscv 
        laser bias current is lower than 
        the threshold value written in
         the Trscv EEPROM <Help> Warning 
        indicating that the Trscv laser 
        bias current is lower than the
         threshold value written in the 
        Trscv EEPROM <Condtype> LINE_BIAS_LOW_WARNING 
        <Probcause> transmitterFailure
         (56) <Alarmtype> equipmentAlarm 
        (5) <Polarity> (2) 
        "
	::= { pm10010ulhAlmlineNetworkLaneAlarmWarning1Entry 15 }


pm10010ulhAlmLineBiasLowAlarmPortn OBJECT-TYPE
	SYNTAX  EkiOnOff
	MAX-ACCESS read-only
	STATUS current
	DESCRIPTION
        "
        Line Trscv Tx Bias Low Alarm :This 
        OID indicates that the Trscv laser 
        bias current is lower than the
         threshold value written in the 
        Trscv EEPROM <Help> Alarm indicating 
        that the Trscv laser bias current 
        is lower than the threshold value 
        written in the Trscv EEPROM <Condtype> 
        LINE_BIAS_LOW_ALARM <Probcause> 
        transmitterFailure (56) <Alarmtype> 
        equipmentAlarm (5) <Polarity> (2) 
        "
	::= { pm10010ulhAlmlineNetworkLaneAlarmWarning1Entry 14 }


pm10010ulhAlmLineTxPowerHighAlarmPortn OBJECT-TYPE
	SYNTAX  EkiOnOff
	MAX-ACCESS read-only
	STATUS current
	DESCRIPTION
        "
        Line Trscv Tx Power High Alarm 
        :This OID indicates that the Trscv 
        output power is higher than the 
        threshold value written in the
         Trscv EEPROM <Help> Alarm indicating 
        that the Trscv output power is
         higher than the threshold value 
        written in the Trscv EEPROM <Condtype> 
        LINE_TX_POWER_HIGH_ALARM <Probcause> 
        transmitterFailure (56) <Alarmtype> 
        equipmentAlarm (5) <Polarity> (2) 
        "
	::= { pm10010ulhAlmlineNetworkLaneAlarmWarning1Entry 13 }


pm10010ulhAlmLineTxPowerHighWarningPortn OBJECT-TYPE
	SYNTAX  EkiOnOff
	MAX-ACCESS read-only
	STATUS current
	DESCRIPTION
        "
        Line Trscv Tx Power High Warning 
        :This OID indicates that the Trscv 
        output power is higher than the 
        threshold value written in the
         Trscv EEPROM <Help> Warning indicating 
        that the Trscv output power is
         higher than the threshold value 
        written in the Trscv EEPROM <Condtype> 
        LINE_TX_POWER_HIGH_WARNING <Probcause> 
        transmitterFailure (56) <Alarmtype> 
        equipmentAlarm (5) <Polarity> (2) 
        "
	::= { pm10010ulhAlmlineNetworkLaneAlarmWarning1Entry 12 }


pm10010ulhAlmLineTxPowerLowWarningPortn OBJECT-TYPE
	SYNTAX  EkiOnOff
	MAX-ACCESS read-only
	STATUS current
	DESCRIPTION
        "
        Line Trscv Tx Power Low Warning 
        :This OID indicates that the Trscv 
        output power is lower than the
         threshold value written in the 
        Trscv EEPROM <Help> Warning indicating 
        that the Trscv output power is
         lower than the threshold value 
        written in the Trscv EEPROM <Condtype> 
        LINE_TX_POWER_LOW_WARNING <Probcause> 
        transmitterFailure (56) <Alarmtype> 
        equipmentAlarm (5) <Polarity> (2) 
        "
	::= { pm10010ulhAlmlineNetworkLaneAlarmWarning1Entry 11 }


pm10010ulhAlmLineTxPowerLowAlarmPortn OBJECT-TYPE
	SYNTAX  EkiOnOff
	MAX-ACCESS read-only
	STATUS current
	DESCRIPTION
        "
        Line Trscv Tx Power Low Alarm
         :This OID indicates that the Trscv 
        output power is lower than the
         threshold value written in the 
        Trscv EEPROM <Help> Alarm indicating 
        that the Trscv output power is
         lower than the threshold value 
        written in the Trscv EEPROM <Condtype> 
        LINE_TX_POWER_LOW_ALARM <Probcause> 
        transmitterFailure (56) <Alarmtype> 
        equipmentAlarm (5) <Polarity> (2) 
        "
	::= { pm10010ulhAlmlineNetworkLaneAlarmWarning1Entry 10 }


pm10010ulhAlmLineLaserTempHighAlarmPortn OBJECT-TYPE
	SYNTAX  EkiOnOff
	MAX-ACCESS read-only
	STATUS current
	DESCRIPTION
        "
        Line Trscv Tx Laser Temp High
         Alarm :This OID indicates that 
        the Trscv Tx Laser Temperature
         is higher than the threshold value 
        written in the Trscv EEPROM <Help> 
        Alarm indicating that the Trscv 
        Tx Laser Temperature is higher
         than the threshold value written 
        in the Trscv EEPROM <Condtype>
         LINE_LASER_TEMP_HIGH_ALARM <Probcause> 
        temperatureUnacceptable (51) <Alarmtype> 
        equipmentAlarm (5) <Polarity> (2) 
        "
	::= { pm10010ulhAlmlineNetworkLaneAlarmWarning1Entry 9 }


pm10010ulhAlmLineLaserTempHighWarningPortn OBJECT-TYPE
	SYNTAX  EkiOnOff
	MAX-ACCESS read-only
	STATUS current
	DESCRIPTION
        "
        Line Trscv Tx Laser Temp High
         Warning :This OID indicates that 
        the Trscv Tx Laser Temperature
         is higher than the threshold value 
        written in the Trscv EEPROM <Help> 
        Warning indicating that the Trscv 
        Tx Laser Temperature is higher
         than the threshold value written 
        in the Trscv EEPROM <Condtype>
         LINE_LASER_TEMP_HIGH_WARNING <Probcause> 
        temperatureUnacceptable (51) <Alarmtype> 
        equipmentAlarm (5) <Polarity> (2) 
        "
	::= { pm10010ulhAlmlineNetworkLaneAlarmWarning1Entry 8 }


pm10010ulhAlmLineLaserTempLowWarningPortn OBJECT-TYPE
	SYNTAX  EkiOnOff
	MAX-ACCESS read-only
	STATUS current
	DESCRIPTION
        "
        Line Trscv Tx Laser Temp Low Warning 
        :This OID indicates that the Trscv 
        Tx Laser Temperature is lower than 
        the threshold value written in
         the Trscv EEPROM <Help> Warning 
        indicating that the Trscv Tx Laser 
        Temperature is lower than the threshold 
        value written in the Trscv EEPROM 
        <Condtype> LINE_LASER_TEMP_LOW_WARNING 
        <Probcause> temperatureUnacceptable 
        (51) <Alarmtype> equipmentAlarm 
        (5) <Polarity> (2) 
        "
	::= { pm10010ulhAlmlineNetworkLaneAlarmWarning1Entry 7 }


pm10010ulhAlmLineLaserTempLowAlarmPortn OBJECT-TYPE
	SYNTAX  EkiOnOff
	MAX-ACCESS read-only
	STATUS current
	DESCRIPTION
        "
        Line Trscv Tx Laser Temp Low Alarm 
        :This OID indicates that the Trscv 
        Tx Laser Temperature is lower than 
        the threshold value written in
         the Trscv EEPROM <Help> Alarm
         indicating that the Trscv Tx Laser 
        Temperature is lower than the threshold 
        value written in the Trscv EEPROM 
        <Condtype> LINE_LASER_TEMP_LOW_ALARM 
        <Probcause> temperatureUnacceptable 
        (51) <Alarmtype> equipmentAlarm 
        (5) <Polarity> (2) 
        "
	::= { pm10010ulhAlmlineNetworkLaneAlarmWarning1Entry 6 }


pm10010ulhAlmLineRxPowerHighAlarmPortn OBJECT-TYPE
	SYNTAX  EkiOnOff
	MAX-ACCESS read-only
	STATUS current
	DESCRIPTION
        "
        Line Trscv Rx Power High Alarm 
        :This OID indicates that the Trscv 
        input power is higher than the
         threshold value written in the 
        Trscv EEPROM <Help> Alarm indicating 
        that the Trscv input power is higher 
        than the threshold value written 
        in the Trscv EEPROM <Condtype>
         LINE_RX_POWER_HIGH_ALARM <Probcause> 
        receiveFailure (41) <Alarmtype> 
        equipmentAlarm (5) <Polarity> (2) 
        "
	::= { pm10010ulhAlmlineNetworkLaneAlarmWarning1Entry 5 }


pm10010ulhAlmLineRxPowerHighWarningPortn OBJECT-TYPE
	SYNTAX  EkiOnOff
	MAX-ACCESS read-only
	STATUS current
	DESCRIPTION
        "
        Line Trscv Rx Power High Warning 
        :This OID indicates that the Trscv 
        input power is higher than the
         threshold value written in the 
        Trscv EEPROM <Help> Warning indicating 
        that the Trscv input power is higher 
        than the threshold value written 
        in the Trscv EEPROM <Condtype>
         LINE_RX_POWER_HIGH_WARNING <Probcause> 
        receiveFailure (41) <Alarmtype> 
        equipmentAlarm (5) <Polarity> (2) 
        "
	::= { pm10010ulhAlmlineNetworkLaneAlarmWarning1Entry 4 }


pm10010ulhAlmLineRxPowerLowWarningPortn OBJECT-TYPE
	SYNTAX  EkiOnOff
	MAX-ACCESS read-only
	STATUS current
	DESCRIPTION
        "
        Line Trscv Rx Power Low Warning 
        :This OID indicates that the Trscv 
        input power is lower than the threshold 
        value written in the Trscv EEPROM 
        <Help> Warning indicating that
         the Trscv input power is lower 
        than the threshold value written 
        in the Trscv EEPROM <Condtype>
         LINE_RX_POWER_LOW_WARNING <Probcause> 
        receiveFailure (41) <Alarmtype> 
        equipmentAlarm (5) <Polarity> (2) 
        "
	::= { pm10010ulhAlmlineNetworkLaneAlarmWarning1Entry 3 }


pm10010ulhAlmLineRxPowerLowAlarmPortn OBJECT-TYPE
	SYNTAX  EkiOnOff
	MAX-ACCESS read-only
	STATUS current
	DESCRIPTION
        "
        Line Trscv Rx Power Low Alarm
         :This OID indicates that the Trscv 
        input power is lower than the threshold 
        value written in the Trscv EEPROM 
        <Help> Alarm indicating that the 
        Trscv input power is lower than 
        the threshold value written in
         the Trscv EEPROM <Condtype> LINE_RX_POWER_LOW_ALARM 
        <Probcause> receiveFailure (41) 
        <Alarmtype> equipmentAlarm (5)
         <Polarity> (2) 
        "
	::= { pm10010ulhAlmlineNetworkLaneAlarmWarning1Entry 2 }


--- *********************************************************
---     TABLE for the pm10010ulhAlmlineNetworkLaneAlarmWarning2 articles
--- *********************************************************

pm10010ulhAlmlineNetworkLaneAlarmWarning2Table OBJECT-TYPE
	SYNTAX  SEQUENCE OF Pm10010ulhAlmlineNetworkLaneAlarmWarning2Entry
	MAX-ACCESS not-accessible
	STATUS current
	DESCRIPTION
        "
        List of pm10010ulhAlmlineNetworkLaneAlarmWarning2 
        Article
        "
	::= { pm10010ulhAlmLineNurg 188 }


pm10010ulhAlmlineNetworkLaneAlarmWarning2Entry OBJECT-TYPE
	SYNTAX Pm10010ulhAlmlineNetworkLaneAlarmWarning2Entry
	MAX-ACCESS not-accessible
	STATUS current
	DESCRIPTION
        "
        Row definition for the pm10010ulhAlmlineNetworkLaneAlarmWarning2 
        table
        "
	INDEX   { pm10010ulhAlmlineNetworkLaneAlarmWarning2Index }
	::= { pm10010ulhAlmlineNetworkLaneAlarmWarning2Table 1 }


Pm10010ulhAlmlineNetworkLaneAlarmWarning2Entry ::=
	SEQUENCE {
	pm10010ulhAlmlineNetworkLaneAlarmWarning2Index
		INTEGER,
	pm10010ulhAlmRxLaserBiasHighAlarmPortn
		EkiOnOff,
	pm10010ulhAlmRxLaserBiasHighWarningPortn
		EkiOnOff,
	pm10010ulhAlmRxLaserBiasLowWarningPortn
		EkiOnOff,
	pm10010ulhAlmRxLaserBiasLowAlarmPortn
		EkiOnOff,
	pm10010ulhAlmRxLaserOutputHighAlarmPortn
		EkiOnOff,
	pm10010ulhAlmRxLaserOutputHighWarningPortn
		EkiOnOff,
	pm10010ulhAlmRxLaserOutputLowWarningPortn
		EkiOnOff,
	pm10010ulhAlmRxLaserOutputLowAlarmPortn
		EkiOnOff,
	pm10010ulhAlmRxLaserTempHighAlarmPortn
		EkiOnOff,
	pm10010ulhAlmRxLaserTempHighWarningPortn
		EkiOnOff,
	pm10010ulhAlmRxLaserTempLowWarningPortn
		EkiOnOff,
	pm10010ulhAlmRxLaserTempLowAlarmPortn
		EkiOnOff,
	pm10010ulhAlmTxModulatorBiasHighAlarmPortn
		EkiOnOff,
	pm10010ulhAlmTxModulatorBiasHighWarningPortn
		EkiOnOff,
	pm10010ulhAlmTxModulatorBiasLowWarningPortn
		EkiOnOff,
	pm10010ulhAlmTxModulatorBiasLowAlarmPortn
		EkiOnOff
	}


pm10010ulhAlmlineNetworkLaneAlarmWarning2Index OBJECT-TYPE
	SYNTAX  INTEGER(0..128)
	MAX-ACCESS  read-only
	STATUS current
	DESCRIPTION
        "
        Index definition for the pm10010ulhAlmlineNetworkLaneAlarmWarning2 
        table
        "
	::= { pm10010ulhAlmlineNetworkLaneAlarmWarning2Entry 1 }


pm10010ulhAlmRxLaserBiasHighAlarmPortn OBJECT-TYPE
	SYNTAX  EkiOnOff
	MAX-ACCESS read-only
	STATUS current
	DESCRIPTION
        "
        Line Trscv Rx Bias High Alarm
         :This OID indicates that the Trscv 
        Rx laser bias current is higher 
        than the threshold value written 
        in the Trscv EEPROM <Help> Alarm 
        indicating that the Trscv Rx laser 
        bias current is higher than the 
        threshold value written in the
         Trscv EEPROM <Condtype> RX_LASER_BIAS_HIGH_ALARM 
        <Probcause> receiveFailure (41) 
        <Alarmtype> equipmentAlarm (5)
         <Polarity> (2) 
        "
	::= { pm10010ulhAlmlineNetworkLaneAlarmWarning2Entry 17 }


pm10010ulhAlmRxLaserBiasHighWarningPortn OBJECT-TYPE
	SYNTAX  EkiOnOff
	MAX-ACCESS read-only
	STATUS current
	DESCRIPTION
        "
        Line Trscv Rx Bias High Warning 
        :This OID indicates that the Trscv 
        Rx laser bias current is higher 
        than the threshold value written 
        in the Trscv EEPROM <Help> Warning 
        indicating that the Trscv Rx laser 
        bias current is higher than the 
        threshold value written in the
         Trscv EEPROM <Condtype> RX_LASER_BIAS_HIGH_WARNING 
        <Probcause> receiveFailure (41) 
        <Alarmtype> equipmentAlarm (5)
         <Polarity> (2) 
        "
	::= { pm10010ulhAlmlineNetworkLaneAlarmWarning2Entry 16 }


pm10010ulhAlmRxLaserBiasLowWarningPortn OBJECT-TYPE
	SYNTAX  EkiOnOff
	MAX-ACCESS read-only
	STATUS current
	DESCRIPTION
        "
        Line Trscv Rx Bias Low Warning 
        :This OID indicates that the Trscv 
        Rx laser bias current is lower
         than the threshold value written 
        in the Trscv EEPROM <Help> Warning 
        indicating that the Trscv Rx laser 
        bias current is lower than the
         threshold value written in the 
        Trscv EEPROM <Condtype> RX_LASER_BIAS_LOW_WARNING 
        <Probcause> receiveFailure (41) 
        <Alarmtype> equipmentAlarm (5)
         <Polarity> (2) 
        "
	::= { pm10010ulhAlmlineNetworkLaneAlarmWarning2Entry 15 }


pm10010ulhAlmRxLaserBiasLowAlarmPortn OBJECT-TYPE
	SYNTAX  EkiOnOff
	MAX-ACCESS read-only
	STATUS current
	DESCRIPTION
        "
        Line Trscv Rx Bias Low Alarm :This 
        OID indicates that the Trscv Rx 
        laser bias current is lower than 
        the threshold value written in
         the Trscv EEPROM <Help> Alarm
         indicating that the Trscv Rx laser 
        bias current is lower than the
         threshold value written in the 
        Trscv EEPROM <Condtype> RX_LASER_BIAS_LOW_ALARM 
        <Probcause> receiveFailure (41) 
        <Alarmtype> equipmentAlarm (5)
         <Polarity> (2) 
        "
	::= { pm10010ulhAlmlineNetworkLaneAlarmWarning2Entry 14 }


pm10010ulhAlmRxLaserOutputHighAlarmPortn OBJECT-TYPE
	SYNTAX  EkiOnOff
	MAX-ACCESS read-only
	STATUS current
	DESCRIPTION
        "
        Line Trscv Rx Output Power High 
        Alarm :This OID indicates that
         the Trscv Rx output power is higher 
        than the threshold value written 
        in the Trscv EEPROM <Help> Alarm 
        indicating that the Trscv Rx output 
        power is higher than the threshold 
        value written in the Trscv EEPROM 
        <Condtype> RX_LASER_OUTPUT_HIGH_ALARM 
        <Probcause> receiveFailure (41) 
        <Alarmtype> equipmentAlarm (5)
         <Polarity> (2) 
        "
	::= { pm10010ulhAlmlineNetworkLaneAlarmWarning2Entry 13 }


pm10010ulhAlmRxLaserOutputHighWarningPortn OBJECT-TYPE
	SYNTAX  EkiOnOff
	MAX-ACCESS read-only
	STATUS current
	DESCRIPTION
        "
        Line Trscv Rx Output Power High 
        Warning :This OID indicates that 
        the Trscv Rx output power is higher 
        than the threshold value written 
        in the Trscv EEPROM <Help> Warning 
        indicating that the Trscv Rx output 
        power is higher than the threshold 
        value written in the Trscv EEPROM 
        <Condtype> RX_LASER_OUTPUT_HIGH_WARNING 
        <Probcause> receiveFailure (41) 
        <Alarmtype> equipmentAlarm (5)
         <Polarity> (2) 
        "
	::= { pm10010ulhAlmlineNetworkLaneAlarmWarning2Entry 12 }


pm10010ulhAlmRxLaserOutputLowWarningPortn OBJECT-TYPE
	SYNTAX  EkiOnOff
	MAX-ACCESS read-only
	STATUS current
	DESCRIPTION
        "
        Line Trscv Rx Output Power Low 
        Warning :This OID indicates that 
        the Trscv Rx output power is lower 
        than the threshold value written 
        in the Trscv EEPROM <Help> Warning 
        indicating that the Trscv Rx output 
        power is lower than the threshold 
        value written in the Trscv EEPROM 
        <Condtype> RX_LASER_OUTPUT_LOW_WARNING 
        <Probcause> receiveFailure (41) 
        <Alarmtype> equipmentAlarm (5)
         <Polarity> (2) 
        "
	::= { pm10010ulhAlmlineNetworkLaneAlarmWarning2Entry 11 }


pm10010ulhAlmRxLaserOutputLowAlarmPortn OBJECT-TYPE
	SYNTAX  EkiOnOff
	MAX-ACCESS read-only
	STATUS current
	DESCRIPTION
        "
        Line Trscv Rx Output Power Low 
        Alarm :This OID indicates that
         the Trscv Rx output power is lower 
        than the threshold value written 
        in the Trscv EEPROM <Help> Alarm 
        indicating that the Trscv Rx output 
        power is lower than the threshold 
        value written in the Trscv EEPROM 
        <Condtype> RX_LASER_OUTPUT_LOW_ALARM 
        <Probcause> receiveFailure (41) 
        <Alarmtype> equipmentAlarm (5)
         <Polarity> (2) 
        "
	::= { pm10010ulhAlmlineNetworkLaneAlarmWarning2Entry 10 }


pm10010ulhAlmRxLaserTempHighAlarmPortn OBJECT-TYPE
	SYNTAX  EkiOnOff
	MAX-ACCESS read-only
	STATUS current
	DESCRIPTION
        "
        Line Trscv Rx Laser Temp High
         Alarm :This OID indicates that 
        the Trscv Rx Laser Temperature
         is higher than the threshold value 
        written in the Trscv EEPROM <Help> 
        Alarm indicating that the Trscv 
        Rx Laser Temperature is higher
         than the threshold value written 
        in the Trscv EEPROM <Condtype>
         RX_LASER_TEMP_HIGH_ALARM <Probcause> 
        temperatureUnacceptable (51) <Alarmtype> 
        equipmentAlarm (5) <Polarity> (2) 
        "
	::= { pm10010ulhAlmlineNetworkLaneAlarmWarning2Entry 9 }


pm10010ulhAlmRxLaserTempHighWarningPortn OBJECT-TYPE
	SYNTAX  EkiOnOff
	MAX-ACCESS read-only
	STATUS current
	DESCRIPTION
        "
        Line Trscv Rx Laser Temp High
         Warning :This OID indicates that 
        the Trscv Rx Laser Temperature
         is higher than the threshold value 
        written in the Trscv EEPROM <Help> 
        Warning indicating that the Trscv 
        Rx Laser Temperature is higher
         than the threshold value written 
        in the Trscv EEPROM <Condtype>
         RX_LASER_TEMP_HIGH_WARNING <Probcause> 
        temperatureUnacceptable (51) <Alarmtype> 
        equipmentAlarm (5) <Polarity> (2) 
        "
	::= { pm10010ulhAlmlineNetworkLaneAlarmWarning2Entry 8 }


pm10010ulhAlmRxLaserTempLowWarningPortn OBJECT-TYPE
	SYNTAX  EkiOnOff
	MAX-ACCESS read-only
	STATUS current
	DESCRIPTION
        "
        Line Trscv Rx Laser Temp Low Warning 
        :This OID indicates that the Trscv 
        Rx Laser Temperature is lower than 
        the threshold value written in
         the Trscv EEPROM <Help> Warning 
        indicating that the Trscv Rx Laser 
        Temperature is lower than the threshold 
        value written in the Trscv EEPROM 
        <Condtype> RX_LASER_TEMP_LOW_WARNING 
        <Probcause> temperatureUnacceptable 
        (51) <Alarmtype> equipmentAlarm 
        (5) <Polarity> (2) 
        "
	::= { pm10010ulhAlmlineNetworkLaneAlarmWarning2Entry 7 }


pm10010ulhAlmRxLaserTempLowAlarmPortn OBJECT-TYPE
	SYNTAX  EkiOnOff
	MAX-ACCESS read-only
	STATUS current
	DESCRIPTION
        "
        Line Trscv Rx Laser Temp Low Alarm 
        :This OID indicates that the Trscv 
        Rx Laser Temperature is lower than 
        the threshold value written in
         the Trscv EEPROM <Help> Alarm
         indicating that the Trscv Rx Laser 
        Temperature is lower than the threshold 
        value written in the Trscv EEPROM 
        <Condtype> RX_LASER_TEMP_LOW_ALARM 
        <Probcause> temperatureUnacceptable 
        (51) <Alarmtype> equipmentAlarm 
        (5) <Polarity> (2) 
        "
	::= { pm10010ulhAlmlineNetworkLaneAlarmWarning2Entry 6 }


pm10010ulhAlmTxModulatorBiasHighAlarmPortn OBJECT-TYPE
	SYNTAX  EkiOnOff
	MAX-ACCESS read-only
	STATUS current
	DESCRIPTION
        "
        Line Trscv Tx Modulator Bias High 
        Alarm :This OID indicates that
         the Trscv Tx modulator bias current 
        is higher than the threshold value 
        written in the Trscv EEPROM <Help> 
        Alarm indicating that the Trscv 
        Tx modulator bias current is higher 
        than the threshold value written 
        in the Trscv EEPROM <Condtype>
         TX_MODULATOR_BIAS_HIGH_ALARM <Probcause> 
        transmitterFailure (56) <Alarmtype> 
        equipmentAlarm (5) <Polarity> (2) 
        "
	::= { pm10010ulhAlmlineNetworkLaneAlarmWarning2Entry 5 }


pm10010ulhAlmTxModulatorBiasHighWarningPortn OBJECT-TYPE
	SYNTAX  EkiOnOff
	MAX-ACCESS read-only
	STATUS current
	DESCRIPTION
        "
        Line Trscv Tx Modulator Bias High 
        Warning :This OID indicates that 
        the Trscv Tx modulator bias current 
        is higher than the threshold value 
        written in the Trscv EEPROM <Help> 
        Warning indicating that the Trscv 
        Tx modulator bias current is higher 
        than the threshold value written 
        in the Trscv EEPROM <Condtype>
         TX_MODULATOR_BIAS_HIGH_WARNING 
        <Probcause> transmitterFailure
         (56) <Alarmtype> equipmentAlarm 
        (5) <Polarity> (2) 
        "
	::= { pm10010ulhAlmlineNetworkLaneAlarmWarning2Entry 4 }


pm10010ulhAlmTxModulatorBiasLowWarningPortn OBJECT-TYPE
	SYNTAX  EkiOnOff
	MAX-ACCESS read-only
	STATUS current
	DESCRIPTION
        "
        Line Trscv Tx Modulator Bias Low 
        Warning :This OID indicates that 
        the Trscv Tx modulator bias current 
        is lower than the threshold value 
        written in the Trscv EEPROM <Help> 
        Warning indicating that the Trscv 
        Tx modulator bias current is lower 
        than the threshold value written 
        in the Trscv EEPROM <Condtype>
         TX_MODULATOR_BIAS_LOW_WARNING
         <Probcause> transmitterFailure 
        (56) <Alarmtype> equipmentAlarm 
        (5) <Polarity> (2) 
        "
	::= { pm10010ulhAlmlineNetworkLaneAlarmWarning2Entry 3 }


pm10010ulhAlmTxModulatorBiasLowAlarmPortn OBJECT-TYPE
	SYNTAX  EkiOnOff
	MAX-ACCESS read-only
	STATUS current
	DESCRIPTION
        "
        Line Trscv Tx Modulator Bias Low 
        Alarm :This OID indicates that
         the Trscv Tx modulator bias current 
        is lower than the threshold value 
        written in the Trscv EEPROM <Help> 
        Alarm indicating that the Trscv 
        Tx modulator bias current is lower 
        than the threshold value written 
        in the Trscv EEPROM <Condtype>
         TX_MODULATOR_BIAS_LOW_ALARM <Probcause> 
        transmitterFailure (56) <Alarmtype> 
        equipmentAlarm (5) <Polarity> (2) 
        "
	::= { pm10010ulhAlmlineNetworkLaneAlarmWarning2Entry 2 }


--- *********************************************************
---     TABLE for the pm10010ulhAlmlineNetworkLaneFault articles
--- *********************************************************

pm10010ulhAlmlineNetworkLaneFaultTable OBJECT-TYPE
	SYNTAX  SEQUENCE OF Pm10010ulhAlmlineNetworkLaneFaultEntry
	MAX-ACCESS not-accessible
	STATUS current
	DESCRIPTION
        "
        List of pm10010ulhAlmlineNetworkLaneFault 
        Article
        "
	::= { pm10010ulhAlmLineUrg 192 }


pm10010ulhAlmlineNetworkLaneFaultEntry OBJECT-TYPE
	SYNTAX Pm10010ulhAlmlineNetworkLaneFaultEntry
	MAX-ACCESS not-accessible
	STATUS current
	DESCRIPTION
        "
        Row definition for the pm10010ulhAlmlineNetworkLaneFault 
        table
        "
	INDEX   { pm10010ulhAlmlineNetworkLaneFaultIndex }
	::= { pm10010ulhAlmlineNetworkLaneFaultTable 1 }


Pm10010ulhAlmlineNetworkLaneFaultEntry ::=
	SEQUENCE {
	pm10010ulhAlmlineNetworkLaneFaultIndex
		INTEGER,
	pm10010ulhAlmLineLaneTecFaultPortn
		EkiOnOff,
	pm10010ulhAlmLineLaneWavelengthUnlockedPortn
		EkiOnOff,
	pm10010ulhAlmLineLaneApdPowerSupplyPortn
		EkiOnOff,
	pm10010ulhAlmLineLaneTxLosfPortn
		EkiOnOff,
	pm10010ulhAlmLineLaneTxLolPortn
		EkiOnOff,
	pm10010ulhAlmLineLaneRxLosPortn
		EkiOnOff,
	pm10010ulhAlmLineLaneRxLolPortn
		EkiOnOff,
	pm10010ulhAlmLineLaneRxFifoErrorPortn
		EkiOnOff,
	pm10010ulhAlmLineLaneRxTecFaultPortn
		EkiOnOff
	}


pm10010ulhAlmlineNetworkLaneFaultIndex OBJECT-TYPE
	SYNTAX  INTEGER(0..128)
	MAX-ACCESS  read-only
	STATUS current
	DESCRIPTION
        "
        Index definition for the pm10010ulhAlmlineNetworkLaneFault 
        table
        "
	::= { pm10010ulhAlmlineNetworkLaneFaultEntry 1 }


pm10010ulhAlmLineLaneTecFaultPortn OBJECT-TYPE
	SYNTAX  EkiOnOff
	MAX-ACCESS read-only
	STATUS current
	DESCRIPTION
        "
        Line Network Lane TEC Fault :This 
        OID indicates a Tx TEC Fault on 
        the Line Trscv Network Lane <Help> 
        Alarm indicating a Tx TEC Fault 
        on the Line Trscv Network Lane
         <Condtype> LINE_LANE_TEC_FAULT 
        <Probcause> transmitterFailure
         (56) <Alarmtype> equipmentAlarm 
        (5) <Polarity> (2) 
        "
	::= { pm10010ulhAlmlineNetworkLaneFaultEntry 17 }


pm10010ulhAlmLineLaneWavelengthUnlockedPortn OBJECT-TYPE
	SYNTAX  EkiOnOff
	MAX-ACCESS read-only
	STATUS current
	DESCRIPTION
        "
        Line Network Lane Wavelength Unlock 
        :This OID indicates a Wavelength 
        unlock on the Line Trscv Network 
        Lane <Help> Alarm indicating a
         Wavelength unlock on the Line
         Trscv Network Lane <Condtype>
         LINE_LANE_WAVELENGTH_UNLOCKED
         <Probcause> transmitterFailure 
        (56) <Alarmtype> equipmentAlarm 
        (5) <Polarity> (2) 
        "
	::= { pm10010ulhAlmlineNetworkLaneFaultEntry 16 }


pm10010ulhAlmLineLaneApdPowerSupplyPortn OBJECT-TYPE
	SYNTAX  EkiOnOff
	MAX-ACCESS read-only
	STATUS current
	DESCRIPTION
        "
        Line Network Lane APD Power Supply 
        :This OID indicates an APD Power 
        supply failure on the Line Trscv 
        Network Lane <Help> Alarm indicating 
        an APD Power supply failure on
         the Line Trscv Network Lane <Condtype> 
        LINE_LANE_APD_POWER_SUPPLY <Probcause> 
        transmitterFailure (56) <Alarmtype> 
        equipmentAlarm (5) <Polarity> (2) 
        "
	::= { pm10010ulhAlmlineNetworkLaneFaultEntry 15 }


pm10010ulhAlmLineLaneTxLosfPortn OBJECT-TYPE
	SYNTAX  EkiOnOff
	MAX-ACCESS read-only
	STATUS current
	DESCRIPTION
        "
        Line Network Lane Tx Loss Of Signal 
        Functionality :This OID indicates 
        a Tx Loss of Signal Functionality 
        on the Line Trscv Network Lane
         <Help> Alarm indicating a Tx Loss 
        of Signal Functionality on the
         Line Trscv Network Lane <Condtype> 
        LINE_LANE_TX_LOSF <Probcause> transmitterFailure 
        (56) <Alarmtype> equipmentAlarm 
        (5) <Polarity> (2) 
        "
	::= { pm10010ulhAlmlineNetworkLaneFaultEntry 9 }


pm10010ulhAlmLineLaneTxLolPortn OBJECT-TYPE
	SYNTAX  EkiOnOff
	MAX-ACCESS read-only
	STATUS current
	DESCRIPTION
        "
        Line Network Lane Tx Loss Of Lock 
        :This OID indicates a Tx Loss of 
        Lock on the Line Trscv Network
         Lane <Help> Alarm indicating a 
        Tx Loss of Lock on the Line Trscv 
        Network Lane <Condtype> LINE_LANE_TX_LOL 
        <Probcause> transmitterFailure
         (56) <Alarmtype> equipmentAlarm 
        (5) <Polarity> (2) 
        "
	::= { pm10010ulhAlmlineNetworkLaneFaultEntry 8 }


pm10010ulhAlmLineLaneRxLosPortn OBJECT-TYPE
	SYNTAX  EkiOnOff
	MAX-ACCESS read-only
	STATUS current
	DESCRIPTION
        "
        Line Network Lane Rx Loss Of Signal 
        :This OID indicates a Rx Loss of 
        Signal on the Line Trscv Network 
        Lane <Help> Alarm indicating a
         Rx Loss of Signal on the Line
         Trscv Network Lane <Condtype>
         LINE_LANE_RX_LOS <Probcause> receiveFailure 
        (41) <Alarmtype> physicalViolation 
        (9) <Polarity> (2) 
        "
	::= { pm10010ulhAlmlineNetworkLaneFaultEntry 6 }


pm10010ulhAlmLineLaneRxLolPortn OBJECT-TYPE
	SYNTAX  EkiOnOff
	MAX-ACCESS read-only
	STATUS current
	DESCRIPTION
        "
        Line Network Lane Rx Loss Of Lock 
        :This OID indicates a Rx Loss of 
        Lock on the Line Trscv Network
         Lane <Help> Alarm indicating a 
        Rx Loss of Lock on the Line Trscv 
        Network Lane <Condtype> LINE_LANE_RX_LOL 
        <Probcause> receiverFailure (42) 
        <Alarmtype> equipmentAlarm (5)
         <Polarity> (2) 
        "
	::= { pm10010ulhAlmlineNetworkLaneFaultEntry 5 }


pm10010ulhAlmLineLaneRxFifoErrorPortn OBJECT-TYPE
	SYNTAX  EkiOnOff
	MAX-ACCESS read-only
	STATUS current
	DESCRIPTION
        "
        Line Network Lane Rx FIFO Error 
        :This OID indicates a Rx FIFO Error 
        on the Line Trscv Network Lane
         <Help> Alarm indicating a Rx FIFO 
        Error on the Line Trscv Network 
        Lane <Condtype> LINE_LANE_RX_FIFO_ERROR 
        <Probcause> receiverFailure (42) 
        <Alarmtype> equipmentAlarm (5)
         <Polarity> (2) 
        "
	::= { pm10010ulhAlmlineNetworkLaneFaultEntry 4 }


pm10010ulhAlmLineLaneRxTecFaultPortn OBJECT-TYPE
	SYNTAX  EkiOnOff
	MAX-ACCESS read-only
	STATUS current
	DESCRIPTION
        "
        Line Network Lane Rx TEC Fault 
        :This OID indicates a Rx TEC Fault 
        on the Line Trscv Network Lane
         <Help> Alarm indicating a Rx TEC 
        Fault on the Line Trscv Network 
        Lane <Condtype> LINE_LANE_RX_TEC_FAULT 
        <Probcause> receiverFailure (42) 
        <Alarmtype> equipmentAlarm (5)
         <Polarity> (2) 
        "
	::= { pm10010ulhAlmlineNetworkLaneFaultEntry 3 }


--- *********************************************************
---     TABLE for the pm10010ulhAlmlineHostLaneFault articles
--- *********************************************************

pm10010ulhAlmlineHostLaneFaultTable OBJECT-TYPE
	SYNTAX  SEQUENCE OF Pm10010ulhAlmlineHostLaneFaultEntry
	MAX-ACCESS not-accessible
	STATUS current
	DESCRIPTION
        "
        List of pm10010ulhAlmlineHostLaneFault 
        Article
        "
	::= { pm10010ulhAlmLineUrg 196 }


pm10010ulhAlmlineHostLaneFaultEntry OBJECT-TYPE
	SYNTAX Pm10010ulhAlmlineHostLaneFaultEntry
	MAX-ACCESS not-accessible
	STATUS current
	DESCRIPTION
        "
        Row definition for the pm10010ulhAlmlineHostLaneFault 
        table
        "
	INDEX   { pm10010ulhAlmlineHostLaneFaultIndex }
	::= { pm10010ulhAlmlineHostLaneFaultTable 1 }


Pm10010ulhAlmlineHostLaneFaultEntry ::=
	SEQUENCE {
	pm10010ulhAlmlineHostLaneFaultIndex
		INTEGER,
	pm10010ulhAlmLineLaneTxFifoErrorPortn
		EkiOnOff,
	pm10010ulhAlmLineTxHostLolPortn
		EkiOnOff,
	pm10010ulhAlmLineSmIaeDetectedPortn
		EkiOnOff,
	pm10010ulhAlmLineSmIaeInsertedPortn
		EkiOnOff,
	pm10010ulhAlmLineSmBdiDetectedPortn
		EkiOnOff,
	pm10010ulhAlmLineSmBdiInsertedPortn
		EkiOnOff,
	pm10010ulhAlmLineLossOfFramePortn
		EkiOnOff,
	pm10010ulhAlmLineInputLossOfSignalPortn
		EkiOnOff
	}


pm10010ulhAlmlineHostLaneFaultIndex OBJECT-TYPE
	SYNTAX  INTEGER(0..128)
	MAX-ACCESS  read-only
	STATUS current
	DESCRIPTION
        "
        Index definition for the pm10010ulhAlmlineHostLaneFault 
        table
        "
	::= { pm10010ulhAlmlineHostLaneFaultEntry 1 }


pm10010ulhAlmLineLaneTxFifoErrorPortn OBJECT-TYPE
	SYNTAX  EkiOnOff
	MAX-ACCESS read-only
	STATUS current
	DESCRIPTION
        "
        Line Host Lane Tx FIFO Error :This 
        OID indicates a Tx FIFO Error on 
        the Line Trscv Host Lane <Help> 
        Alarm indicating a Tx FIFO Error 
        on the Line Trscv Host Lane <Condtype> 
        LINE_LANE_TX_FIFO_ERROR <Probcause> 
        receiverFailure (42) <Alarmtype> 
        equipmentAlarm (5) <Polarity> (2) 
        "
	::= { pm10010ulhAlmlineHostLaneFaultEntry 11 }


pm10010ulhAlmLineTxHostLolPortn OBJECT-TYPE
	SYNTAX  EkiOnOff
	MAX-ACCESS read-only
	STATUS current
	DESCRIPTION
        "
        Line Host Lane Tx Loss Of Lock 
        :This OID indicates a Tx Loss of 
        Lock on the Line Trscv Host Lane 
        <Help> Alarm indicating a Tx Loss 
        of Lock on the Line Trscv Host
         Lane <Condtype> LINE_TX_HOST_LOL 
        <Probcause> receiverFailure (42) 
        <Alarmtype> equipmentAlarm (5)
         <Polarity> (2) 
        "
	::= { pm10010ulhAlmlineHostLaneFaultEntry 10 }


pm10010ulhAlmLineSmIaeDetectedPortn OBJECT-TYPE
	SYNTAX  EkiOnOff
	MAX-ACCESS read-only
	STATUS current
	DESCRIPTION
        "
        Line SM IAE Detected :This OID 
        indicates a SM Incoming Alignment 
        Error is detected on the incoming 
        Line signal <Help> Alarm indicating 
        a SM Incoming Alignment Error is 
        detected on the incoming Line signal 
        <Condtype> LINE_SM_IAE_DETECTED 
        <Probcause> receiveFailure (41) 
        <Alarmtype> integrityViolation
         (7) <Polarity> (2) 
        "
	::= { pm10010ulhAlmlineHostLaneFaultEntry 7 }


pm10010ulhAlmLineSmIaeInsertedPortn OBJECT-TYPE
	SYNTAX  EkiOnOff
	MAX-ACCESS read-only
	STATUS current
	DESCRIPTION
        "
        Line SM IAE Inserted :This OID 
        indicates a SM Incoming Alignment 
        Error is inserted on the outgoing 
        Line signal <Help> Status indicating 
        a SM Incoming Alignment Error is 
        inserted on the outgoing Line signal 
        <Condtype> LINE_SM_IAE_INSERTED 
        <Probcause> informationalStatus(1000) 
        <Alarmtype> other (1) <Polarity> 
        (2) 
        "
	::= { pm10010ulhAlmlineHostLaneFaultEntry 6 }


pm10010ulhAlmLineSmBdiDetectedPortn OBJECT-TYPE
	SYNTAX  EkiOnOff
	MAX-ACCESS read-only
	STATUS current
	DESCRIPTION
        "
        Line SM BDI Detected :This OID 
        indicates a SM Backward Defect
         Indication is detected on the
         incoming Line signal <Help> Alarm 
        indicating a SM Backward Defect 
        Indication is detected on the incoming 
        Line signal <Condtype> LINE_SM_BDI_DETECTED 
        <Probcause> receiveFailure (41) 
        <Alarmtype> integrityViolation
         (7) <Polarity> (2) 
        "
	::= { pm10010ulhAlmlineHostLaneFaultEntry 5 }


pm10010ulhAlmLineSmBdiInsertedPortn OBJECT-TYPE
	SYNTAX  EkiOnOff
	MAX-ACCESS read-only
	STATUS current
	DESCRIPTION
        "
        Line SM BDI Inserted :This OID 
        indicates a SM Backward Defect
         Indication is inserted on the
         outgoing Line signal <Help> Status 
        indicating a SM Backward Defect 
        Indication is inserted on the outgoing 
        Line signal <Condtype> LINE_SM_BDI_INSERTED 
        <Probcause> informationalStatus(1000) 
        <Alarmtype> other (1) <Polarity> 
        (2) 
        "
	::= { pm10010ulhAlmlineHostLaneFaultEntry 4 }


pm10010ulhAlmLineLossOfFramePortn OBJECT-TYPE
	SYNTAX  EkiOnOff
	MAX-ACCESS read-only
	STATUS current
	DESCRIPTION
        "
        Line Loss Of Frame :This OID indicates 
        the module is not aligned with
         the incoming Line signal <Help> 
        Alarm indicating the module is
         not aligned with the incoming
         Line signal <Condtype> LINE_LOSS_OF_FRAME 
        <Probcause> receiveFailure (41) 
        <Alarmtype> integrityViolation
         (7) <Polarity> (2) 
        "
	::= { pm10010ulhAlmlineHostLaneFaultEntry 3 }


pm10010ulhAlmLineInputLossOfSignalPortn OBJECT-TYPE
	SYNTAX  EkiOnOff
	MAX-ACCESS read-only
	STATUS current
	DESCRIPTION
        "
        Line Input Loss Of Signal :This 
        OID indicates a Loss of Signal
         is detected on the Line Trscv
         <Help> Alarm indicating a Loss 
        of Signal is detected on the Line 
        Trscv <Condtype> LINE_INPUT_LOSS_OF_SIGNAL 
        <Probcause> receiveFailure (41) 
        <Alarmtype> physicalViolation (9) 
        <Polarity> (2) 
        "
	::= { pm10010ulhAlmlineHostLaneFaultEntry 2 }


--- *********************************************************
---     TABLE for the pm10010ulhAlmlineNetworkLaneRxOtn articles
--- *********************************************************

pm10010ulhAlmlineNetworkLaneRxOtnTable OBJECT-TYPE
	SYNTAX  SEQUENCE OF Pm10010ulhAlmlineNetworkLaneRxOtnEntry
	MAX-ACCESS not-accessible
	STATUS current
	DESCRIPTION
        "
        List of pm10010ulhAlmlineNetworkLaneRxOtn 
        Article
        "
	::= { pm10010ulhAlmLineUrg 200 }


pm10010ulhAlmlineNetworkLaneRxOtnEntry OBJECT-TYPE
	SYNTAX Pm10010ulhAlmlineNetworkLaneRxOtnEntry
	MAX-ACCESS not-accessible
	STATUS current
	DESCRIPTION
        "
        Row definition for the pm10010ulhAlmlineNetworkLaneRxOtn 
        table
        "
	INDEX   { pm10010ulhAlmlineNetworkLaneRxOtnIndex }
	::= { pm10010ulhAlmlineNetworkLaneRxOtnTable 1 }


Pm10010ulhAlmlineNetworkLaneRxOtnEntry ::=
	SEQUENCE {
	pm10010ulhAlmlineNetworkLaneRxOtnIndex
		INTEGER,
	pm10010ulhAlmLineRxOtnLofPortn
		EkiOnOff,
	pm10010ulhAlmLineRxOtnOofPortn
		EkiOnOff,
	pm10010ulhAlmLineRxOtnLomPortn
		EkiOnOff,
	pm10010ulhAlmLineRxOtnOomPortn
		EkiOnOff,
	pm10010ulhAlmLineRxOtnIaePortn
		EkiOnOff,
	pm10010ulhAlmLineRxSmBdiPortn
		EkiOnOff,
	pm10010ulhAlmLineRxOtnOtuAisPortn
		EkiOnOff,
	pm10010ulhAlmLineRxOtnOduAisPortn
		EkiOnOff
	}


pm10010ulhAlmlineNetworkLaneRxOtnIndex OBJECT-TYPE
	SYNTAX  INTEGER(0..128)
	MAX-ACCESS  read-only
	STATUS current
	DESCRIPTION
        "
        Index definition for the pm10010ulhAlmlineNetworkLaneRxOtn 
        table
        "
	::= { pm10010ulhAlmlineNetworkLaneRxOtnEntry 1 }


pm10010ulhAlmLineRxOtnLofPortn OBJECT-TYPE
	SYNTAX  EkiOnOff
	MAX-ACCESS read-only
	STATUS current
	DESCRIPTION
        "
        Line Network Rx LOF :This OID
         indicates a Loss of Frame is detected 
        on the Rx Network interface of
         the Line Trscv <Help> Alarm indicating 
        a Loss of Frame is detected on
         the Rx Network interface of the 
        Line Trscv <Condtype> LINE_RX_OTN_LOF 
        <Probcause> receiveFailure (41) 
        <Alarmtype> equipmentAlarm (5)
         <Polarity> (2) 
        "
	::= { pm10010ulhAlmlineNetworkLaneRxOtnEntry 17 }


pm10010ulhAlmLineRxOtnOofPortn OBJECT-TYPE
	SYNTAX  EkiOnOff
	MAX-ACCESS read-only
	STATUS current
	DESCRIPTION
        "
        Line Network Rx OOF :This OID
         indicates an Out of Frame is detected 
        on the Rx Network interface of
         the Line Trscv <Help> Alarm indicating 
        an Out of Frame is detected on
         the Rx Network interface of the 
        Line Trscv <Condtype> LINE_RX_OTN_OOF 
        <Probcause> receiveFailure (41) 
        <Alarmtype> equipmentAlarm (5)
         <Polarity> (2) 
        "
	::= { pm10010ulhAlmlineNetworkLaneRxOtnEntry 16 }


pm10010ulhAlmLineRxOtnLomPortn OBJECT-TYPE
	SYNTAX  EkiOnOff
	MAX-ACCESS read-only
	STATUS current
	DESCRIPTION
        "
        Line Network Rx LOM :This OID
         indicates a Loss of Multiframe 
        is detected on the Rx Network interface 
        of the Line Trscv <Help> Alarm
         indicating a Loss of Multiframe 
        is detected on the Rx Network interface 
        of the Line Trscv <Condtype> LINE_RX_OTN_LOM 
        <Probcause> receiveFailure (41) 
        <Alarmtype> equipmentAlarm (5)
         <Polarity> (2) 
        "
	::= { pm10010ulhAlmlineNetworkLaneRxOtnEntry 15 }


pm10010ulhAlmLineRxOtnOomPortn OBJECT-TYPE
	SYNTAX  EkiOnOff
	MAX-ACCESS read-only
	STATUS current
	DESCRIPTION
        "
        Line Network Rx OOM :This OID
         indicates an Out of Multiframe 
        is detected on the Rx Network interface 
        of the Line Trscv <Help> Alarm
         indicating an Out of Multiframe 
        is detected on the Rx Network interface 
        of the Line Trscv <Condtype> LINE_RX_OTN_OOM 
        <Probcause> receiveFailure (41) 
        <Alarmtype> equipmentAlarm (5)
         <Polarity> (2) 
        "
	::= { pm10010ulhAlmlineNetworkLaneRxOtnEntry 14 }


pm10010ulhAlmLineRxOtnIaePortn OBJECT-TYPE
	SYNTAX  EkiOnOff
	MAX-ACCESS read-only
	STATUS current
	DESCRIPTION
        "
        Line Network Rx IAE :This OID
         indicates an Incoming Alignment 
        Error is detected on the Rx Network 
        interface of the Line Trscv <Help> 
        Alarm indicating an Incoming Alignment 
        Error is detected on the Rx Network 
        interface of the Line Trscv <Condtype> 
        LINE_RX_OTN_IAE <Probcause> receiveFailure 
        (41) <Alarmtype> equipmentAlarm 
        (5) <Polarity> (2) 
        "
	::= { pm10010ulhAlmlineNetworkLaneRxOtnEntry 13 }


pm10010ulhAlmLineRxSmBdiPortn OBJECT-TYPE
	SYNTAX  EkiOnOff
	MAX-ACCESS read-only
	STATUS current
	DESCRIPTION
        "
        Line Network Rx SM BDI :This OID 
        indicates an SM Backward Defect 
        Indication is detected on the Rx 
        Network interface of the Line Trscv 
        <Help> Alarm indicating an SM Backward 
        Defect Indication is detected on 
        the Rx Network interface of the 
        Line Trscv <Condtype> LINE_RX_SM_BDI 
        <Probcause> informationalStatus(1000) 
        <Alarmtype> other (1) <Polarity> 
        (2) 
        "
	::= { pm10010ulhAlmlineNetworkLaneRxOtnEntry 12 }


pm10010ulhAlmLineRxOtnOtuAisPortn OBJECT-TYPE
	SYNTAX  EkiOnOff
	MAX-ACCESS read-only
	STATUS current
	DESCRIPTION
        "
        Line Network Rx OTU AIS :This
         OID indicates an OTU This OID
         Indication Signal is detected
         on the Rx Network interface of 
        the Line Trscv <Help> Alarm indicating 
        an OTU Alarm Indication Signal
         is detected on the Rx Network
         interface of the Line Trscv <Condtype> 
        LINE_RX_OTN_OTU_AIS <Probcause> 
        receiveFailure (41) <Alarmtype> 
        equipmentAlarm (5) <Polarity> (2) 
        "
	::= { pm10010ulhAlmlineNetworkLaneRxOtnEntry 11 }


pm10010ulhAlmLineRxOtnOduAisPortn OBJECT-TYPE
	SYNTAX  EkiOnOff
	MAX-ACCESS read-only
	STATUS current
	DESCRIPTION
        "
        Line Network Rx ODU AIS :This
         OID indicates an ODU This OID
         Indication Signal is detected
         on the Rx Network interface of 
        the Line Trscv <Help> Alarm indicating 
        an ODU Alarm Indication Signal
         is detected on the Rx Network
         interface of the Line Trscv <Condtype> 
        LINE_RX_OTN_ODU_AIS <Probcause> 
        receiveFailure (41) <Alarmtype> 
        equipmentAlarm (5) <Polarity> (2) 
        "
	::= { pm10010ulhAlmlineNetworkLaneRxOtnEntry 10 }


--- *********************************************************
---     TABLE for the pm10010ulhAlmlineHostLaneTxOtn articles
--- *********************************************************

pm10010ulhAlmlineHostLaneTxOtnTable OBJECT-TYPE
	SYNTAX  SEQUENCE OF Pm10010ulhAlmlineHostLaneTxOtnEntry
	MAX-ACCESS not-accessible
	STATUS current
	DESCRIPTION
        "
        List of pm10010ulhAlmlineHostLaneTxOtn 
        Article
        "
	::= { pm10010ulhAlmLineUrg 204 }


pm10010ulhAlmlineHostLaneTxOtnEntry OBJECT-TYPE
	SYNTAX Pm10010ulhAlmlineHostLaneTxOtnEntry
	MAX-ACCESS not-accessible
	STATUS current
	DESCRIPTION
        "
        Row definition for the pm10010ulhAlmlineHostLaneTxOtn 
        table
        "
	INDEX   { pm10010ulhAlmlineHostLaneTxOtnIndex }
	::= { pm10010ulhAlmlineHostLaneTxOtnTable 1 }


Pm10010ulhAlmlineHostLaneTxOtnEntry ::=
	SEQUENCE {
	pm10010ulhAlmlineHostLaneTxOtnIndex
		INTEGER,
	pm10010ulhAlmLineTxOtnLofPortn
		EkiOnOff,
	pm10010ulhAlmLineTxOtnOofPortn
		EkiOnOff,
	pm10010ulhAlmLineTxOtnLomPortn
		EkiOnOff,
	pm10010ulhAlmLineTxOtnOomPortn
		EkiOnOff,
	pm10010ulhAlmLineTxOtnIaePortn
		EkiOnOff,
	pm10010ulhAlmLineTxSmBdiPortn
		EkiOnOff,
	pm10010ulhAlmLineTxOtnOtuAisPortn
		EkiOnOff,
	pm10010ulhAlmLineTxOtnOduAisPortn
		EkiOnOff
	}


pm10010ulhAlmlineHostLaneTxOtnIndex OBJECT-TYPE
	SYNTAX  INTEGER(0..128)
	MAX-ACCESS  read-only
	STATUS current
	DESCRIPTION
        "
        Index definition for the pm10010ulhAlmlineHostLaneTxOtn 
        table
        "
	::= { pm10010ulhAlmlineHostLaneTxOtnEntry 1 }


pm10010ulhAlmLineTxOtnLofPortn OBJECT-TYPE
	SYNTAX  EkiOnOff
	MAX-ACCESS read-only
	STATUS current
	DESCRIPTION
        "
        Line Host Tx LOF :This OID indicates 
        a Loss of Frame is detected on
         the Tx Host interface of the Line 
        Trscv <Help> Alarm indicating a 
        Loss of Frame is detected on the 
        Tx Host interface of the Line Trscv 
        <Condtype> LINE_TX_OTN_LOF <Probcause> 
        receiveFailure (41) <Alarmtype> 
        equipmentAlarm (5) <Polarity> (2) 
        "
	::= { pm10010ulhAlmlineHostLaneTxOtnEntry 17 }


pm10010ulhAlmLineTxOtnOofPortn OBJECT-TYPE
	SYNTAX  EkiOnOff
	MAX-ACCESS read-only
	STATUS current
	DESCRIPTION
        "
        Line Host Tx OOF :This OID indicates 
        an Out of Frame is detected on
         the Tx Host interface of the Line 
        Trscv <Help> Alarm indicating an 
        Out of Frame is detected on the 
        Tx Host interface of the Line Trscv 
        <Condtype> LINE_TX_OTN_OOF <Probcause> 
        receiveFailure (41) <Alarmtype> 
        equipmentAlarm (5) <Polarity> (2) 
        "
	::= { pm10010ulhAlmlineHostLaneTxOtnEntry 16 }


pm10010ulhAlmLineTxOtnLomPortn OBJECT-TYPE
	SYNTAX  EkiOnOff
	MAX-ACCESS read-only
	STATUS current
	DESCRIPTION
        "
        Line Host Tx LOM :This OID indicates 
        a Loss of Multiframe is detected 
        on the Tx Host interface of the 
        Line Trscv <Help> Alarm indicating 
        a Loss of Multiframe is detected 
        on the Tx Host interface of the 
        Line Trscv <Condtype> LINE_TX_OTN_LOM 
        <Probcause> receiveFailure (41) 
        <Alarmtype> equipmentAlarm (5)
         <Polarity> (2) 
        "
	::= { pm10010ulhAlmlineHostLaneTxOtnEntry 15 }


pm10010ulhAlmLineTxOtnOomPortn OBJECT-TYPE
	SYNTAX  EkiOnOff
	MAX-ACCESS read-only
	STATUS current
	DESCRIPTION
        "
        Line Host Tx OOM :This OID indicates 
        an Out of Multiframe is detected 
        on the Tx Host interface of the 
        Line Trscv <Help> Alarm indicating 
        an Out of Multiframe is detected 
        on the Tx Host interface of the 
        Line Trscv <Condtype> LINE_TX_OTN_OOM 
        <Probcause> receiveFailure (41) 
        <Alarmtype> equipmentAlarm (5)
         <Polarity> (2) 
        "
	::= { pm10010ulhAlmlineHostLaneTxOtnEntry 14 }


pm10010ulhAlmLineTxOtnIaePortn OBJECT-TYPE
	SYNTAX  EkiOnOff
	MAX-ACCESS read-only
	STATUS current
	DESCRIPTION
        "
        Line Host Tx IAE :This OID indicates 
        an Incoming Alignment Error is
         detected on the Tx Host interface 
        of the Line Trscv <Help> Alarm
         indicating an Incoming Alignment 
        Error is detected on the Tx Host 
        interface of the Line Trscv <Condtype> 
        LINE_TX_OTN_IAE <Probcause> receiveFailure 
        (41) <Alarmtype> equipmentAlarm 
        (5) <Polarity> (2) 
        "
	::= { pm10010ulhAlmlineHostLaneTxOtnEntry 13 }


pm10010ulhAlmLineTxSmBdiPortn OBJECT-TYPE
	SYNTAX  EkiOnOff
	MAX-ACCESS read-only
	STATUS current
	DESCRIPTION
        "
        Line Host Tx SM BDI :This OID
         indicates an SM Backward Defect 
        Indication is detected on the Tx 
        Host interface of the Line Trscv 
        <Help> Alarm indicating an SM Backward 
        Defect Indication is detected on 
        the Tx Host interface of the Line 
        Trscv <Condtype> LINE_TX_SM_BDI 
        <Probcause> informationalStatus(1000) 
        <Alarmtype> other (1) <Polarity> 
        (2) 
        "
	::= { pm10010ulhAlmlineHostLaneTxOtnEntry 12 }


pm10010ulhAlmLineTxOtnOtuAisPortn OBJECT-TYPE
	SYNTAX  EkiOnOff
	MAX-ACCESS read-only
	STATUS current
	DESCRIPTION
        "
        Line Host Tx OTU AIS :This OID 
        indicates an OTU This OID Indication 
        Signal is detected on the Tx Host 
        interface of the Line Trscv <Help> 
        Alarm indicating an OTU Alarm Indication 
        Signal is detected on the Tx Host 
        interface of the Line Trscv <Condtype> 
        LINE_TX_OTN_OTU_AIS <Probcause> 
        receiveFailure (41) <Alarmtype> 
        equipmentAlarm (5) <Polarity> (2) 
        "
	::= { pm10010ulhAlmlineHostLaneTxOtnEntry 11 }


pm10010ulhAlmLineTxOtnOduAisPortn OBJECT-TYPE
	SYNTAX  EkiOnOff
	MAX-ACCESS read-only
	STATUS current
	DESCRIPTION
        "
        Line Host Tx ODU AIS :This OID 
        indicates an ODU This OID Indication 
        Signal is detected on the Tx Host 
        interface of the Line Trscv <Help> 
        Alarm indicating an ODU Alarm Indication 
        Signal is detected on the Tx Host 
        interface of the Line Trscv <Condtype> 
        LINE_TX_OTN_ODU_AIS <Probcause> 
        receiveFailure (41) <Alarmtype> 
        equipmentAlarm (5) <Polarity> (2) 
        "
	::= { pm10010ulhAlmlineHostLaneTxOtnEntry 10 }


--- *********************************************************
---     TABLE for the pm10010ulhAlmclientSfpAlmDdm articles
--- *********************************************************

pm10010ulhAlmclientSfpAlmDdmTable OBJECT-TYPE
	SYNTAX  SEQUENCE OF Pm10010ulhAlmclientSfpAlmDdmEntry
	MAX-ACCESS not-accessible
	STATUS current
	DESCRIPTION
        "
        List of pm10010ulhAlmclientSfpAlmDdm 
        Article
        "
	::= { pm10010ulhAlmClientUrg 240 }


pm10010ulhAlmclientSfpAlmDdmEntry OBJECT-TYPE
	SYNTAX Pm10010ulhAlmclientSfpAlmDdmEntry
	MAX-ACCESS not-accessible
	STATUS current
	DESCRIPTION
        "
        Row definition for the pm10010ulhAlmclientSfpAlmDdm 
        table
        "
	INDEX   { pm10010ulhAlmclientSfpAlmDdmIndex }
	::= { pm10010ulhAlmclientSfpAlmDdmTable 1 }


Pm10010ulhAlmclientSfpAlmDdmEntry ::=
	SEQUENCE {
	pm10010ulhAlmclientSfpAlmDdmIndex
		INTEGER,
	pm10010ulhAlmRxPwrHighAlaPortn
		EkiOnOff,
	pm10010ulhAlmRxPwrLowAlaPortn
		EkiOnOff,
	pm10010ulhAlmTempHighAlaPortn
		EkiOnOff,
	pm10010ulhAlmTempLowAlaPortn
		EkiOnOff,
	pm10010ulhAlmVccHighAlaPortn
		EkiOnOff,
	pm10010ulhAlmVccLowAlaPortn
		EkiOnOff,
	pm10010ulhAlmTxBiasHighAlaPortn
		EkiOnOff,
	pm10010ulhAlmTxBiasLowAlaPortn
		EkiOnOff,
	pm10010ulhAlmTxPwrHighAlaPortn
		EkiOnOff,
	pm10010ulhAlmTxPwrLowAlaPortn
		EkiOnOff
	}


pm10010ulhAlmclientSfpAlmDdmIndex OBJECT-TYPE
	SYNTAX  INTEGER(0..128)
	MAX-ACCESS  read-only
	STATUS current
	DESCRIPTION
        "
        Index definition for the pm10010ulhAlmclientSfpAlmDdm 
        table
        "
	::= { pm10010ulhAlmclientSfpAlmDdmEntry 1 }


pm10010ulhAlmRxPwrHighAlaPortn OBJECT-TYPE
	SYNTAX  EkiOnOff
	MAX-ACCESS read-only
	STATUS current
	DESCRIPTION
        "
        Client Trscv Rx Power High :This 
        OID indicates that the Trscv input 
        power of port is higher than the 
        threshold value written in the
         Trscv EEPROM <Help> Alarm indicating 
        that the Trscv input power of port 
        is higher than the threshold value 
        written in the Trscv EEPROM <Condtype> 
        RX_PWR_HIGH_ALA_1 <Probcause> receiveFailure 
        (41) <Alarmtype> equipmentAlarm 
        (5) <Polarity> (2) 
        "
	::= { pm10010ulhAlmclientSfpAlmDdmEntry 17 }


pm10010ulhAlmRxPwrLowAlaPortn OBJECT-TYPE
	SYNTAX  EkiOnOff
	MAX-ACCESS read-only
	STATUS current
	DESCRIPTION
        "
        Client Trscv Rx Power Low :This 
        OID indicates that the Trscv input 
        power of port is lower than the 
        threshold value written in the
         Trscv EEPROM <Help> Alarm indicating 
        that the Trscv input power of port 
        is lower than the threshold value 
        written in the Trscv EEPROM <Condtype> 
        RX_PWR_LOW_ALA_1 <Probcause> receiveFailure 
        (41) <Alarmtype> equipmentAlarm 
        (5) <Polarity> (2) 
        "
	::= { pm10010ulhAlmclientSfpAlmDdmEntry 16 }


pm10010ulhAlmTempHighAlaPortn OBJECT-TYPE
	SYNTAX  EkiOnOff
	MAX-ACCESS read-only
	STATUS current
	DESCRIPTION
        "
        Client Trscv Temp High :This OID 
        indicates that the Trscv temperature 
        of port is higher than the threshold 
        value written in the Trscv EEPROM 
        <Help> Alarm indicating that the 
        Trscv temperature of port is higher 
        than the threshold value written 
        in the Trscv EEPROM <Condtype>
         TEMP_HIGH_ALA_1 <Probcause> temperatureUnacceptable 
        (51) <Alarmtype> equipmentAlarm 
        (5) <Polarity> (2) 
        "
	::= { pm10010ulhAlmclientSfpAlmDdmEntry 9 }


pm10010ulhAlmTempLowAlaPortn OBJECT-TYPE
	SYNTAX  EkiOnOff
	MAX-ACCESS read-only
	STATUS current
	DESCRIPTION
        "
        Client Trscv Temp Low :This OID 
        indicates that the Trscv temperature 
        of port is lower than the threshold 
        value written in the Trscv EEPROM 
        <Help> Alarm indicating that the 
        Trscv temperature of port is lower 
        than the threshold value written 
        in the Trscv EEPROM <Condtype>
         TEMP_LOW_ALA_1 <Probcause> temperatureUnacceptable 
        (51) <Alarmtype> equipmentAlarm 
        (5) <Polarity> (2) 
        "
	::= { pm10010ulhAlmclientSfpAlmDdmEntry 8 }


pm10010ulhAlmVccHighAlaPortn OBJECT-TYPE
	SYNTAX  EkiOnOff
	MAX-ACCESS read-only
	STATUS current
	DESCRIPTION
        "
        Client Trscv Power Supply High 
        :This OID indicates that the Trscv 
        power supply of port is higher
         than the threshold value written 
        in the Trscv EEPROM <Help> Alarm 
        indicating that the Trscv power 
        supply of port is higher than the 
        threshold value written in the
         Trscv EEPROM <Condtype> VCC_HIGH_ALA_1 
        <Probcause> powerProblem (36) <Alarmtype> 
        equipmentAlarm (5) <Polarity> (2) 
        "
	::= { pm10010ulhAlmclientSfpAlmDdmEntry 7 }


pm10010ulhAlmVccLowAlaPortn OBJECT-TYPE
	SYNTAX  EkiOnOff
	MAX-ACCESS read-only
	STATUS current
	DESCRIPTION
        "
        Client Trscv Power Supply Low
         :This OID indicates that the Trscv 
        power supply of port is lower than 
        the threshold value written in
         the Trscv EEPROM <Help> Alarm
         indicating that the Trscv power 
        supply of port is lower than the 
        threshold value written in the
         Trscv EEPROM <Condtype> VCC_LOW_ALA_1 
        <Probcause> powerProblem (36) <Alarmtype> 
        equipmentAlarm (5) <Polarity> (2) 
        "
	::= { pm10010ulhAlmclientSfpAlmDdmEntry 6 }


pm10010ulhAlmTxBiasHighAlaPortn OBJECT-TYPE
	SYNTAX  EkiOnOff
	MAX-ACCESS read-only
	STATUS current
	DESCRIPTION
        "
        Client Trscv Bias High :This OID 
        indicates that the Trscv laser
         bias current of port is higher 
        than the threshold value written 
        in the Trscv EEPROM <Help> Alarm 
        indicating that the Trscv laser 
        bias current of port is higher
         than the threshold value written 
        in the Trscv EEPROM <Condtype>
         TX_BIAS_HIGH_ALA_1 <Probcause> 
        transmitterFailure (56) <Alarmtype> 
        equipmentAlarm (5) <Polarity> (2) 
        "
	::= { pm10010ulhAlmclientSfpAlmDdmEntry 5 }


pm10010ulhAlmTxBiasLowAlaPortn OBJECT-TYPE
	SYNTAX  EkiOnOff
	MAX-ACCESS read-only
	STATUS current
	DESCRIPTION
        "
        Client Trscv Bias Low :This OID 
        indicates that the Trscv laser
         bias current of port is lower
         than the threshold value written 
        in the Trscv EEPROM <Help> Alarm 
        indicating that the Trscv laser 
        bias current of port is lower than 
        the threshold value written in
         the Trscv EEPROM <Condtype> TX_BIAS_LOW_ALA_1 
        <Probcause> transmitterFailure
         (56) <Alarmtype> equipmentAlarm 
        (5) <Polarity> (2) 
        "
	::= { pm10010ulhAlmclientSfpAlmDdmEntry 4 }


pm10010ulhAlmTxPwrHighAlaPortn OBJECT-TYPE
	SYNTAX  EkiOnOff
	MAX-ACCESS read-only
	STATUS current
	DESCRIPTION
        "
        Client Trscv Tx Power High :This 
        OID indicates that the Trscv output 
        power of port is higher than the 
        threshold value written in the
         Trscv EEPROM <Help> Alarm indicating 
        that the Trscv output power of
         port is higher than the threshold 
        value written in the Trscv EEPROM 
        <Condtype> TX_PWR_HIGH_ALA_1 <Probcause> 
        transmitterFailure (56) <Alarmtype> 
        equipmentAlarm (5) <Polarity> (2) 
        "
	::= { pm10010ulhAlmclientSfpAlmDdmEntry 3 }


pm10010ulhAlmTxPwrLowAlaPortn OBJECT-TYPE
	SYNTAX  EkiOnOff
	MAX-ACCESS read-only
	STATUS current
	DESCRIPTION
        "
        Client Trscv Tx Power Low :This 
        OID indicates that the Trscv output 
        power of port is lower than the 
        threshold value written in the
         Trscv EEPROM <Help> Alarm indicating 
        that the Trscv output power of
         port is lower than the threshold 
        value written in the Trscv EEPROM 
        <Condtype> TX_PWR_LOW_ALA_1 <Probcause> 
        transmitterFailure (56) <Alarmtype> 
        equipmentAlarm (5) <Polarity> (2) 
        "
	::= { pm10010ulhAlmclientSfpAlmDdmEntry 2 }


--- *********************************************************
---     TABLE for the pm10010ulhAlmclientSfpWarnDdm articles
--- *********************************************************

pm10010ulhAlmclientSfpWarnDdmTable OBJECT-TYPE
	SYNTAX  SEQUENCE OF Pm10010ulhAlmclientSfpWarnDdmEntry
	MAX-ACCESS not-accessible
	STATUS current
	DESCRIPTION
        "
        List of pm10010ulhAlmclientSfpWarnDdm 
        Article
        "
	::= { pm10010ulhAlmClientNurg 272 }


pm10010ulhAlmclientSfpWarnDdmEntry OBJECT-TYPE
	SYNTAX Pm10010ulhAlmclientSfpWarnDdmEntry
	MAX-ACCESS not-accessible
	STATUS current
	DESCRIPTION
        "
        Row definition for the pm10010ulhAlmclientSfpWarnDdm 
        table
        "
	INDEX   { pm10010ulhAlmclientSfpWarnDdmIndex }
	::= { pm10010ulhAlmclientSfpWarnDdmTable 1 }


Pm10010ulhAlmclientSfpWarnDdmEntry ::=
	SEQUENCE {
	pm10010ulhAlmclientSfpWarnDdmIndex
		INTEGER,
	pm10010ulhAlmRxPwrHighWngPortn
		EkiOnOff,
	pm10010ulhAlmRxPwrLowWngPortn
		EkiOnOff,
	pm10010ulhAlmTempHighWngPortn
		EkiOnOff,
	pm10010ulhAlmTempLowWngPortn
		EkiOnOff,
	pm10010ulhAlmVccHighWngPortn
		EkiOnOff,
	pm10010ulhAlmVccLowWngPortn
		EkiOnOff,
	pm10010ulhAlmTxBiasHighWngPortn
		EkiOnOff,
	pm10010ulhAlmTxBiasLowWngPortn
		EkiOnOff,
	pm10010ulhAlmTxPwrHighWngPortn
		EkiOnOff,
	pm10010ulhAlmTxPwLowWngPortn
		EkiOnOff
	}


pm10010ulhAlmclientSfpWarnDdmIndex OBJECT-TYPE
	SYNTAX  INTEGER(0..128)
	MAX-ACCESS  read-only
	STATUS current
	DESCRIPTION
        "
        Index definition for the pm10010ulhAlmclientSfpWarnDdm 
        table
        "
	::= { pm10010ulhAlmclientSfpWarnDdmEntry 1 }


pm10010ulhAlmRxPwrHighWngPortn OBJECT-TYPE
	SYNTAX  EkiOnOff
	MAX-ACCESS read-only
	STATUS current
	DESCRIPTION
        "
        Client Trscv Rx Power High Warning 
        :This OID indicates that the Trscv 
        input power is higher than the
         threshold value written in the 
        Trscv EEPROM <Help> Warning indicating 
        that the Trscv input power is higher 
        than the threshold value written 
        in the Trscv EEPROM <Condtype>
         RX_PWR_HIGH_WNG_1 <Probcause>
         receiveFailure (41) <Alarmtype> 
        equipmentAlarm (5) <Polarity> (2) 
        "
	::= { pm10010ulhAlmclientSfpWarnDdmEntry 17 }


pm10010ulhAlmRxPwrLowWngPortn OBJECT-TYPE
	SYNTAX  EkiOnOff
	MAX-ACCESS read-only
	STATUS current
	DESCRIPTION
        "
        Client Trscv Rx Power Low Warning 
        :This OID indicates that the Trscv 
        input power is lower than the threshold 
        value written in the Trscv EEPROM 
        <Help> Warning indicating that
         the Trscv input power is lower 
        than the threshold value written 
        in the Trscv EEPROM <Condtype>
         RX_PWR_LOW_WNG_1 <Probcause> receiveFailure 
        (41) <Alarmtype> equipmentAlarm 
        (5) <Polarity> (2) 
        "
	::= { pm10010ulhAlmclientSfpWarnDdmEntry 16 }


pm10010ulhAlmTempHighWngPortn OBJECT-TYPE
	SYNTAX  EkiOnOff
	MAX-ACCESS read-only
	STATUS current
	DESCRIPTION
        "
        Client Trscv Temp High Warning 
        :This OID indicates that the Trscv 
        temperature is higher than the
         threshold value written in the 
        Trscv EEPROM <Help> Warning indicating 
        that the Trscv temperature is higher 
        than the threshold value written 
        in the Trscv EEPROM <Condtype>
         TEMP_HIGH_WNG_1 <Probcause> temperatureUnacceptable 
        (51) <Alarmtype> equipmentAlarm 
        (5) <Polarity> (2) 
        "
	::= { pm10010ulhAlmclientSfpWarnDdmEntry 9 }


pm10010ulhAlmTempLowWngPortn OBJECT-TYPE
	SYNTAX  EkiOnOff
	MAX-ACCESS read-only
	STATUS current
	DESCRIPTION
        "
        Client Trscv Temp Low Warning
         :This OID indicates that the Trscv 
        temperature is lower than the threshold 
        value written in the Trscv EEPROM 
        <Help> Warning indicating that
         the Trscv temperature is lower 
        than the threshold value written 
        in the Trscv EEPROM <Condtype>
         TEMP_LOW_WNG_1 <Probcause> temperatureUnacceptable 
        (51) <Alarmtype> equipmentAlarm 
        (5) <Polarity> (2) 
        "
	::= { pm10010ulhAlmclientSfpWarnDdmEntry 8 }


pm10010ulhAlmVccHighWngPortn OBJECT-TYPE
	SYNTAX  EkiOnOff
	MAX-ACCESS read-only
	STATUS current
	DESCRIPTION
        "
        Client Trscv Power Supply High 
        Warning :This OID indicates that 
        the Trscv power supply is higher 
        than the threshold value written 
        in the Trscv EEPROM <Help> Warning 
        indicating that the Trscv power 
        supply is higher than the threshold 
        value written in the Trscv EEPROM 
        <Condtype> VCC_HIGH_WNG_1 <Probcause> 
        powerProblem (36) <Alarmtype> equipmentAlarm 
        (5) <Polarity> (2) 
        "
	::= { pm10010ulhAlmclientSfpWarnDdmEntry 7 }


pm10010ulhAlmVccLowWngPortn OBJECT-TYPE
	SYNTAX  EkiOnOff
	MAX-ACCESS read-only
	STATUS current
	DESCRIPTION
        "
        Client Trscv Power Supply Low
         Warning :This OID indicates that 
        the Trscv power supply is lower 
        than the threshold value written 
        in the Trscv EEPROM <Help> Warning 
        indicating that the Trscv power 
        supply is lower than the threshold 
        value written in the Trscv EEPROM 
        <Condtype> VCC_LOW_WNG_1 <Probcause> 
        powerProblem (36) <Alarmtype> equipmentAlarm 
        (5) <Polarity> (2) 
        "
	::= { pm10010ulhAlmclientSfpWarnDdmEntry 6 }


pm10010ulhAlmTxBiasHighWngPortn OBJECT-TYPE
	SYNTAX  EkiOnOff
	MAX-ACCESS read-only
	STATUS current
	DESCRIPTION
        "
        Client Trscv Bias High Warning 
        :This OID indicates that the Trscv 
        laser bias current is higher than 
        the threshold value written in
         the Trscv EEPROM <Help> Warning 
        indicating that the Trscv laser 
        bias current is higher than the 
        threshold value written in the
         Trscv EEPROM <Condtype> TX_BIAS_HIGH_WNG_1 
        <Probcause> transmitterFailure
         (56) <Alarmtype> equipmentAlarm 
        (5) <Polarity> (2) 
        "
	::= { pm10010ulhAlmclientSfpWarnDdmEntry 5 }


pm10010ulhAlmTxBiasLowWngPortn OBJECT-TYPE
	SYNTAX  EkiOnOff
	MAX-ACCESS read-only
	STATUS current
	DESCRIPTION
        "
        Client Trscv Bias Low Warning
         :This OID indicates that the Trscv 
        laser bias current is lower than 
        the threshold value written in
         the Trscv EEPROM <Help> Warning 
        indicating that the Trscv laser 
        bias current is lower than the
         threshold value written in the 
        Trscv EEPROM <Condtype> TX_BIAS_LOW_WNG_1 
        <Probcause> transmitterFailure
         (56) <Alarmtype> equipmentAlarm 
        (5) <Polarity> (2) 
        "
	::= { pm10010ulhAlmclientSfpWarnDdmEntry 4 }


pm10010ulhAlmTxPwrHighWngPortn OBJECT-TYPE
	SYNTAX  EkiOnOff
	MAX-ACCESS read-only
	STATUS current
	DESCRIPTION
        "
        Client Trscv Tx Power High Warning 
        :This OID indicates that the Trscv 
        output power is higher than the 
        threshold value written in the
         Trscv EEPROM <Help> Warning indicating 
        that the Trscv output power is
         higher than the threshold value 
        written in the Trscv EEPROM <Condtype> 
        TX_PWR_HIGH_WNG_1 <Probcause> transmitterFailure 
        (56) <Alarmtype> equipmentAlarm 
        (5) <Polarity> (2) 
        "
	::= { pm10010ulhAlmclientSfpWarnDdmEntry 3 }


pm10010ulhAlmTxPwLowWngPortn OBJECT-TYPE
	SYNTAX  EkiOnOff
	MAX-ACCESS read-only
	STATUS current
	DESCRIPTION
        "
        Client Trscv Tx Power Low Warning 
        :This OID indicates that the Trscv 
        output power is lower than the
         threshold value written in the 
        Trscv EEPROM <Help> Warning indicating 
        that the Trscv output power is
         lower than the threshold value 
        written in the Trscv EEPROM <Condtype> 
        TX_PW_LOW_WNG_1 <Probcause> transmitterFailure 
        (56) <Alarmtype> equipmentAlarm 
        (5) <Polarity> (2) 
        "
	::= { pm10010ulhAlmclientSfpWarnDdmEntry 2 }


--- *****************************************************
---     LEAF for the modFanFail article
--- *****************************************************
pm10010ulhAlmmodFanFail OBJECT IDENTIFIER ::= { pm10010ulhAlmOtherUrg 336 }




pm10010ulhAlmFanHighSpeed OBJECT-TYPE
	  SYNTAX EkiOnOff
	  MAX-ACCESS read-only
	  STATUS current
	  DESCRIPTION
        "
        Fan High Speed :This OID indicates 
        the fan is blowing at high speed 
        <Help> This alarm indicates the 
        fan is blowing at high speed <Condtype> 
        FAN_HIGH_SPEED <Probcause> other 
        (1) <Alarmtype> other (1) <Polarity> 
        (2) 
        "
	  ::= { pm10010ulhAlmmodFanFail 2 }



pm10010ulhAlmFanFail OBJECT-TYPE
	  SYNTAX EkiOnOff
	  MAX-ACCESS read-only
	  STATUS current
	  DESCRIPTION
        "
        Fan Module Failure :This OID indicates 
        that the FAN unit inside the module 
        is in fail condition  <Help>  This 
        alarm indicates that the FAN is 
        in a fail condition. <Condtype> 
        FAN_FAIL <Probcause> heatingVentCoolingSystemProblem 
        (22) <Alarmtype> equipmentAlarm 
        (5) <Polarity> (2) 
        "
	  ::= { pm10010ulhAlmmodFanFail 1 }








--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm10010ulhCtrlconfMgnt1 OBJECT IDENTIFIER ::= { pm10010ulhCtrlOther 1 }




pm10010ulhCtrlConf2Clear1 OBJECT-TYPE
	  SYNTAX EkiOnOff
	  MAX-ACCESS read-write
	  STATUS current
	  DESCRIPTION
        "
        Clear Configuration Tables :This 
        OID clears the configuration tables 
        from configuration2 in the flash. 
         <Help>  This control restores
         the default configuration of the 
        module
        "
	  ::= { pm10010ulhCtrlconfMgnt1 14 }



pm10010ulhCtrlConf2Flash1 OBJECT-TYPE
	  SYNTAX EkiOnOff
	  MAX-ACCESS read-write
	  STATUS current
	  DESCRIPTION
        "
        Write Configuration Tables :This 
        OID saves the current configuration 
        of the PM as configuration2 in
         the flash.  <Help>  This control 
        saves the customer configuration 
        on the module
        "
	  ::= { pm10010ulhCtrlconfMgnt1 10 }



pm10010ulhCtrlConf2Load1 OBJECT-TYPE
	  SYNTAX EkiOnOff
	  MAX-ACCESS read-write
	  STATUS current
	  DESCRIPTION
        "
        Load Configuration Tables Set
         Nb 2 :When set this OID enables 
        loading from flash configuration2 
        into the PM.
        "
	  ::= { pm10010ulhCtrlconfMgnt1 2 }



pm10010ulhCtrlConf1Load1 OBJECT-TYPE
	  SYNTAX EkiOnOff
	  MAX-ACCESS read-write
	  STATUS current
	  DESCRIPTION
        "
        Load Configuration Tables Set
         Nb 1 :When set this OID enables 
        loading from flash configuration1 
        into the PM.
        "
	  ::= { pm10010ulhCtrlconfMgnt1 1 }



--- *****************************************************
---     LEAF for the synth4 article
--- *****************************************************
pm10010ulhCtrlsynth4 OBJECT IDENTIFIER ::= { pm10010ulhCtrlOther 4 }




pm10010ulhCtrlCorrelatOff OBJECT-TYPE
	  SYNTAX EkiOnOff
	  MAX-ACCESS read-write
	  STATUS current
	  DESCRIPTION
        "
        Disable Alarm Correlation :This 
        OID disables the alarm correlation 
        in the PM.
        "
	  ::= { pm10010ulhCtrlsynth4 2 }



pm10010ulhCtrlCorrelatOn OBJECT-TYPE
	  SYNTAX EkiOnOff
	  MAX-ACCESS read-write
	  STATUS current
	  DESCRIPTION
        "
        Enable Alarm Correlation :This 
        OID enables the alarm correlation 
        in the PM.
        "
	  ::= { pm10010ulhCtrlsynth4 1 }



--- *****************************************************
---     LEAF for the swMgnt article
--- *****************************************************
pm10010ulhCtrlswMgnt OBJECT IDENTIFIER ::= { pm10010ulhCtrlOther 5 }




pm10010ulhCtrlLoadSwBank2 OBJECT-TYPE
	  SYNTAX EkiOnOff
	  MAX-ACCESS read-write
	  STATUS current
	  DESCRIPTION
        "
        Set Software Nb 2 As Active :This 
        OID, when set, loads the SW from 
        bank2 into the PM. It must be followed 
        by a reset.  <Help>  This controls 
        selects the second SW bank as the 
        active bank for the next module 
        reset
        "
	  ::= { pm10010ulhCtrlswMgnt 6 }



pm10010ulhCtrlLoadSwBank1 OBJECT-TYPE
	  SYNTAX EkiOnOff
	  MAX-ACCESS read-write
	  STATUS current
	  DESCRIPTION
        "
        Set Software Nb 1 As Active :This 
        OID, when set, loads the SW from 
        bank1 into the PM. It must be followed 
        by a reset.  <Help>  This controls 
        selects the first SW bank as the 
        active bank for the next module 
        reset
        "
	  ::= { pm10010ulhCtrlswMgnt 5 }



pm10010ulhCtrlWarmReset OBJECT-TYPE
	  SYNTAX EkiOnOff
	  MAX-ACCESS read-write
	  STATUS current
	  DESCRIPTION
        "
        PM Warm Reset :This OID, when
         set, causes a warm reset of the 
        PM. This reset is not traffic affecting, 
        and the configuration of PM remains 
        unchanged.  <Help>  This control 
        initiates a warm reset of the module. 
        "
	  ::= { pm10010ulhCtrlswMgnt 3 }



pm10010ulhCtrlColdReset OBJECT-TYPE
	  SYNTAX EkiOnOff
	  MAX-ACCESS read-write
	  STATUS current
	  DESCRIPTION
        "
        PM Cold Reset :This OID, when
         set, causes a cold reset of the 
        PM. This reset is traffic affecting, 
        and the configuration of PM is
         reloaded on start-up.  <Help>
          This control initiates a cold 
        reset of the module. 
        "
	  ::= { pm10010ulhCtrlswMgnt 2 }



--- *****************************************************
---     LEAF for the gwMgnt article
--- *****************************************************
pm10010ulhCtrlgwMgnt OBJECT IDENTIFIER ::= { pm10010ulhCtrlOther 6 }




pm10010ulhCtrlLoadGwBank4 OBJECT-TYPE
	  SYNTAX EkiOnOff
	  MAX-ACCESS read-write
	  STATUS current
	  DESCRIPTION
        "
        Set Gateware Nb 4 As Active :This 
        OID, when set, loads the GW from 
        bank4 (Flash) into the PM. It is 
        followed by an automatic gateware 
        cold reset.
        "
	  ::= { pm10010ulhCtrlgwMgnt 8 }



pm10010ulhCtrlLoadGwBank3 OBJECT-TYPE
	  SYNTAX EkiOnOff
	  MAX-ACCESS read-write
	  STATUS current
	  DESCRIPTION
        "
        Set Gateware Nb 3 As Active :This 
        OID, when set, loads the GW from 
        bank3 (Flash) into the PM. It is 
        followed by an automatic gateware 
        cold reset.  <Help>  This controls 
        initiates a cold reset of the module 
        and select the third GW bank as 
        the active bank
        "
	  ::= { pm10010ulhCtrlgwMgnt 7 }



pm10010ulhCtrlLoadGwBank2 OBJECT-TYPE
	  SYNTAX EkiOnOff
	  MAX-ACCESS read-write
	  STATUS current
	  DESCRIPTION
        "
        Set Gateware Nb 2 As Active :This 
        OID, when set, loads the GW from 
        bank2 (Flash) into the PM. It is 
        followed by an automatic gateware 
        cold reset.
        "
	  ::= { pm10010ulhCtrlgwMgnt 6 }



pm10010ulhCtrlLoadGwBank1 OBJECT-TYPE
	  SYNTAX EkiOnOff
	  MAX-ACCESS read-write
	  STATUS current
	  DESCRIPTION
        "
        Set Gateware Nb 1 As Active :This 
        OID, when set, loads the GW from 
        bank1 (Flash) into the PM. It is 
        followed by an automatic gateware 
        cold reset.  <Help>  This controls 
        initiates a cold reset of the module 
        and select the first GW bank as 
        the active bank
        "
	  ::= { pm10010ulhCtrlgwMgnt 5 }



pm10010ulhCtrlCurrentGwReset OBJECT-TYPE
	  SYNTAX EkiOnOff
	  MAX-ACCESS read-write
	  STATUS current
	  DESCRIPTION
        "
        Active Gateware Reset :This OID, 
        when set, resets the active gateware. 
        It is traffic affecting.
        "
	  ::= { pm10010ulhCtrlgwMgnt 1 }



--- *********************************************************
---     TABLE for the pm10010ulhCtrlaccessLoop articles
--- *********************************************************

pm10010ulhCtrlaccessLoopTable OBJECT-TYPE
	SYNTAX  SEQUENCE OF Pm10010ulhCtrlaccessLoopEntry
	MAX-ACCESS not-accessible
	STATUS current
	DESCRIPTION
        "
        List of pm10010ulhCtrlaccessLoop 
        Article
        "
	::= { pm10010ulhCtrlClient 16 }


pm10010ulhCtrlaccessLoopEntry OBJECT-TYPE
	SYNTAX Pm10010ulhCtrlaccessLoopEntry
	MAX-ACCESS not-accessible
	STATUS current
	DESCRIPTION
        "
        Row definition for the pm10010ulhCtrlaccessLoop 
        table
        "
	INDEX   { pm10010ulhCtrlaccessLoopIndex }
	::= { pm10010ulhCtrlaccessLoopTable 1 }


Pm10010ulhCtrlaccessLoopEntry ::=
	SEQUENCE {
	pm10010ulhCtrlaccessLoopIndex
		INTEGER,
	pm10010ulhCtrlaccessLoopPortn
		EkiState
	}


pm10010ulhCtrlaccessLoopIndex OBJECT-TYPE
	SYNTAX  INTEGER(0..128)
	MAX-ACCESS  read-only
	STATUS current
	DESCRIPTION
        "
        Index definition for the pm10010ulhCtrlaccessLoop 
        table
        "
	::= { pm10010ulhCtrlaccessLoopEntry 1 }


pm10010ulhCtrlaccessLoopPortn OBJECT-TYPE
	SYNTAX  EkiState
	MAX-ACCESS read-write
	STATUS current
	DESCRIPTION
        "
        Client Facility Loopback :This 
        OID, when set at '1' puts the client 
        port in loopback, looping the received 
        10 Gb/s signal on the transmit
         10 Gb/s output.  <Help> This control 
        enables the Out Loopback on the 
        client port, looping the client 
        input signal on the client output
        "
	::= { pm10010ulhCtrlaccessLoopEntry 2 }


--- *********************************************************
---     TABLE for the pm10010ulhCtrlclientLoopToLine articles
--- *********************************************************

pm10010ulhCtrlclientLoopToLineTable OBJECT-TYPE
	SYNTAX  SEQUENCE OF Pm10010ulhCtrlclientLoopToLineEntry
	MAX-ACCESS not-accessible
	STATUS current
	DESCRIPTION
        "
        List of pm10010ulhCtrlclientLoopToLine 
        Article
        "
	::= { pm10010ulhCtrlClient 17 }


pm10010ulhCtrlclientLoopToLineEntry OBJECT-TYPE
	SYNTAX Pm10010ulhCtrlclientLoopToLineEntry
	MAX-ACCESS not-accessible
	STATUS current
	DESCRIPTION
        "
        Row definition for the pm10010ulhCtrlclientLoopToLine 
        table
        "
	INDEX   { pm10010ulhCtrlclientLoopToLineIndex }
	::= { pm10010ulhCtrlclientLoopToLineTable 1 }


Pm10010ulhCtrlclientLoopToLineEntry ::=
	SEQUENCE {
	pm10010ulhCtrlclientLoopToLineIndex
		INTEGER,
	pm10010ulhCtrlclientLoopToLinePortn
		EkiState
	}


pm10010ulhCtrlclientLoopToLineIndex OBJECT-TYPE
	SYNTAX  INTEGER(0..128)
	MAX-ACCESS  read-only
	STATUS current
	DESCRIPTION
        "
        Index definition for the pm10010ulhCtrlclientLoopToLine 
        table
        "
	::= { pm10010ulhCtrlclientLoopToLineEntry 1 }


pm10010ulhCtrlclientLoopToLinePortn OBJECT-TYPE
	SYNTAX  EkiState
	MAX-ACCESS read-write
	STATUS current
	DESCRIPTION
        "
        Client Terminal Loopback :This 
        OID, when set, puts the client
         port in loop back, looping the 
        10 Gb/s output signal on the 10 
        Gb/s input.<Help> This control
         enables the In Loopback on the 
        client port, looping the client 
        output signal on the client input
        "
	::= { pm10010ulhCtrlclientLoopToLineEntry 2 }


--- *********************************************************
---     TABLE for the pm10010ulhCtrlcsfUpIns articles
--- *********************************************************

pm10010ulhCtrlcsfUpInsTable OBJECT-TYPE
	SYNTAX  SEQUENCE OF Pm10010ulhCtrlcsfUpInsEntry
	MAX-ACCESS not-accessible
	STATUS current
	DESCRIPTION
        "
        List of pm10010ulhCtrlcsfUpIns 
        Article
        "
	::= { pm10010ulhCtrlClient 21 }


pm10010ulhCtrlcsfUpInsEntry OBJECT-TYPE
	SYNTAX Pm10010ulhCtrlcsfUpInsEntry
	MAX-ACCESS not-accessible
	STATUS current
	DESCRIPTION
        "
        Row definition for the pm10010ulhCtrlcsfUpIns 
        table
        "
	INDEX   { pm10010ulhCtrlcsfUpInsIndex }
	::= { pm10010ulhCtrlcsfUpInsTable 1 }


Pm10010ulhCtrlcsfUpInsEntry ::=
	SEQUENCE {
	pm10010ulhCtrlcsfUpInsIndex
		INTEGER,
	pm10010ulhCtrlcsfUpInsPortn
		EkiState
	}


pm10010ulhCtrlcsfUpInsIndex OBJECT-TYPE
	SYNTAX  INTEGER(0..128)
	MAX-ACCESS  read-only
	STATUS current
	DESCRIPTION
        "
        Index definition for the pm10010ulhCtrlcsfUpIns 
        table
        "
	::= { pm10010ulhCtrlcsfUpInsEntry 1 }


pm10010ulhCtrlcsfUpInsPortn OBJECT-TYPE
	SYNTAX  EkiState
	MAX-ACCESS read-write
	STATUS current
	DESCRIPTION
        "
        Client Signal Fail Insertion :This 
        OID, when set, inserts  a client 
        signal fail in the upstream client 
        Port.  <Help>  This control inserts 
        a Client Signal Fail for the client 
        port
        "
	::= { pm10010ulhCtrlcsfUpInsEntry 2 }


--- *********************************************************
---     TABLE for the pm10010ulhCtrlcaisDwIns articles
--- *********************************************************

pm10010ulhCtrlcaisDwInsTable OBJECT-TYPE
	SYNTAX  SEQUENCE OF Pm10010ulhCtrlcaisDwInsEntry
	MAX-ACCESS not-accessible
	STATUS current
	DESCRIPTION
        "
        List of pm10010ulhCtrlcaisDwIns 
        Article
        "
	::= { pm10010ulhCtrlClient 22 }


pm10010ulhCtrlcaisDwInsEntry OBJECT-TYPE
	SYNTAX Pm10010ulhCtrlcaisDwInsEntry
	MAX-ACCESS not-accessible
	STATUS current
	DESCRIPTION
        "
        Row definition for the pm10010ulhCtrlcaisDwIns 
        table
        "
	INDEX   { pm10010ulhCtrlcaisDwInsIndex }
	::= { pm10010ulhCtrlcaisDwInsTable 1 }


Pm10010ulhCtrlcaisDwInsEntry ::=
	SEQUENCE {
	pm10010ulhCtrlcaisDwInsIndex
		INTEGER,
	pm10010ulhCtrlcaisDwInsPortn
		EkiState
	}


pm10010ulhCtrlcaisDwInsIndex OBJECT-TYPE
	SYNTAX  INTEGER(0..128)
	MAX-ACCESS  read-only
	STATUS current
	DESCRIPTION
        "
        Index definition for the pm10010ulhCtrlcaisDwIns 
        table
        "
	::= { pm10010ulhCtrlcaisDwInsEntry 1 }


pm10010ulhCtrlcaisDwInsPortn OBJECT-TYPE
	SYNTAX  EkiState
	MAX-ACCESS read-write
	STATUS current
	DESCRIPTION
        "
        Client AIS Insertion :This OID, 
        when set, inserts a client AIS
         on the downstream client Port. 
         <Help>  This control inserts a 
        Client AIS for the client port
        "
	::= { pm10010ulhCtrlcaisDwInsEntry 2 }


--- *********************************************************
---     TABLE for the pm10010ulhCtrlcommAccessLoop articles
--- *********************************************************

pm10010ulhCtrlcommAccessLoopTable OBJECT-TYPE
	SYNTAX  SEQUENCE OF Pm10010ulhCtrlcommAccessLoopEntry
	MAX-ACCESS not-accessible
	STATUS current
	DESCRIPTION
        "
        List of pm10010ulhCtrlcommAccessLoop 
        Article
        "
	::= { pm10010ulhCtrlLine 64 }


pm10010ulhCtrlcommAccessLoopEntry OBJECT-TYPE
	SYNTAX Pm10010ulhCtrlcommAccessLoopEntry
	MAX-ACCESS not-accessible
	STATUS current
	DESCRIPTION
        "
        Row definition for the pm10010ulhCtrlcommAccessLoop 
        table
        "
	INDEX   { pm10010ulhCtrlcommAccessLoopIndex }
	::= { pm10010ulhCtrlcommAccessLoopTable 1 }


Pm10010ulhCtrlcommAccessLoopEntry ::=
	SEQUENCE {
	pm10010ulhCtrlcommAccessLoopIndex
		INTEGER,
	pm10010ulhCtrlcommAccessLoopPortn
		EkiState
	}


pm10010ulhCtrlcommAccessLoopIndex OBJECT-TYPE
	SYNTAX  INTEGER(0..128)
	MAX-ACCESS  read-only
	STATUS current
	DESCRIPTION
        "
        Index definition for the pm10010ulhCtrlcommAccessLoop 
        table
        "
	::= { pm10010ulhCtrlcommAccessLoopEntry 1 }


pm10010ulhCtrlcommAccessLoopPortn OBJECT-TYPE
	SYNTAX  EkiState
	MAX-ACCESS read-write
	STATUS current
	DESCRIPTION
        "
        Line Terminal Loopback :This OID, 
        when set, puts the module in common 
        access loop back, looping the 200 
        Gb/s output signal on the 200 Gb/s 
        input.<Help> This control enables 
        the In Loopback on the line port, 
        looping the 200 Gb/s output signal 
        on the 200 Gb/s input
        "
	::= { pm10010ulhCtrlcommAccessLoopEntry 2 }


--- *********************************************************
---     TABLE for the pm10010ulhCtrllineLoop articles
--- *********************************************************

pm10010ulhCtrllineLoopTable OBJECT-TYPE
	SYNTAX  SEQUENCE OF Pm10010ulhCtrllineLoopEntry
	MAX-ACCESS not-accessible
	STATUS current
	DESCRIPTION
        "
        List of pm10010ulhCtrllineLoop 
        Article
        "
	::= { pm10010ulhCtrlLine 66 }


pm10010ulhCtrllineLoopEntry OBJECT-TYPE
	SYNTAX Pm10010ulhCtrllineLoopEntry
	MAX-ACCESS not-accessible
	STATUS current
	DESCRIPTION
        "
        Row definition for the pm10010ulhCtrllineLoop 
        table
        "
	INDEX   { pm10010ulhCtrllineLoopIndex }
	::= { pm10010ulhCtrllineLoopTable 1 }


Pm10010ulhCtrllineLoopEntry ::=
	SEQUENCE {
	pm10010ulhCtrllineLoopIndex
		INTEGER,
	pm10010ulhCtrllineLoopPortn
		EkiState
	}


pm10010ulhCtrllineLoopIndex OBJECT-TYPE
	SYNTAX  INTEGER(0..128)
	MAX-ACCESS  read-only
	STATUS current
	DESCRIPTION
        "
        Index definition for the pm10010ulhCtrllineLoop 
        table
        "
	::= { pm10010ulhCtrllineLoopEntry 1 }


pm10010ulhCtrllineLoopPortn OBJECT-TYPE
	SYNTAX  EkiState
	MAX-ACCESS read-write
	STATUS current
	DESCRIPTION
        "
        Line Facility Loopback :This OID, 
        when set at '1' puts the module 
        in line loopback mode, looping
         the received 200 Gb/s signal on 
        the transmit 200 Gb/s output. The 
        Upstream part of the module is
         timed on the 200 Gb/s recovered 
        clock in that case.<Help> This
         control enables the Out Loopback 
        on the line port, looping the 200 
        Gb/s input signal on the 200 Gb/s 
        output
        "
	::= { pm10010ulhCtrllineLoopEntry 2 }


--- *********************************************************
---     TABLE for the pm10010ulhCtrlfecDisable articles
--- *********************************************************

pm10010ulhCtrlfecDisableTable OBJECT-TYPE
	SYNTAX  SEQUENCE OF Pm10010ulhCtrlfecDisableEntry
	MAX-ACCESS not-accessible
	STATUS current
	DESCRIPTION
        "
        List of pm10010ulhCtrlfecDisable 
        Article
        "
	::= { pm10010ulhCtrlLine 69 }


pm10010ulhCtrlfecDisableEntry OBJECT-TYPE
	SYNTAX Pm10010ulhCtrlfecDisableEntry
	MAX-ACCESS not-accessible
	STATUS current
	DESCRIPTION
        "
        Row definition for the pm10010ulhCtrlfecDisable 
        table
        "
	INDEX   { pm10010ulhCtrlfecDisableIndex }
	::= { pm10010ulhCtrlfecDisableTable 1 }


Pm10010ulhCtrlfecDisableEntry ::=
	SEQUENCE {
	pm10010ulhCtrlfecDisableIndex
		INTEGER,
	pm10010ulhCtrlfecDisablePortn
		EkiState
	}


pm10010ulhCtrlfecDisableIndex OBJECT-TYPE
	SYNTAX  INTEGER(0..128)
	MAX-ACCESS  read-only
	STATUS current
	DESCRIPTION
        "
        Index definition for the pm10010ulhCtrlfecDisable 
        table
        "
	::= { pm10010ulhCtrlfecDisableEntry 1 }


pm10010ulhCtrlfecDisablePortn OBJECT-TYPE
	SYNTAX  EkiState
	MAX-ACCESS read-write
	STATUS current
	DESCRIPTION
        "
        Forward Error Correction Inhibition 
        :This OID, when set, inhibits the 
        Forward Error Correction feature 
        on the line input  <Help>  This 
        control enables/disables the Forward 
        Error Correction on the line interface
        "
	::= { pm10010ulhCtrlfecDisableEntry 2 }


--- *****************************************************
---     LEAF for the ledTest article
--- *****************************************************
pm10010ulhCtrlledTest OBJECT IDENTIFIER ::= { pm10010ulhCtrlOther 192 }




pm10010ulhCtrlLedOff OBJECT-TYPE
	  SYNTAX EkiOnOff
	  MAX-ACCESS read-write
	  STATUS current
	  DESCRIPTION
        "
        Leds Off :This OID switches off 
        all the Leds as a test feature. 
         <Help>  This control initiates 
        a test leds turning all the LEDs 
        to OFF
        "
	  ::= { pm10010ulhCtrlledTest 3 }



pm10010ulhCtrlRedLed OBJECT-TYPE
	  SYNTAX EkiOnOff
	  MAX-ACCESS read-write
	  STATUS current
	  DESCRIPTION
        "
        Red Leds Test :This OID switches 
        on all the red Leds as a test feature. 
         <Help>  This control initiates 
        a test leds turning all the LEDs 
        to red
        "
	  ::= { pm10010ulhCtrlledTest 2 }



pm10010ulhCtrlGreenLed OBJECT-TYPE
	  SYNTAX EkiOnOff
	  MAX-ACCESS read-write
	  STATUS current
	  DESCRIPTION
        "
        Green Leds Test :This OID switches 
        on all the green Leds as a test 
        feature.  <Help>  This control
         initiates a test leds turning
         all the LEDs to green
        "
	  ::= { pm10010ulhCtrlledTest 1 }



--- *****************************************************
---     LEAF for the initSwitchMarvell article
--- *****************************************************
pm10010ulhCtrlinitSwitchMarvell OBJECT IDENTIFIER ::= { pm10010ulhCtrlOther 201 }




pm10010ulhCtrlInitSwitchMarvell OBJECT-TYPE
	  SYNTAX EkiOnOff
	  MAX-ACCESS read-write
	  STATUS current
	  DESCRIPTION
        "
        Switch Initialization :This OID 
        operates an initialization of the 
        switch managed through the module 
         <Help>  This control activates 
        an initialization of the switch 
        managed through the module
        "
	  ::= { pm10010ulhCtrlinitSwitchMarvell 1 }



--- *********************************************************
---     TABLE for the pm10010ulhCtrlmsaLineLoop articles
--- *********************************************************

pm10010ulhCtrlmsaLineLoopTable OBJECT-TYPE
	SYNTAX  SEQUENCE OF Pm10010ulhCtrlmsaLineLoopEntry
	MAX-ACCESS not-accessible
	STATUS current
	DESCRIPTION
        "
        List of pm10010ulhCtrlmsaLineLoop 
        Article
        "
	::= { pm10010ulhCtrlLine 209 }


pm10010ulhCtrlmsaLineLoopEntry OBJECT-TYPE
	SYNTAX Pm10010ulhCtrlmsaLineLoopEntry
	MAX-ACCESS not-accessible
	STATUS current
	DESCRIPTION
        "
        Row definition for the pm10010ulhCtrlmsaLineLoop 
        table
        "
	INDEX   { pm10010ulhCtrlmsaLineLoopIndex }
	::= { pm10010ulhCtrlmsaLineLoopTable 1 }


Pm10010ulhCtrlmsaLineLoopEntry ::=
	SEQUENCE {
	pm10010ulhCtrlmsaLineLoopIndex
		INTEGER,
	pm10010ulhCtrlmsaLineLoopPortn
		EkiState
	}


pm10010ulhCtrlmsaLineLoopIndex OBJECT-TYPE
	SYNTAX  INTEGER(0..128)
	MAX-ACCESS  read-only
	STATUS current
	DESCRIPTION
        "
        Index definition for the pm10010ulhCtrlmsaLineLoop 
        table
        "
	::= { pm10010ulhCtrlmsaLineLoopEntry 1 }


pm10010ulhCtrlmsaLineLoopPortn OBJECT-TYPE
	SYNTAX  EkiState
	MAX-ACCESS read-write
	STATUS current
	DESCRIPTION
        "
        MSA Line Loop :This OID operates 
        a line loopback on the MSA Line 
         <Help>  This control defines the 
        line loop back of the line transceiver
        "
	::= { pm10010ulhCtrlmsaLineLoopEntry 2 }


--- *********************************************************
---     TABLE for the pm10010ulhCtrlmsaTxReset articles
--- *********************************************************

pm10010ulhCtrlmsaTxResetTable OBJECT-TYPE
	SYNTAX  SEQUENCE OF Pm10010ulhCtrlmsaTxResetEntry
	MAX-ACCESS not-accessible
	STATUS current
	DESCRIPTION
        "
        List of pm10010ulhCtrlmsaTxReset 
        Article
        "
	::= { pm10010ulhCtrlLine 210 }


pm10010ulhCtrlmsaTxResetEntry OBJECT-TYPE
	SYNTAX Pm10010ulhCtrlmsaTxResetEntry
	MAX-ACCESS not-accessible
	STATUS current
	DESCRIPTION
        "
        Row definition for the pm10010ulhCtrlmsaTxReset 
        table
        "
	INDEX   { pm10010ulhCtrlmsaTxResetIndex }
	::= { pm10010ulhCtrlmsaTxResetTable 1 }


Pm10010ulhCtrlmsaTxResetEntry ::=
	SEQUENCE {
	pm10010ulhCtrlmsaTxResetIndex
		INTEGER,
	pm10010ulhCtrlmsaTxResetPortn
		EkiState
	}


pm10010ulhCtrlmsaTxResetIndex OBJECT-TYPE
	SYNTAX  INTEGER(0..128)
	MAX-ACCESS  read-only
	STATUS current
	DESCRIPTION
        "
        Index definition for the pm10010ulhCtrlmsaTxReset 
        table
        "
	::= { pm10010ulhCtrlmsaTxResetEntry 1 }


pm10010ulhCtrlmsaTxResetPortn OBJECT-TYPE
	SYNTAX  EkiState
	MAX-ACCESS read-write
	STATUS current
	DESCRIPTION
        "
        Line MSA TX Reset :This OID resets 
        the TX portion of the MSA line
         module  <Help > This control 
         initiates a reset of the transmitting 
        side
        "
	::= { pm10010ulhCtrlmsaTxResetEntry 2 }


--- *********************************************************
---     TABLE for the pm10010ulhCtrlmsaRxReset articles
--- *********************************************************

pm10010ulhCtrlmsaRxResetTable OBJECT-TYPE
	SYNTAX  SEQUENCE OF Pm10010ulhCtrlmsaRxResetEntry
	MAX-ACCESS not-accessible
	STATUS current
	DESCRIPTION
        "
        List of pm10010ulhCtrlmsaRxReset 
        Article
        "
	::= { pm10010ulhCtrlLine 211 }


pm10010ulhCtrlmsaRxResetEntry OBJECT-TYPE
	SYNTAX Pm10010ulhCtrlmsaRxResetEntry
	MAX-ACCESS not-accessible
	STATUS current
	DESCRIPTION
        "
        Row definition for the pm10010ulhCtrlmsaRxReset 
        table
        "
	INDEX   { pm10010ulhCtrlmsaRxResetIndex }
	::= { pm10010ulhCtrlmsaRxResetTable 1 }


Pm10010ulhCtrlmsaRxResetEntry ::=
	SEQUENCE {
	pm10010ulhCtrlmsaRxResetIndex
		INTEGER,
	pm10010ulhCtrlmsaRxResetPortn
		EkiState
	}


pm10010ulhCtrlmsaRxResetIndex OBJECT-TYPE
	SYNTAX  INTEGER(0..128)
	MAX-ACCESS  read-only
	STATUS current
	DESCRIPTION
        "
        Index definition for the pm10010ulhCtrlmsaRxReset 
        table
        "
	::= { pm10010ulhCtrlmsaRxResetEntry 1 }


pm10010ulhCtrlmsaRxResetPortn OBJECT-TYPE
	SYNTAX  EkiState
	MAX-ACCESS read-write
	STATUS current
	DESCRIPTION
        "
        Line MSA RX Reset :This OID resets 
        the RX portion of the MSA line
         module  <Help > This control 
         initiates a reset of the receiving 
        side
        "
	::= { pm10010ulhCtrlmsaRxResetEntry 2 }


--- *********************************************************
---     TABLE for the pm10010ulhCtrlmsaShutdown articles
--- *********************************************************

pm10010ulhCtrlmsaShutdownTable OBJECT-TYPE
	SYNTAX  SEQUENCE OF Pm10010ulhCtrlmsaShutdownEntry
	MAX-ACCESS not-accessible
	STATUS current
	DESCRIPTION
        "
        List of pm10010ulhCtrlmsaShutdown 
        Article
        "
	::= { pm10010ulhCtrlLine 212 }


pm10010ulhCtrlmsaShutdownEntry OBJECT-TYPE
	SYNTAX Pm10010ulhCtrlmsaShutdownEntry
	MAX-ACCESS not-accessible
	STATUS current
	DESCRIPTION
        "
        Row definition for the pm10010ulhCtrlmsaShutdown 
        table
        "
	INDEX   { pm10010ulhCtrlmsaShutdownIndex }
	::= { pm10010ulhCtrlmsaShutdownTable 1 }


Pm10010ulhCtrlmsaShutdownEntry ::=
	SEQUENCE {
	pm10010ulhCtrlmsaShutdownIndex
		INTEGER,
	pm10010ulhCtrlmsaShutdownPortn
		EkiState
	}


pm10010ulhCtrlmsaShutdownIndex OBJECT-TYPE
	SYNTAX  INTEGER(0..128)
	MAX-ACCESS  read-only
	STATUS current
	DESCRIPTION
        "
        Index definition for the pm10010ulhCtrlmsaShutdown 
        table
        "
	::= { pm10010ulhCtrlmsaShutdownEntry 1 }


pm10010ulhCtrlmsaShutdownPortn OBJECT-TYPE
	SYNTAX  EkiState
	MAX-ACCESS read-write
	STATUS current
	DESCRIPTION
        "
        Line MSA Shutdown :This OID enters 
        a process to shutdown the MSA line 
        module  <Help > This control  initiates 
        a shutdown of the module
        "
	::= { pm10010ulhCtrlmsaShutdownEntry 2 }


--- *****************************************************
---     LEAF for the resetCount article
--- *****************************************************
pm10010ulhCtrlresetCount OBJECT IDENTIFIER ::= { pm10010ulhCtrlOther 259 }




pm10010ulhCtrlResetcount OBJECT-TYPE
	  SYNTAX EkiOnOff
	  MAX-ACCESS read-write
	  STATUS current
	  DESCRIPTION
        "
        Module Count Global Reset :This 
        OID resets all the errors counters 
        on the module  <Help > This control 
         initiates a reset of the errors 
        counters on the module
        "
	  ::= { pm10010ulhCtrlresetCount 1 }



--- *****************************************************
---     LEAF for the resetRmon article
--- *****************************************************
pm10010ulhCtrlresetRmon OBJECT IDENTIFIER ::= { pm10010ulhCtrlOther 260 }




pm10010ulhCtrlResetrmon OBJECT-TYPE
	  SYNTAX EkiOnOff
	  MAX-ACCESS read-write
	  STATUS current
	  DESCRIPTION
        "
        Module Rmon Global Reset :This 
        OID resets all the Rmon counters 
        on the module  <Help > This control 
         initiates a reset of the Rmon
         counters on the module
        "
	  ::= { pm10010ulhCtrlresetRmon 1 }



--- *****************************************************
---     LEAF for the resetMeasurements article
--- *****************************************************
pm10010ulhCtrlresetMeasurements OBJECT IDENTIFIER ::= { pm10010ulhCtrlOther 261 }




pm10010ulhCtrlResetmeasurements OBJECT-TYPE
	  SYNTAX EkiOnOff
	  MAX-ACCESS read-write
	  STATUS current
	  DESCRIPTION
        "
        Management Meas Global Reset :This 
        OID resets some measurements on 
        the management  <Help > This control 
         initiates a reset of some measurements 
        on the management
        "
	  ::= { pm10010ulhCtrlresetMeasurements 1 }



--- *********************************************************
---     TABLE for the pm10010ulhCtrlclientResetAllCount articles
--- *********************************************************

pm10010ulhCtrlclientResetAllCountTable OBJECT-TYPE
	SYNTAX  SEQUENCE OF Pm10010ulhCtrlclientResetAllCountEntry
	MAX-ACCESS not-accessible
	STATUS current
	DESCRIPTION
        "
        List of pm10010ulhCtrlclientResetAllCount 
        Article
        "
	::= { pm10010ulhCtrlClient 262 }


pm10010ulhCtrlclientResetAllCountEntry OBJECT-TYPE
	SYNTAX Pm10010ulhCtrlclientResetAllCountEntry
	MAX-ACCESS not-accessible
	STATUS current
	DESCRIPTION
        "
        Row definition for the pm10010ulhCtrlclientResetAllCount 
        table
        "
	INDEX   { pm10010ulhCtrlclientResetAllCountIndex }
	::= { pm10010ulhCtrlclientResetAllCountTable 1 }


Pm10010ulhCtrlclientResetAllCountEntry ::=
	SEQUENCE {
	pm10010ulhCtrlclientResetAllCountIndex
		INTEGER,
	pm10010ulhCtrlclientResetAllCountsPortn
		EkiState
	}


pm10010ulhCtrlclientResetAllCountIndex OBJECT-TYPE
	SYNTAX  INTEGER(0..128)
	MAX-ACCESS  read-only
	STATUS current
	DESCRIPTION
        "
        Index definition for the pm10010ulhCtrlclientResetAllCount 
        table
        "
	::= { pm10010ulhCtrlclientResetAllCountEntry 1 }


pm10010ulhCtrlclientResetAllCountsPortn OBJECT-TYPE
	SYNTAX  EkiState
	MAX-ACCESS read-write
	STATUS current
	DESCRIPTION
        "
        Client Counters Reset :This OID 
        resets every counter on the client 
        port  <Help>   This control operates 
        a reset on the statistics current 
        ,previous and history client port 
        counters  
        "
	::= { pm10010ulhCtrlclientResetAllCountEntry 2 }


--- *********************************************************
---     TABLE for the pm10010ulhCtrllineResetAllCount articles
--- *********************************************************

pm10010ulhCtrllineResetAllCountTable OBJECT-TYPE
	SYNTAX  SEQUENCE OF Pm10010ulhCtrllineResetAllCountEntry
	MAX-ACCESS not-accessible
	STATUS current
	DESCRIPTION
        "
        List of pm10010ulhCtrllineResetAllCount 
        Article
        "
	::= { pm10010ulhCtrlLine 263 }


pm10010ulhCtrllineResetAllCountEntry OBJECT-TYPE
	SYNTAX Pm10010ulhCtrllineResetAllCountEntry
	MAX-ACCESS not-accessible
	STATUS current
	DESCRIPTION
        "
        Row definition for the pm10010ulhCtrllineResetAllCount 
        table
        "
	INDEX   { pm10010ulhCtrllineResetAllCountIndex }
	::= { pm10010ulhCtrllineResetAllCountTable 1 }


Pm10010ulhCtrllineResetAllCountEntry ::=
	SEQUENCE {
	pm10010ulhCtrllineResetAllCountIndex
		INTEGER,
	pm10010ulhCtrllineResetAllCountsPortn
		EkiState
	}


pm10010ulhCtrllineResetAllCountIndex OBJECT-TYPE
	SYNTAX  INTEGER(0..128)
	MAX-ACCESS  read-only
	STATUS current
	DESCRIPTION
        "
        Index definition for the pm10010ulhCtrllineResetAllCount 
        table
        "
	::= { pm10010ulhCtrllineResetAllCountEntry 1 }


pm10010ulhCtrllineResetAllCountsPortn OBJECT-TYPE
	SYNTAX  EkiState
	MAX-ACCESS read-write
	STATUS current
	DESCRIPTION
        "
        Line Counters Reset :This OID
         resets every counter on the line 
        port  <Help>   This control operates 
        a reset on the statistics current 
        ,previous and history line port 
        counters  
        "
	::= { pm10010ulhCtrllineResetAllCountEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm10010ulhCntclientInputErrorCounter articles
--- *********************************************************

pm10010ulhCntclientInputErrorCounterTable OBJECT-TYPE
	SYNTAX  SEQUENCE OF Pm10010ulhCntclientInputErrorCounterEntry
	MAX-ACCESS not-accessible
	STATUS current
	DESCRIPTION
        "
        List of pm10010ulhCntclientInputErrorCounter 
        Article
        "
	::= { pm10010ulhCntClient 112 }


pm10010ulhCntclientInputErrorCounterEntry OBJECT-TYPE
	SYNTAX Pm10010ulhCntclientInputErrorCounterEntry
	MAX-ACCESS not-accessible
	STATUS current
	DESCRIPTION
        "
        Row definition for the pm10010ulhCntclientInputErrorCounter 
        table
        "
	INDEX   { pm10010ulhCntclientInputErrorCounterIndex }
	::= { pm10010ulhCntclientInputErrorCounterTable 1 }


Pm10010ulhCntclientInputErrorCounterEntry ::=
	SEQUENCE {
	pm10010ulhCntclientInputErrorCounterIndex
		INTEGER,
	pm10010ulhCntclientInputErrorCounterValuePortn
		Counter32,
	pm10010ulhCntclientInputErrorCounterErrorPortn
		EkiOnOff,
	pm10010ulhCntclientInputErrorCounterOverloadPortn
		EkiOnOff
	}


pm10010ulhCntclientInputErrorCounterIndex OBJECT-TYPE
	SYNTAX  INTEGER(0..128)
	MAX-ACCESS  read-only
	STATUS current
	DESCRIPTION
        "
        Index definition for the pm10010ulhCntclientInputErrorCounter 
        table
        "
	::= { pm10010ulhCntclientInputErrorCounterEntry 1 }


pm10010ulhCntclientInputErrorCounterValuePortn OBJECT-TYPE
	SYNTAX  Counter32
	MAX-ACCESS read-only
	STATUS current
	DESCRIPTION
        "
        Client Input Errors :This counter 
        is increased each time a 10b/8b 
        running disparity error is detected 
        on the Client input stream  <Help> 
         This counter gives the number
         of 10b/8b running disparity errors 
        on the client port
        "
	::= { pm10010ulhCntclientInputErrorCounterEntry 2 }


pm10010ulhCntclientInputErrorCounterErrorPortn OBJECT-TYPE
	SYNTAX  EkiOnOff
	MAX-ACCESS read-only
	STATUS current
	DESCRIPTION
        "
        Client Counter Error :This OID 
        when set indicates the client error 
        counter value is invalid on Port
        "
	::= { pm10010ulhCntclientInputErrorCounterEntry 3 }


pm10010ulhCntclientInputErrorCounterOverloadPortn OBJECT-TYPE
	SYNTAX  EkiOnOff
	MAX-ACCESS read-only
	STATUS current
	DESCRIPTION
        "
        Client Counter Overload :This
         OID when set indicates a client 
        input error counter overload on 
        Port
        "
	::= { pm10010ulhCntclientInputErrorCounterEntry 4 }


--- *********************************************************
---     TABLE for the pm10010ulhCntclientCbipCounter articles
--- *********************************************************

pm10010ulhCntclientCbipCounterTable OBJECT-TYPE
	SYNTAX  SEQUENCE OF Pm10010ulhCntclientCbipCounterEntry
	MAX-ACCESS not-accessible
	STATUS current
	DESCRIPTION
        "
        List of pm10010ulhCntclientCbipCounter 
        Article
        "
	::= { pm10010ulhCntClient 144 }


pm10010ulhCntclientCbipCounterEntry OBJECT-TYPE
	SYNTAX Pm10010ulhCntclientCbipCounterEntry
	MAX-ACCESS not-accessible
	STATUS current
	DESCRIPTION
        "
        Row definition for the pm10010ulhCntclientCbipCounter 
        table
        "
	INDEX   { pm10010ulhCntclientCbipCounterIndex }
	::= { pm10010ulhCntclientCbipCounterTable 1 }


Pm10010ulhCntclientCbipCounterEntry ::=
	SEQUENCE {
	pm10010ulhCntclientCbipCounterIndex
		INTEGER,
	pm10010ulhCntclientCbipCounterValuePortn
		Counter32,
	pm10010ulhCntclientCbipCounterErrorPortn
		EkiOnOff,
	pm10010ulhCntclientCbipCounterOverloadPortn
		EkiOnOff
	}


pm10010ulhCntclientCbipCounterIndex OBJECT-TYPE
	SYNTAX  INTEGER(0..128)
	MAX-ACCESS  read-only
	STATUS current
	DESCRIPTION
        "
        Index definition for the pm10010ulhCntclientCbipCounter 
        table
        "
	::= { pm10010ulhCntclientCbipCounterEntry 1 }


pm10010ulhCntclientCbipCounterValuePortn OBJECT-TYPE
	SYNTAX  Counter32
	MAX-ACCESS read-only
	STATUS current
	DESCRIPTION
        "
        Client Output Errors :This counter 
        is incremented each time a CBIP 
        parity error is detected on the 
        Client output stream  <Help>  This 
        counter gives the number of CBIP 
        errors on the client port
        "
	::= { pm10010ulhCntclientCbipCounterEntry 2 }


pm10010ulhCntclientCbipCounterErrorPortn OBJECT-TYPE
	SYNTAX  EkiOnOff
	MAX-ACCESS read-only
	STATUS current
	DESCRIPTION
        "
        Client Counter Error :This OID 
        when set indicates the CBIP error 
        counter value is invalid on Port
        "
	::= { pm10010ulhCntclientCbipCounterEntry 3 }


pm10010ulhCntclientCbipCounterOverloadPortn OBJECT-TYPE
	SYNTAX  EkiOnOff
	MAX-ACCESS read-only
	STATUS current
	DESCRIPTION
        "
        Client CBIP Counter Overload :This 
        OID when set indicates a CBIP error 
        counter overload on Port
        "
	::= { pm10010ulhCntclientCbipCounterEntry 4 }


--- *********************************************************
---     TABLE for the pm10010ulhCntlocalLineSmBip8ErrorCounter articles
--- *********************************************************

pm10010ulhCntlocalLineSmBip8ErrorCounterTable OBJECT-TYPE
	SYNTAX  SEQUENCE OF Pm10010ulhCntlocalLineSmBip8ErrorCounterEntry
	MAX-ACCESS not-accessible
	STATUS current
	DESCRIPTION
        "
        List of pm10010ulhCntlocalLineSmBip8ErrorCounter 
        Article
        "
	::= { pm10010ulhCntLine 192 }


pm10010ulhCntlocalLineSmBip8ErrorCounterEntry OBJECT-TYPE
	SYNTAX Pm10010ulhCntlocalLineSmBip8ErrorCounterEntry
	MAX-ACCESS not-accessible
	STATUS current
	DESCRIPTION
        "
        Row definition for the pm10010ulhCntlocalLineSmBip8ErrorCounter 
        table
        "
	INDEX   { pm10010ulhCntlocalLineSmBip8ErrorCounterIndex }
	::= { pm10010ulhCntlocalLineSmBip8ErrorCounterTable 1 }


Pm10010ulhCntlocalLineSmBip8ErrorCounterEntry ::=
	SEQUENCE {
	pm10010ulhCntlocalLineSmBip8ErrorCounterIndex
		INTEGER,
	pm10010ulhCntlocalLineSmBip8ErrorCounterValuePortn
		Counter64,
	pm10010ulhCntlocalLineSmBip8ErrorCounterErrorPortn
		EkiOnOff,
	pm10010ulhCntlocalLineSmBip8ErrorCounterOverloadPortn
		EkiOnOff
	}


pm10010ulhCntlocalLineSmBip8ErrorCounterIndex OBJECT-TYPE
	SYNTAX  INTEGER(0..128)
	MAX-ACCESS  read-only
	STATUS current
	DESCRIPTION
        "
        Index definition for the pm10010ulhCntlocalLineSmBip8ErrorCounter 
        table
        "
	::= { pm10010ulhCntlocalLineSmBip8ErrorCounterEntry 1 }


pm10010ulhCntlocalLineSmBip8ErrorCounterValuePortn OBJECT-TYPE
	SYNTAX  Counter64
	MAX-ACCESS read-only
	STATUS current
	DESCRIPTION
        "
        Uncorrected SD FEC Errors :This 
        OID gives the current Bit Error 
        Rate (residual SM-BIP8 error) after 
        FEC   <Help> This counter gives 
        the current Bit Error Rate (residual 
        SM-BIP8 error) after FEC
        "
	::= { pm10010ulhCntlocalLineSmBip8ErrorCounterEntry 2 }


pm10010ulhCntlocalLineSmBip8ErrorCounterErrorPortn OBJECT-TYPE
	SYNTAX  EkiOnOff
	MAX-ACCESS read-only
	STATUS current
	DESCRIPTION
        "
        Line Counter Error :This OID when 
        set indicates the B1 error counter 
        value is invalid on Port
        "
	::= { pm10010ulhCntlocalLineSmBip8ErrorCounterEntry 3 }


pm10010ulhCntlocalLineSmBip8ErrorCounterOverloadPortn OBJECT-TYPE
	SYNTAX  EkiOnOff
	MAX-ACCESS read-only
	STATUS current
	DESCRIPTION
        "
        Line Counter Overload :This OID 
        when set indicates a B1 error counter 
        overload on Port
        "
	::= { pm10010ulhCntlocalLineSmBip8ErrorCounterEntry 4 }


--- *********************************************************
---     TABLE for the pm10010ulhCntlocalLineFecCorrectedErrorsCounter articles
--- *********************************************************

pm10010ulhCntlocalLineFecCorrectedErrorsCounterTable OBJECT-TYPE
	SYNTAX  SEQUENCE OF Pm10010ulhCntlocalLineFecCorrectedErrorsCounterEntry
	MAX-ACCESS not-accessible
	STATUS current
	DESCRIPTION
        "
        List of pm10010ulhCntlocalLineFecCorrectedErrorsCounter 
        Article
        "
	::= { pm10010ulhCntLine 193 }


pm10010ulhCntlocalLineFecCorrectedErrorsCounterEntry OBJECT-TYPE
	SYNTAX Pm10010ulhCntlocalLineFecCorrectedErrorsCounterEntry
	MAX-ACCESS not-accessible
	STATUS current
	DESCRIPTION
        "
        Row definition for the pm10010ulhCntlocalLineFecCorrectedErrorsCounter 
        table
        "
	INDEX   { pm10010ulhCntlocalLineFecCorrectedErrorsCounterIndex }
	::= { pm10010ulhCntlocalLineFecCorrectedErrorsCounterTable 1 }


Pm10010ulhCntlocalLineFecCorrectedErrorsCounterEntry ::=
	SEQUENCE {
	pm10010ulhCntlocalLineFecCorrectedErrorsCounterIndex
		INTEGER,
	pm10010ulhCntlocalLineFecCorrectedErrorsCounterValuePortn
		Counter64,
	pm10010ulhCntlocalLineFecCorrectedErrorsCounterErrorPortn
		EkiOnOff,
	pm10010ulhCntlocalLineFecCorrectedErrorsCounterOverloadPortn
		EkiOnOff
	}


pm10010ulhCntlocalLineFecCorrectedErrorsCounterIndex OBJECT-TYPE
	SYNTAX  INTEGER(0..128)
	MAX-ACCESS  read-only
	STATUS current
	DESCRIPTION
        "
        Index definition for the pm10010ulhCntlocalLineFecCorrectedErrorsCounter 
        table
        "
	::= { pm10010ulhCntlocalLineFecCorrectedErrorsCounterEntry 1 }


pm10010ulhCntlocalLineFecCorrectedErrorsCounterValuePortn OBJECT-TYPE
	SYNTAX  Counter64
	MAX-ACCESS read-only
	STATUS current
	DESCRIPTION
        "
        Line Input HD FEC Corrected Errors 
        :This OID gives the current Bit 
        Error Rate before the Hard Decision 
        FEC  <Help> This counter gives
         the current Bit Error Rate before 
        the Hard Decision FEC
        "
	::= { pm10010ulhCntlocalLineFecCorrectedErrorsCounterEntry 2 }


pm10010ulhCntlocalLineFecCorrectedErrorsCounterErrorPortn OBJECT-TYPE
	SYNTAX  EkiOnOff
	MAX-ACCESS read-only
	STATUS current
	DESCRIPTION
        "
        FEC Counter Error :This bit when 
        set indicates the FEC corrected 
        errors counter value is invalid 
        on Line
        "
	::= { pm10010ulhCntlocalLineFecCorrectedErrorsCounterEntry 3 }


pm10010ulhCntlocalLineFecCorrectedErrorsCounterOverloadPortn OBJECT-TYPE
	SYNTAX  EkiOnOff
	MAX-ACCESS read-only
	STATUS current
	DESCRIPTION
        "
        FEC Counter Overload :This bit 
        when set indicates a FEC corrected 
        errors counter overload on Line
        "
	::= { pm10010ulhCntlocalLineFecCorrectedErrorsCounterEntry 4 }


--- *********************************************************
---     TABLE for the pm10010ulhCntremoteLineSmBip8ErrorCounter articles
--- *********************************************************

pm10010ulhCntremoteLineSmBip8ErrorCounterTable OBJECT-TYPE
	SYNTAX  SEQUENCE OF Pm10010ulhCntremoteLineSmBip8ErrorCounterEntry
	MAX-ACCESS not-accessible
	STATUS current
	DESCRIPTION
        "
        List of pm10010ulhCntremoteLineSmBip8ErrorCounter 
        Article
        "
	::= { pm10010ulhCntLine 194 }


pm10010ulhCntremoteLineSmBip8ErrorCounterEntry OBJECT-TYPE
	SYNTAX Pm10010ulhCntremoteLineSmBip8ErrorCounterEntry
	MAX-ACCESS not-accessible
	STATUS current
	DESCRIPTION
        "
        Row definition for the pm10010ulhCntremoteLineSmBip8ErrorCounter 
        table
        "
	INDEX   { pm10010ulhCntremoteLineSmBip8ErrorCounterIndex }
	::= { pm10010ulhCntremoteLineSmBip8ErrorCounterTable 1 }


Pm10010ulhCntremoteLineSmBip8ErrorCounterEntry ::=
	SEQUENCE {
	pm10010ulhCntremoteLineSmBip8ErrorCounterIndex
		INTEGER,
	pm10010ulhCntremoteLineSmBip8ErrorCounterValuePortn
		Counter64,
	pm10010ulhCntremoteLineSmBip8ErrorCounterErrorPortn
		EkiOnOff,
	pm10010ulhCntremoteLineSmBip8ErrorCounterOverloadPortn
		EkiOnOff
	}


pm10010ulhCntremoteLineSmBip8ErrorCounterIndex OBJECT-TYPE
	SYNTAX  INTEGER(0..128)
	MAX-ACCESS  read-only
	STATUS current
	DESCRIPTION
        "
        Index definition for the pm10010ulhCntremoteLineSmBip8ErrorCounter 
        table
        "
	::= { pm10010ulhCntremoteLineSmBip8ErrorCounterEntry 1 }


pm10010ulhCntremoteLineSmBip8ErrorCounterValuePortn OBJECT-TYPE
	SYNTAX  Counter64
	MAX-ACCESS read-only
	STATUS current
	DESCRIPTION
        "
        Remote SM BIP8 :This OID gives 
        the current Bit Error Rate (residual 
        SM-BIP8 error) after FEC on the 
        remote side  <Help> This counter 
        gives the current Bit Error Rate 
        (residual SM-BIP8 error) after
         FEC on the remote side
        "
	::= { pm10010ulhCntremoteLineSmBip8ErrorCounterEntry 2 }


pm10010ulhCntremoteLineSmBip8ErrorCounterErrorPortn OBJECT-TYPE
	SYNTAX  EkiOnOff
	MAX-ACCESS read-only
	STATUS current
	DESCRIPTION
        "
        Remote Counter Error :
        "
	::= { pm10010ulhCntremoteLineSmBip8ErrorCounterEntry 3 }


pm10010ulhCntremoteLineSmBip8ErrorCounterOverloadPortn OBJECT-TYPE
	SYNTAX  EkiOnOff
	MAX-ACCESS read-only
	STATUS current
	DESCRIPTION
        "
        Remote Counter Overload :
        "
	::= { pm10010ulhCntremoteLineSmBip8ErrorCounterEntry 4 }


--- *********************************************************
---     TABLE for the pm10010ulhCntlineDfrmTimCnt articles
--- *********************************************************

pm10010ulhCntlineDfrmTimCntTable OBJECT-TYPE
	SYNTAX  SEQUENCE OF Pm10010ulhCntlineDfrmTimCntEntry
	MAX-ACCESS not-accessible
	STATUS current
	DESCRIPTION
        "
        List of pm10010ulhCntlineDfrmTimCnt 
        Article
        "
	::= { pm10010ulhCntLine 195 }


pm10010ulhCntlineDfrmTimCntEntry OBJECT-TYPE
	SYNTAX Pm10010ulhCntlineDfrmTimCntEntry
	MAX-ACCESS not-accessible
	STATUS current
	DESCRIPTION
        "
        Row definition for the pm10010ulhCntlineDfrmTimCnt 
        table
        "
	INDEX   { pm10010ulhCntlineDfrmTimCntIndex }
	::= { pm10010ulhCntlineDfrmTimCntTable 1 }


Pm10010ulhCntlineDfrmTimCntEntry ::=
	SEQUENCE {
	pm10010ulhCntlineDfrmTimCntIndex
		INTEGER,
	pm10010ulhCntlineDfrmTimCntValuePortn
		Counter64,
	pm10010ulhCntlineDfrmTimCntErrorPortn
		EkiOnOff,
	pm10010ulhCntlineDfrmTimCntOverloadPortn
		EkiOnOff
	}


pm10010ulhCntlineDfrmTimCntIndex OBJECT-TYPE
	SYNTAX  INTEGER(0..128)
	MAX-ACCESS  read-only
	STATUS current
	DESCRIPTION
        "
        Index definition for the pm10010ulhCntlineDfrmTimCnt 
        table
        "
	::= { pm10010ulhCntlineDfrmTimCntEntry 1 }


pm10010ulhCntlineDfrmTimCntValuePortn OBJECT-TYPE
	SYNTAX  Counter64
	MAX-ACCESS read-only
	STATUS current
	DESCRIPTION
        "
        Line Timer Counter :
        "
	::= { pm10010ulhCntlineDfrmTimCntEntry 2 }


pm10010ulhCntlineDfrmTimCntErrorPortn OBJECT-TYPE
	SYNTAX  EkiOnOff
	MAX-ACCESS read-only
	STATUS current
	DESCRIPTION
        "
        Line Counter Error :This OID when 
        set indicates the deframer timer 
        counter value is invalid on Port
        "
	::= { pm10010ulhCntlineDfrmTimCntEntry 3 }


pm10010ulhCntlineDfrmTimCntOverloadPortn OBJECT-TYPE
	SYNTAX  EkiOnOff
	MAX-ACCESS read-only
	STATUS current
	DESCRIPTION
        "
        Line Counter Overload :This OID 
        when set indicates a deframer timer 
        counter overload on Port
        "
	::= { pm10010ulhCntlineDfrmTimCntEntry 4 }


--- *********************************************************
---     TABLE for the pm10010ulhCntlocalLineTrscvPreSdFecErrorCounter articles
--- *********************************************************

pm10010ulhCntlocalLineTrscvPreSdFecErrorCounterTable OBJECT-TYPE
	SYNTAX  SEQUENCE OF Pm10010ulhCntlocalLineTrscvPreSdFecErrorCounterEntry
	MAX-ACCESS not-accessible
	STATUS current
	DESCRIPTION
        "
        List of pm10010ulhCntlocalLineTrscvPreSdFecErrorCounter 
        Article
        "
	::= { pm10010ulhCntLine 196 }


pm10010ulhCntlocalLineTrscvPreSdFecErrorCounterEntry OBJECT-TYPE
	SYNTAX Pm10010ulhCntlocalLineTrscvPreSdFecErrorCounterEntry
	MAX-ACCESS not-accessible
	STATUS current
	DESCRIPTION
        "
        Row definition for the pm10010ulhCntlocalLineTrscvPreSdFecErrorCounter 
        table
        "
	INDEX   { pm10010ulhCntlocalLineTrscvPreSdFecErrorCounterIndex }
	::= { pm10010ulhCntlocalLineTrscvPreSdFecErrorCounterTable 1 }


Pm10010ulhCntlocalLineTrscvPreSdFecErrorCounterEntry ::=
	SEQUENCE {
	pm10010ulhCntlocalLineTrscvPreSdFecErrorCounterIndex
		INTEGER,
	pm10010ulhCntlocalLineTrscvPreSdFecErrorCounterValuePortn
		Counter64,
	pm10010ulhCntlocalLineTrscvPreSdFecErrorCounterErrorPortn
		EkiOnOff,
	pm10010ulhCntlocalLineTrscvPreSdFecErrorCounterOverloadPortn
		EkiOnOff
	}


pm10010ulhCntlocalLineTrscvPreSdFecErrorCounterIndex OBJECT-TYPE
	SYNTAX  INTEGER(0..128)
	MAX-ACCESS  read-only
	STATUS current
	DESCRIPTION
        "
        Index definition for the pm10010ulhCntlocalLineTrscvPreSdFecErrorCounter 
        table
        "
	::= { pm10010ulhCntlocalLineTrscvPreSdFecErrorCounterEntry 1 }


pm10010ulhCntlocalLineTrscvPreSdFecErrorCounterValuePortn OBJECT-TYPE
	SYNTAX  Counter64
	MAX-ACCESS read-only
	STATUS current
	DESCRIPTION
        "
        Pre-SD FEC Errors :This OID gives 
        the current Bit Error Rate before 
        the Soft Decision FEC  <Help> This 
        counter gives the current Bit Error 
        Rate before the Soft Decision FEC
        "
	::= { pm10010ulhCntlocalLineTrscvPreSdFecErrorCounterEntry 2 }


pm10010ulhCntlocalLineTrscvPreSdFecErrorCounterErrorPortn OBJECT-TYPE
	SYNTAX  EkiOnOff
	MAX-ACCESS read-only
	STATUS current
	DESCRIPTION
        "
        Line Counter Error :This OID when 
        set indicates the deframer timer 
        counter value is invalid on Port
        "
	::= { pm10010ulhCntlocalLineTrscvPreSdFecErrorCounterEntry 3 }


pm10010ulhCntlocalLineTrscvPreSdFecErrorCounterOverloadPortn OBJECT-TYPE
	SYNTAX  EkiOnOff
	MAX-ACCESS read-only
	STATUS current
	DESCRIPTION
        "
        Line Counter Overload :This OID 
        when set indicates a deframer timer 
        counter overload on Port
        "
	::= { pm10010ulhCntlocalLineTrscvPreSdFecErrorCounterEntry 4 }


--- *********************************************************
---     TABLE for the pm10010ulhCntlocalLineTrscvUncorrectedSdFecErrorCounter articles
--- *********************************************************

pm10010ulhCntlocalLineTrscvUncorrectedSdFecErrorCounterTable OBJECT-TYPE
	SYNTAX  SEQUENCE OF Pm10010ulhCntlocalLineTrscvUncorrectedSdFecErrorCounterEntry
	MAX-ACCESS not-accessible
	STATUS current
	DESCRIPTION
        "
        List of pm10010ulhCntlocalLineTrscvUncorrectedSdFecErrorCounter 
        Article
        "
	::= { pm10010ulhCntLine 197 }


pm10010ulhCntlocalLineTrscvUncorrectedSdFecErrorCounterEntry OBJECT-TYPE
	SYNTAX Pm10010ulhCntlocalLineTrscvUncorrectedSdFecErrorCounterEntry
	MAX-ACCESS not-accessible
	STATUS current
	DESCRIPTION
        "
        Row definition for the pm10010ulhCntlocalLineTrscvUncorrectedSdFecErrorCounter 
        table
        "
	INDEX   { pm10010ulhCntlocalLineTrscvUncorrectedSdFecErrorCounterIndex }
	::= { pm10010ulhCntlocalLineTrscvUncorrectedSdFecErrorCounterTable 1 }


Pm10010ulhCntlocalLineTrscvUncorrectedSdFecErrorCounterEntry ::=
	SEQUENCE {
	pm10010ulhCntlocalLineTrscvUncorrectedSdFecErrorCounterIndex
		INTEGER,
	pm10010ulhCntlocalLineTrscvUncorrectedSdFecErrorCounterValuePortn
		Counter64,
	pm10010ulhCntlocalLineTrscvUncorrectedSdFecErrorCounterErrorPortn
		EkiOnOff,
	pm10010ulhCntlocalLineTrscvUncorrectedSdFecErrorCounterOverloadPortn
		EkiOnOff
	}


pm10010ulhCntlocalLineTrscvUncorrectedSdFecErrorCounterIndex OBJECT-TYPE
	SYNTAX  INTEGER(0..128)
	MAX-ACCESS  read-only
	STATUS current
	DESCRIPTION
        "
        Index definition for the pm10010ulhCntlocalLineTrscvUncorrectedSdFecErrorCounter 
        table
        "
	::= { pm10010ulhCntlocalLineTrscvUncorrectedSdFecErrorCounterEntry 1 }


pm10010ulhCntlocalLineTrscvUncorrectedSdFecErrorCounterValuePortn OBJECT-TYPE
	SYNTAX  Counter64
	MAX-ACCESS read-only
	STATUS current
	DESCRIPTION
        "
        Uncorrected SD FEC Errors :This 
        OID gives the current Bit Error 
        Rate after the Soft Decision FEC 
        (residual)  <Help> This counter 
        gives the current Bit Error Rate 
        after the Soft Decision FEC (residual)
        "
	::= { pm10010ulhCntlocalLineTrscvUncorrectedSdFecErrorCounterEntry 2 }


pm10010ulhCntlocalLineTrscvUncorrectedSdFecErrorCounterErrorPortn OBJECT-TYPE
	SYNTAX  EkiOnOff
	MAX-ACCESS read-only
	STATUS current
	DESCRIPTION
        "
        Line Counter Error :This OID when 
        set indicates the deframer timer 
        counter value is invalid on Port
        "
	::= { pm10010ulhCntlocalLineTrscvUncorrectedSdFecErrorCounterEntry 3 }


pm10010ulhCntlocalLineTrscvUncorrectedSdFecErrorCounterOverloadPortn OBJECT-TYPE
	SYNTAX  EkiOnOff
	MAX-ACCESS read-only
	STATUS current
	DESCRIPTION
        "
        Line Counter Overload :This OID 
        when set indicates a deframer timer 
        counter overload on Port
        "
	::= { pm10010ulhCntlocalLineTrscvUncorrectedSdFecErrorCounterEntry 4 }


--- *********************************************************
---     TABLE for the pm10010ulhCntlocalLineTrscvPreSdFecBitCounter articles
--- *********************************************************

pm10010ulhCntlocalLineTrscvPreSdFecBitCounterTable OBJECT-TYPE
	SYNTAX  SEQUENCE OF Pm10010ulhCntlocalLineTrscvPreSdFecBitCounterEntry
	MAX-ACCESS not-accessible
	STATUS current
	DESCRIPTION
        "
        List of pm10010ulhCntlocalLineTrscvPreSdFecBitCounter 
        Article
        "
	::= { pm10010ulhCntLine 198 }


pm10010ulhCntlocalLineTrscvPreSdFecBitCounterEntry OBJECT-TYPE
	SYNTAX Pm10010ulhCntlocalLineTrscvPreSdFecBitCounterEntry
	MAX-ACCESS not-accessible
	STATUS current
	DESCRIPTION
        "
        Row definition for the pm10010ulhCntlocalLineTrscvPreSdFecBitCounter 
        table
        "
	INDEX   { pm10010ulhCntlocalLineTrscvPreSdFecBitCounterIndex }
	::= { pm10010ulhCntlocalLineTrscvPreSdFecBitCounterTable 1 }


Pm10010ulhCntlocalLineTrscvPreSdFecBitCounterEntry ::=
	SEQUENCE {
	pm10010ulhCntlocalLineTrscvPreSdFecBitCounterIndex
		INTEGER,
	pm10010ulhCntlocalLineTrscvPreSdFecBitCounterValuePortn
		Counter64,
	pm10010ulhCntlocalLineTrscvPreSdFecBitCounterErrorPortn
		EkiOnOff,
	pm10010ulhCntlocalLineTrscvPreSdFecBitCounterOverloadPortn
		EkiOnOff
	}


pm10010ulhCntlocalLineTrscvPreSdFecBitCounterIndex OBJECT-TYPE
	SYNTAX  INTEGER(0..128)
	MAX-ACCESS  read-only
	STATUS current
	DESCRIPTION
        "
        Index definition for the pm10010ulhCntlocalLineTrscvPreSdFecBitCounter 
        table
        "
	::= { pm10010ulhCntlocalLineTrscvPreSdFecBitCounterEntry 1 }


pm10010ulhCntlocalLineTrscvPreSdFecBitCounterValuePortn OBJECT-TYPE
	SYNTAX  Counter64
	MAX-ACCESS read-only
	STATUS current
	DESCRIPTION
        "
        Pre-SD FEC Bit Counter :This OID 
        gives the current Bit count before 
        the Soft Decision FEC  <Help> This 
        counter gives the current Bit Count 
        before the Soft Decision FEC
        "
	::= { pm10010ulhCntlocalLineTrscvPreSdFecBitCounterEntry 2 }


pm10010ulhCntlocalLineTrscvPreSdFecBitCounterErrorPortn OBJECT-TYPE
	SYNTAX  EkiOnOff
	MAX-ACCESS read-only
	STATUS current
	DESCRIPTION
        "
        Line Counter Error :This OID when 
        set indicates the deframer timer 
        counter value is invalid on Port
        "
	::= { pm10010ulhCntlocalLineTrscvPreSdFecBitCounterEntry 3 }


pm10010ulhCntlocalLineTrscvPreSdFecBitCounterOverloadPortn OBJECT-TYPE
	SYNTAX  EkiOnOff
	MAX-ACCESS read-only
	STATUS current
	DESCRIPTION
        "
        Line Counter Overload :This OID 
        when set indicates a deframer timer 
        counter overload on Port
        "
	::= { pm10010ulhCntlocalLineTrscvPreSdFecBitCounterEntry 4 }


--- *********************************************************
---     TABLE for the pm10010ulhCntlocalLineTrscvUncorrectedSdFecBitCounter articles
--- *********************************************************

pm10010ulhCntlocalLineTrscvUncorrectedSdFecBitCounterTable OBJECT-TYPE
	SYNTAX  SEQUENCE OF Pm10010ulhCntlocalLineTrscvUncorrectedSdFecBitCounterEntry
	MAX-ACCESS not-accessible
	STATUS current
	DESCRIPTION
        "
        List of pm10010ulhCntlocalLineTrscvUncorrectedSdFecBitCounter 
        Article
        "
	::= { pm10010ulhCntLine 199 }


pm10010ulhCntlocalLineTrscvUncorrectedSdFecBitCounterEntry OBJECT-TYPE
	SYNTAX Pm10010ulhCntlocalLineTrscvUncorrectedSdFecBitCounterEntry
	MAX-ACCESS not-accessible
	STATUS current
	DESCRIPTION
        "
        Row definition for the pm10010ulhCntlocalLineTrscvUncorrectedSdFecBitCounter 
        table
        "
	INDEX   { pm10010ulhCntlocalLineTrscvUncorrectedSdFecBitCounterIndex }
	::= { pm10010ulhCntlocalLineTrscvUncorrectedSdFecBitCounterTable 1 }


Pm10010ulhCntlocalLineTrscvUncorrectedSdFecBitCounterEntry ::=
	SEQUENCE {
	pm10010ulhCntlocalLineTrscvUncorrectedSdFecBitCounterIndex
		INTEGER,
	pm10010ulhCntlocalLineTrscvUncorrectedSdFecBitCounterValuePortn
		Counter64,
	pm10010ulhCntlocalLineTrscvUncorrectedSdFecBitCounterErrorPortn
		EkiOnOff,
	pm10010ulhCntlocalLineTrscvUncorrectedSdFecBitCounterOverloadPortn
		EkiOnOff
	}


pm10010ulhCntlocalLineTrscvUncorrectedSdFecBitCounterIndex OBJECT-TYPE
	SYNTAX  INTEGER(0..128)
	MAX-ACCESS  read-only
	STATUS current
	DESCRIPTION
        "
        Index definition for the pm10010ulhCntlocalLineTrscvUncorrectedSdFecBitCounter 
        table
        "
	::= { pm10010ulhCntlocalLineTrscvUncorrectedSdFecBitCounterEntry 1 }


pm10010ulhCntlocalLineTrscvUncorrectedSdFecBitCounterValuePortn OBJECT-TYPE
	SYNTAX  Counter64
	MAX-ACCESS read-only
	STATUS current
	DESCRIPTION
        "
        Uncorrected SD FEC Bit Counter 
        :This OID gives the current Bit 
        count after the Soft Decision FEC 
        (residual)  <Help> This counter 
        gives the current Bit Count after 
        the Soft Decision FEC (residual)
        "
	::= { pm10010ulhCntlocalLineTrscvUncorrectedSdFecBitCounterEntry 2 }


pm10010ulhCntlocalLineTrscvUncorrectedSdFecBitCounterErrorPortn OBJECT-TYPE
	SYNTAX  EkiOnOff
	MAX-ACCESS read-only
	STATUS current
	DESCRIPTION
        "
        Line Counter Error :This OID when 
        set indicates the deframer timer 
        counter value is invalid on Port
        "
	::= { pm10010ulhCntlocalLineTrscvUncorrectedSdFecBitCounterEntry 3 }


pm10010ulhCntlocalLineTrscvUncorrectedSdFecBitCounterOverloadPortn OBJECT-TYPE
	SYNTAX  EkiOnOff
	MAX-ACCESS read-only
	STATUS current
	DESCRIPTION
        "
        Line Counter Overload :This OID 
        when set indicates a deframer timer 
        counter overload on Port
        "
	::= { pm10010ulhCntlocalLineTrscvUncorrectedSdFecBitCounterEntry 4 }







--- *****************************************************
--- $$$$$$$$$$$$$$$$$$$$$$$$$$$$$$$$$$$$$$$$$$$$$$$$$$$$$
---     RMON - 64 bits COUNTERS
--- $$$$$$$$$$$$$$$$$$$$$$$$$$$$$$$$$$$$$$$$$$$$$$$$$$$$$
--- *****************************************************



--- *********************************************************
---     TABLE for the pm10010ulhMonupRmonBytesCounterClientInput articles
--- *********************************************************

pm10010ulhMonupRmonBytesCounterClientInputTable OBJECT-TYPE
	SYNTAX  SEQUENCE OF Pm10010ulhMonupRmonBytesCounterClientInputEntry
	MAX-ACCESS not-accessible
	STATUS current
	DESCRIPTION
        "
        List of pm10010ulhMonupRmonBytesCounterClientInput 
        Article
        "
	::= { pm10010ulhMonClientRmonCounter 16 }


pm10010ulhMonupRmonBytesCounterClientInputEntry OBJECT-TYPE
	SYNTAX Pm10010ulhMonupRmonBytesCounterClientInputEntry
	MAX-ACCESS not-accessible
	STATUS current
	DESCRIPTION
        "
        Row definition for the pm10010ulhMonupRmonBytesCounterClientInput 
        table
        "
	INDEX   { pm10010ulhMonupRmonBytesCounterClientInputIndex }
	::= { pm10010ulhMonupRmonBytesCounterClientInputTable 1 }


Pm10010ulhMonupRmonBytesCounterClientInputEntry ::=
	SEQUENCE {
	pm10010ulhMonupRmonBytesCounterClientInputIndex
		INTEGER,
	pm10010ulhMonupRmonBytesCounterClientInputValuePortn
		Counter64,
	pm10010ulhMonupRmonBytesCounterClientInputErrorPortn
		EkiOnOff,
	pm10010ulhMonupRmonBytesCounterClientInputOverloadPortn
		EkiOnOff
	}


pm10010ulhMonupRmonBytesCounterClientInputIndex OBJECT-TYPE
	SYNTAX  INTEGER(0..128)
	MAX-ACCESS  read-only
	STATUS current
	DESCRIPTION
        "
        Index definition for the pm10010ulhMonupRmonBytesCounterClientInput 
        table
        "
	::= { pm10010ulhMonupRmonBytesCounterClientInputEntry 1 }


pm10010ulhMonupRmonBytesCounterClientInputValuePortn OBJECT-TYPE
	SYNTAX  Counter64
	MAX-ACCESS read-only
	STATUS current
	DESCRIPTION
        "
        Client Input Bytes :This counter 
        is increased each time a data byte 
        is received on the client port
          <Help>  This counter gives the 
        number of bytes received on the 
        client port
        "
	::= { pm10010ulhMonupRmonBytesCounterClientInputEntry 2 }


pm10010ulhMonupRmonBytesCounterClientInputErrorPortn OBJECT-TYPE
	SYNTAX  EkiOnOff
	MAX-ACCESS read-only
	STATUS current
	DESCRIPTION
        "
        Bytes Counter Error :This OID
         when set indicates the Bytes counter 
        value is invalid on client port
        "
	::= { pm10010ulhMonupRmonBytesCounterClientInputEntry 3 }


pm10010ulhMonupRmonBytesCounterClientInputOverloadPortn OBJECT-TYPE
	SYNTAX  EkiOnOff
	MAX-ACCESS read-only
	STATUS current
	DESCRIPTION
        "
        Bytes Counter Overload :This OID 
        when set indicates a Bytes counter 
        overload on client port
        "
	::= { pm10010ulhMonupRmonBytesCounterClientInputEntry 4 }


--- *********************************************************
---     TABLE for the pm10010ulhMonupRmonCrcErrorsCounterClientInput articles
--- *********************************************************

pm10010ulhMonupRmonCrcErrorsCounterClientInputTable OBJECT-TYPE
	SYNTAX  SEQUENCE OF Pm10010ulhMonupRmonCrcErrorsCounterClientInputEntry
	MAX-ACCESS not-accessible
	STATUS current
	DESCRIPTION
        "
        List of pm10010ulhMonupRmonCrcErrorsCounterClientInput 
        Article
        "
	::= { pm10010ulhMonClientRmonCounter 48 }


pm10010ulhMonupRmonCrcErrorsCounterClientInputEntry OBJECT-TYPE
	SYNTAX Pm10010ulhMonupRmonCrcErrorsCounterClientInputEntry
	MAX-ACCESS not-accessible
	STATUS current
	DESCRIPTION
        "
        Row definition for the pm10010ulhMonupRmonCrcErrorsCounterClientInput 
        table
        "
	INDEX   { pm10010ulhMonupRmonCrcErrorsCounterClientInputIndex }
	::= { pm10010ulhMonupRmonCrcErrorsCounterClientInputTable 1 }


Pm10010ulhMonupRmonCrcErrorsCounterClientInputEntry ::=
	SEQUENCE {
	pm10010ulhMonupRmonCrcErrorsCounterClientInputIndex
		INTEGER,
	pm10010ulhMonupRmonCrcErrorsCounterClientInputValuePortn
		Counter64,
	pm10010ulhMonupRmonCrcErrorsCounterClientInputErrorPortn
		EkiOnOff,
	pm10010ulhMonupRmonCrcErrorsCounterClientInputOverloadPortn
		EkiOnOff
	}


pm10010ulhMonupRmonCrcErrorsCounterClientInputIndex OBJECT-TYPE
	SYNTAX  INTEGER(0..128)
	MAX-ACCESS  read-only
	STATUS current
	DESCRIPTION
        "
        Index definition for the pm10010ulhMonupRmonCrcErrorsCounterClientInput 
        table
        "
	::= { pm10010ulhMonupRmonCrcErrorsCounterClientInputEntry 1 }


pm10010ulhMonupRmonCrcErrorsCounterClientInputValuePortn OBJECT-TYPE
	SYNTAX  Counter64
	MAX-ACCESS read-only
	STATUS current
	DESCRIPTION
        "
        Client Input CRC Errors :This
         counter is increased each time 
        a CRC error is detected on the
         client port<Help>  This counter 
        gives the number of CRC Errors
         received on the client port
        "
	::= { pm10010ulhMonupRmonCrcErrorsCounterClientInputEntry 2 }


pm10010ulhMonupRmonCrcErrorsCounterClientInputErrorPortn OBJECT-TYPE
	SYNTAX  EkiOnOff
	MAX-ACCESS read-only
	STATUS current
	DESCRIPTION
        "
        CRC Errors Counter Error :This 
        OID when set indicates the CRC
         Errors counter value is invalid 
        on client port
        "
	::= { pm10010ulhMonupRmonCrcErrorsCounterClientInputEntry 3 }


pm10010ulhMonupRmonCrcErrorsCounterClientInputOverloadPortn OBJECT-TYPE
	SYNTAX  EkiOnOff
	MAX-ACCESS read-only
	STATUS current
	DESCRIPTION
        "
        CRC Errors Counter Overload :This 
        OID when set indicates a CRC Errors 
        counter overload on client port
        "
	::= { pm10010ulhMonupRmonCrcErrorsCounterClientInputEntry 4 }


--- *********************************************************
---     TABLE for the pm10010ulhMonupRmonPacketsCounterClientInput articles
--- *********************************************************

pm10010ulhMonupRmonPacketsCounterClientInputTable OBJECT-TYPE
	SYNTAX  SEQUENCE OF Pm10010ulhMonupRmonPacketsCounterClientInputEntry
	MAX-ACCESS not-accessible
	STATUS current
	DESCRIPTION
        "
        List of pm10010ulhMonupRmonPacketsCounterClientInput 
        Article
        "
	::= { pm10010ulhMonClientRmonCounter 80 }


pm10010ulhMonupRmonPacketsCounterClientInputEntry OBJECT-TYPE
	SYNTAX Pm10010ulhMonupRmonPacketsCounterClientInputEntry
	MAX-ACCESS not-accessible
	STATUS current
	DESCRIPTION
        "
        Row definition for the pm10010ulhMonupRmonPacketsCounterClientInput 
        table
        "
	INDEX   { pm10010ulhMonupRmonPacketsCounterClientInputIndex }
	::= { pm10010ulhMonupRmonPacketsCounterClientInputTable 1 }


Pm10010ulhMonupRmonPacketsCounterClientInputEntry ::=
	SEQUENCE {
	pm10010ulhMonupRmonPacketsCounterClientInputIndex
		INTEGER,
	pm10010ulhMonupRmonPacketsCounterClientInputValuePortn
		Counter64,
	pm10010ulhMonupRmonPacketsCounterClientInputErrorPortn
		EkiOnOff,
	pm10010ulhMonupRmonPacketsCounterClientInputOverloadPortn
		EkiOnOff
	}


pm10010ulhMonupRmonPacketsCounterClientInputIndex OBJECT-TYPE
	SYNTAX  INTEGER(0..128)
	MAX-ACCESS  read-only
	STATUS current
	DESCRIPTION
        "
        Index definition for the pm10010ulhMonupRmonPacketsCounterClientInput 
        table
        "
	::= { pm10010ulhMonupRmonPacketsCounterClientInputEntry 1 }


pm10010ulhMonupRmonPacketsCounterClientInputValuePortn OBJECT-TYPE
	SYNTAX  Counter64
	MAX-ACCESS read-only
	STATUS current
	DESCRIPTION
        "
        Client Input Packets :This counter 
        is increased each time a packet 
        is received on the client port
          <Help>  This counter gives the 
        number of packets received on the 
        client port
        "
	::= { pm10010ulhMonupRmonPacketsCounterClientInputEntry 2 }


pm10010ulhMonupRmonPacketsCounterClientInputErrorPortn OBJECT-TYPE
	SYNTAX  EkiOnOff
	MAX-ACCESS read-only
	STATUS current
	DESCRIPTION
        "
        Packets Counter Error :This OID 
        when set indicates the Packets
         counter value is invalid on client 
        port
        "
	::= { pm10010ulhMonupRmonPacketsCounterClientInputEntry 3 }


pm10010ulhMonupRmonPacketsCounterClientInputOverloadPortn OBJECT-TYPE
	SYNTAX  EkiOnOff
	MAX-ACCESS read-only
	STATUS current
	DESCRIPTION
        "
        Packets Counter Overload :This 
        OID when set indicates a Packets 
        counter overload on client port
        "
	::= { pm10010ulhMonupRmonPacketsCounterClientInputEntry 4 }


--- *********************************************************
---     TABLE for the pm10010ulhMonupRmonBroadcastCounterClientInput articles
--- *********************************************************

pm10010ulhMonupRmonBroadcastCounterClientInputTable OBJECT-TYPE
	SYNTAX  SEQUENCE OF Pm10010ulhMonupRmonBroadcastCounterClientInputEntry
	MAX-ACCESS not-accessible
	STATUS current
	DESCRIPTION
        "
        List of pm10010ulhMonupRmonBroadcastCounterClientInput 
        Article
        "
	::= { pm10010ulhMonClientRmonCounter 112 }


pm10010ulhMonupRmonBroadcastCounterClientInputEntry OBJECT-TYPE
	SYNTAX Pm10010ulhMonupRmonBroadcastCounterClientInputEntry
	MAX-ACCESS not-accessible
	STATUS current
	DESCRIPTION
        "
        Row definition for the pm10010ulhMonupRmonBroadcastCounterClientInput 
        table
        "
	INDEX   { pm10010ulhMonupRmonBroadcastCounterClientInputIndex }
	::= { pm10010ulhMonupRmonBroadcastCounterClientInputTable 1 }


Pm10010ulhMonupRmonBroadcastCounterClientInputEntry ::=
	SEQUENCE {
	pm10010ulhMonupRmonBroadcastCounterClientInputIndex
		INTEGER,
	pm10010ulhMonupRmonBroadcastCounterClientInputValuePortn
		Counter64,
	pm10010ulhMonupRmonBroadcastCounterClientInputErrorPortn
		EkiOnOff,
	pm10010ulhMonupRmonBroadcastCounterClientInputOverloadPortn
		EkiOnOff
	}


pm10010ulhMonupRmonBroadcastCounterClientInputIndex OBJECT-TYPE
	SYNTAX  INTEGER(0..128)
	MAX-ACCESS  read-only
	STATUS current
	DESCRIPTION
        "
        Index definition for the pm10010ulhMonupRmonBroadcastCounterClientInput 
        table
        "
	::= { pm10010ulhMonupRmonBroadcastCounterClientInputEntry 1 }


pm10010ulhMonupRmonBroadcastCounterClientInputValuePortn OBJECT-TYPE
	SYNTAX  Counter64
	MAX-ACCESS read-only
	STATUS current
	DESCRIPTION
        "
        Client Input Broadcast Packets 
        :This counter is increased each 
        time a broadcast packet is received 
        on the client port  <Help>  This 
        counter gives the number of Broadcast 
        packets received on the client
         port
        "
	::= { pm10010ulhMonupRmonBroadcastCounterClientInputEntry 2 }


pm10010ulhMonupRmonBroadcastCounterClientInputErrorPortn OBJECT-TYPE
	SYNTAX  EkiOnOff
	MAX-ACCESS read-only
	STATUS current
	DESCRIPTION
        "
        Broadcast Counter Error :This
         OID when set indicates the Broadcast 
        counter value is invalid on client 
        port
        "
	::= { pm10010ulhMonupRmonBroadcastCounterClientInputEntry 3 }


pm10010ulhMonupRmonBroadcastCounterClientInputOverloadPortn OBJECT-TYPE
	SYNTAX  EkiOnOff
	MAX-ACCESS read-only
	STATUS current
	DESCRIPTION
        "
        Broadcast Counter Overload :This 
        OID when set indicates a Broadcast 
        counter overload on client port
        "
	::= { pm10010ulhMonupRmonBroadcastCounterClientInputEntry 4 }


--- *********************************************************
---     TABLE for the pm10010ulhMonupRmonMulticastCounterClientInput articles
--- *********************************************************

pm10010ulhMonupRmonMulticastCounterClientInputTable OBJECT-TYPE
	SYNTAX  SEQUENCE OF Pm10010ulhMonupRmonMulticastCounterClientInputEntry
	MAX-ACCESS not-accessible
	STATUS current
	DESCRIPTION
        "
        List of pm10010ulhMonupRmonMulticastCounterClientInput 
        Article
        "
	::= { pm10010ulhMonClientRmonCounter 144 }


pm10010ulhMonupRmonMulticastCounterClientInputEntry OBJECT-TYPE
	SYNTAX Pm10010ulhMonupRmonMulticastCounterClientInputEntry
	MAX-ACCESS not-accessible
	STATUS current
	DESCRIPTION
        "
        Row definition for the pm10010ulhMonupRmonMulticastCounterClientInput 
        table
        "
	INDEX   { pm10010ulhMonupRmonMulticastCounterClientInputIndex }
	::= { pm10010ulhMonupRmonMulticastCounterClientInputTable 1 }


Pm10010ulhMonupRmonMulticastCounterClientInputEntry ::=
	SEQUENCE {
	pm10010ulhMonupRmonMulticastCounterClientInputIndex
		INTEGER,
	pm10010ulhMonupRmonMulticastCounterClientInputValuePortn
		Counter64,
	pm10010ulhMonupRmonMulticastCounterClientInputErrorPortn
		EkiOnOff,
	pm10010ulhMonupRmonMulticastCounterClientInputOverloadPortn
		EkiOnOff
	}


pm10010ulhMonupRmonMulticastCounterClientInputIndex OBJECT-TYPE
	SYNTAX  INTEGER(0..128)
	MAX-ACCESS  read-only
	STATUS current
	DESCRIPTION
        "
        Index definition for the pm10010ulhMonupRmonMulticastCounterClientInput 
        table
        "
	::= { pm10010ulhMonupRmonMulticastCounterClientInputEntry 1 }


pm10010ulhMonupRmonMulticastCounterClientInputValuePortn OBJECT-TYPE
	SYNTAX  Counter64
	MAX-ACCESS read-only
	STATUS current
	DESCRIPTION
        "
        Client Input Multicast Packets 
        :This counter is increased each 
        time a Multicast packet is received 
        on the client port  <Help>  This 
        counter gives the number of Multicast 
        packets received on the client
         port
        "
	::= { pm10010ulhMonupRmonMulticastCounterClientInputEntry 2 }


pm10010ulhMonupRmonMulticastCounterClientInputErrorPortn OBJECT-TYPE
	SYNTAX  EkiOnOff
	MAX-ACCESS read-only
	STATUS current
	DESCRIPTION
        "
        Multicast Counter Error :This
         OID when set indicates the Multicast 
        counter value is invalid on client 
        port
        "
	::= { pm10010ulhMonupRmonMulticastCounterClientInputEntry 3 }


pm10010ulhMonupRmonMulticastCounterClientInputOverloadPortn OBJECT-TYPE
	SYNTAX  EkiOnOff
	MAX-ACCESS read-only
	STATUS current
	DESCRIPTION
        "
        Multicast Counter Overload :This 
        OID when set indicates a Multicast 
        counter overload on client port
        "
	::= { pm10010ulhMonupRmonMulticastCounterClientInputEntry 4 }


--- *********************************************************
---     TABLE for the pm10010ulhMonupRmonPauseFrameCounterClientInput articles
--- *********************************************************

pm10010ulhMonupRmonPauseFrameCounterClientInputTable OBJECT-TYPE
	SYNTAX  SEQUENCE OF Pm10010ulhMonupRmonPauseFrameCounterClientInputEntry
	MAX-ACCESS not-accessible
	STATUS current
	DESCRIPTION
        "
        List of pm10010ulhMonupRmonPauseFrameCounterClientInput 
        Article
        "
	::= { pm10010ulhMonClientRmonCounter 176 }


pm10010ulhMonupRmonPauseFrameCounterClientInputEntry OBJECT-TYPE
	SYNTAX Pm10010ulhMonupRmonPauseFrameCounterClientInputEntry
	MAX-ACCESS not-accessible
	STATUS current
	DESCRIPTION
        "
        Row definition for the pm10010ulhMonupRmonPauseFrameCounterClientInput 
        table
        "
	INDEX   { pm10010ulhMonupRmonPauseFrameCounterClientInputIndex }
	::= { pm10010ulhMonupRmonPauseFrameCounterClientInputTable 1 }


Pm10010ulhMonupRmonPauseFrameCounterClientInputEntry ::=
	SEQUENCE {
	pm10010ulhMonupRmonPauseFrameCounterClientInputIndex
		INTEGER,
	pm10010ulhMonupRmonPauseFrameCounterClientInputValuePortn
		Counter64,
	pm10010ulhMonupRmonPauseFrameCounterClientInputErrorPortn
		EkiOnOff,
	pm10010ulhMonupRmonPauseFrameCounterClientInputOverloadPortn
		EkiOnOff
	}


pm10010ulhMonupRmonPauseFrameCounterClientInputIndex OBJECT-TYPE
	SYNTAX  INTEGER(0..128)
	MAX-ACCESS  read-only
	STATUS current
	DESCRIPTION
        "
        Index definition for the pm10010ulhMonupRmonPauseFrameCounterClientInput 
        table
        "
	::= { pm10010ulhMonupRmonPauseFrameCounterClientInputEntry 1 }


pm10010ulhMonupRmonPauseFrameCounterClientInputValuePortn OBJECT-TYPE
	SYNTAX  Counter64
	MAX-ACCESS read-only
	STATUS current
	DESCRIPTION
        "
        Client Input Pause Frames :This 
        counter is increased each time
         a Pause frame is received on the 
        client port  <Help>  This counter 
        gives the number of Pause frames 
        received on the client port
        "
	::= { pm10010ulhMonupRmonPauseFrameCounterClientInputEntry 2 }


pm10010ulhMonupRmonPauseFrameCounterClientInputErrorPortn OBJECT-TYPE
	SYNTAX  EkiOnOff
	MAX-ACCESS read-only
	STATUS current
	DESCRIPTION
        "
        Pause Counter Error :This OID
         when set indicates the Pause counter 
        value is invalid on client port
        "
	::= { pm10010ulhMonupRmonPauseFrameCounterClientInputEntry 3 }


pm10010ulhMonupRmonPauseFrameCounterClientInputOverloadPortn OBJECT-TYPE
	SYNTAX  EkiOnOff
	MAX-ACCESS read-only
	STATUS current
	DESCRIPTION
        "
        Pause Counter Overload :This OID 
        when set indicates a Pause counter 
        overload on client port
        "
	::= { pm10010ulhMonupRmonPauseFrameCounterClientInputEntry 4 }


--- *********************************************************
---     TABLE for the pm10010ulhMonupRmonUnicastCounterClientInput articles
--- *********************************************************

pm10010ulhMonupRmonUnicastCounterClientInputTable OBJECT-TYPE
	SYNTAX  SEQUENCE OF Pm10010ulhMonupRmonUnicastCounterClientInputEntry
	MAX-ACCESS not-accessible
	STATUS current
	DESCRIPTION
        "
        List of pm10010ulhMonupRmonUnicastCounterClientInput 
        Article
        "
	::= { pm10010ulhMonClientRmonCounter 304 }


pm10010ulhMonupRmonUnicastCounterClientInputEntry OBJECT-TYPE
	SYNTAX Pm10010ulhMonupRmonUnicastCounterClientInputEntry
	MAX-ACCESS not-accessible
	STATUS current
	DESCRIPTION
        "
        Row definition for the pm10010ulhMonupRmonUnicastCounterClientInput 
        table
        "
	INDEX   { pm10010ulhMonupRmonUnicastCounterClientInputIndex }
	::= { pm10010ulhMonupRmonUnicastCounterClientInputTable 1 }


Pm10010ulhMonupRmonUnicastCounterClientInputEntry ::=
	SEQUENCE {
	pm10010ulhMonupRmonUnicastCounterClientInputIndex
		INTEGER,
	pm10010ulhMonupRmonUnicastCounterClientInputValuePortn
		Counter64,
	pm10010ulhMonupRmonUnicastCounterClientInputErrorPortn
		EkiOnOff,
	pm10010ulhMonupRmonUnicastCounterClientInputOverloadPortn
		EkiOnOff
	}


pm10010ulhMonupRmonUnicastCounterClientInputIndex OBJECT-TYPE
	SYNTAX  INTEGER(0..128)
	MAX-ACCESS  read-only
	STATUS current
	DESCRIPTION
        "
        Index definition for the pm10010ulhMonupRmonUnicastCounterClientInput 
        table
        "
	::= { pm10010ulhMonupRmonUnicastCounterClientInputEntry 1 }


pm10010ulhMonupRmonUnicastCounterClientInputValuePortn OBJECT-TYPE
	SYNTAX  Counter64
	MAX-ACCESS read-only
	STATUS current
	DESCRIPTION
        "
        Client Input Unicast Packets :This 
        counter is increased each time
         a Unicast packet is received on 
        the client port  <Help>  This counter 
        gives the number of Unicast packets 
        received on the client port
        "
	::= { pm10010ulhMonupRmonUnicastCounterClientInputEntry 2 }


pm10010ulhMonupRmonUnicastCounterClientInputErrorPortn OBJECT-TYPE
	SYNTAX  EkiOnOff
	MAX-ACCESS read-only
	STATUS current
	DESCRIPTION
        "
        Unicast Counter Error :This OID 
        when set indicates the Unicast
         counter value is invalid on client 
        port
        "
	::= { pm10010ulhMonupRmonUnicastCounterClientInputEntry 3 }


pm10010ulhMonupRmonUnicastCounterClientInputOverloadPortn OBJECT-TYPE
	SYNTAX  EkiOnOff
	MAX-ACCESS read-only
	STATUS current
	DESCRIPTION
        "
        Unicast Counter Overload :This 
        OID when set indicates a Unicast 
        counter overload on client port
        "
	::= { pm10010ulhMonupRmonUnicastCounterClientInputEntry 4 }


--- *********************************************************
---     TABLE for the pm10010ulhMonupRmonNonunicastCounterClientInput articles
--- *********************************************************

pm10010ulhMonupRmonNonunicastCounterClientInputTable OBJECT-TYPE
	SYNTAX  SEQUENCE OF Pm10010ulhMonupRmonNonunicastCounterClientInputEntry
	MAX-ACCESS not-accessible
	STATUS current
	DESCRIPTION
        "
        List of pm10010ulhMonupRmonNonunicastCounterClientInput 
        Article
        "
	::= { pm10010ulhMonClientRmonCounter 336 }


pm10010ulhMonupRmonNonunicastCounterClientInputEntry OBJECT-TYPE
	SYNTAX Pm10010ulhMonupRmonNonunicastCounterClientInputEntry
	MAX-ACCESS not-accessible
	STATUS current
	DESCRIPTION
        "
        Row definition for the pm10010ulhMonupRmonNonunicastCounterClientInput 
        table
        "
	INDEX   { pm10010ulhMonupRmonNonunicastCounterClientInputIndex }
	::= { pm10010ulhMonupRmonNonunicastCounterClientInputTable 1 }


Pm10010ulhMonupRmonNonunicastCounterClientInputEntry ::=
	SEQUENCE {
	pm10010ulhMonupRmonNonunicastCounterClientInputIndex
		INTEGER,
	pm10010ulhMonupRmonNonunicastCounterClientInputValuePortn
		Counter64,
	pm10010ulhMonupRmonNonunicastCounterClientInputErrorPortn
		EkiOnOff,
	pm10010ulhMonupRmonNonunicastCounterClientInputOverloadPortn
		EkiOnOff
	}


pm10010ulhMonupRmonNonunicastCounterClientInputIndex OBJECT-TYPE
	SYNTAX  INTEGER(0..128)
	MAX-ACCESS  read-only
	STATUS current
	DESCRIPTION
        "
        Index definition for the pm10010ulhMonupRmonNonunicastCounterClientInput 
        table
        "
	::= { pm10010ulhMonupRmonNonunicastCounterClientInputEntry 1 }


pm10010ulhMonupRmonNonunicastCounterClientInputValuePortn OBJECT-TYPE
	SYNTAX  Counter64
	MAX-ACCESS read-only
	STATUS current
	DESCRIPTION
        "
        Client Input Non Unicast Packets 
        :This counter is increased each 
        time a Non-Unicast packet is received 
        on the client port  <Help>  This 
        counter gives the number of Non-Unicast 
        packets received on the client
         port
        "
	::= { pm10010ulhMonupRmonNonunicastCounterClientInputEntry 2 }


pm10010ulhMonupRmonNonunicastCounterClientInputErrorPortn OBJECT-TYPE
	SYNTAX  EkiOnOff
	MAX-ACCESS read-only
	STATUS current
	DESCRIPTION
        "
        Non Unicast Counter Error :This 
        OID when set indicates the Non-Unicast 
        counter value is invalid on client 
        port
        "
	::= { pm10010ulhMonupRmonNonunicastCounterClientInputEntry 3 }


pm10010ulhMonupRmonNonunicastCounterClientInputOverloadPortn OBJECT-TYPE
	SYNTAX  EkiOnOff
	MAX-ACCESS read-only
	STATUS current
	DESCRIPTION
        "
        Non Unicast Counter Overload :This 
        OID when set indicates a Non-Unicast 
        counter overload on client port
        "
	::= { pm10010ulhMonupRmonNonunicastCounterClientInputEntry 4 }


--- *********************************************************
---     TABLE for the pm10010ulhMondownRmonBytesCounterClientOutput articles
--- *********************************************************

pm10010ulhMondownRmonBytesCounterClientOutputTable OBJECT-TYPE
	SYNTAX  SEQUENCE OF Pm10010ulhMondownRmonBytesCounterClientOutputEntry
	MAX-ACCESS not-accessible
	STATUS current
	DESCRIPTION
        "
        List of pm10010ulhMondownRmonBytesCounterClientOutput 
        Article
        "
	::= { pm10010ulhMonClientRmonCounter 400 }


pm10010ulhMondownRmonBytesCounterClientOutputEntry OBJECT-TYPE
	SYNTAX Pm10010ulhMondownRmonBytesCounterClientOutputEntry
	MAX-ACCESS not-accessible
	STATUS current
	DESCRIPTION
        "
        Row definition for the pm10010ulhMondownRmonBytesCounterClientOutput 
        table
        "
	INDEX   { pm10010ulhMondownRmonBytesCounterClientOutputIndex }
	::= { pm10010ulhMondownRmonBytesCounterClientOutputTable 1 }


Pm10010ulhMondownRmonBytesCounterClientOutputEntry ::=
	SEQUENCE {
	pm10010ulhMondownRmonBytesCounterClientOutputIndex
		INTEGER,
	pm10010ulhMondownRmonBytesCounterClientOutputValuePortn
		Counter64,
	pm10010ulhMondownRmonBytesCounterClientOutputErrorPortn
		EkiOnOff,
	pm10010ulhMondownRmonBytesCounterClientOutputOverloadPortn
		EkiOnOff
	}


pm10010ulhMondownRmonBytesCounterClientOutputIndex OBJECT-TYPE
	SYNTAX  INTEGER(0..128)
	MAX-ACCESS  read-only
	STATUS current
	DESCRIPTION
        "
        Index definition for the pm10010ulhMondownRmonBytesCounterClientOutput 
        table
        "
	::= { pm10010ulhMondownRmonBytesCounterClientOutputEntry 1 }


pm10010ulhMondownRmonBytesCounterClientOutputValuePortn OBJECT-TYPE
	SYNTAX  Counter64
	MAX-ACCESS read-only
	STATUS current
	DESCRIPTION
        "
        Client Output Bytes :This counter 
        is increased each time a data byte 
        is transmitted on the client port 
        <Help> This counter gives the number 
        of bytes transmitted on the client 
        port
        "
	::= { pm10010ulhMondownRmonBytesCounterClientOutputEntry 2 }


pm10010ulhMondownRmonBytesCounterClientOutputErrorPortn OBJECT-TYPE
	SYNTAX  EkiOnOff
	MAX-ACCESS read-only
	STATUS current
	DESCRIPTION
        "
        Bytes Counter Error :This OID
         when set indicates the Bytes counter 
        value is invalid on client port
        "
	::= { pm10010ulhMondownRmonBytesCounterClientOutputEntry 3 }


pm10010ulhMondownRmonBytesCounterClientOutputOverloadPortn OBJECT-TYPE
	SYNTAX  EkiOnOff
	MAX-ACCESS read-only
	STATUS current
	DESCRIPTION
        "
        Bytes Counter Overload :This OID 
        when set indicates a Bytes counter 
        overload on client port

        "
	::= { pm10010ulhMondownRmonBytesCounterClientOutputEntry 4 }


--- *********************************************************
---     TABLE for the pm10010ulhMondownRmonCrcErrorsCounterClientOutput articles
--- *********************************************************

pm10010ulhMondownRmonCrcErrorsCounterClientOutputTable OBJECT-TYPE
	SYNTAX  SEQUENCE OF Pm10010ulhMondownRmonCrcErrorsCounterClientOutputEntry
	MAX-ACCESS not-accessible
	STATUS current
	DESCRIPTION
        "
        List of pm10010ulhMondownRmonCrcErrorsCounterClientOutput 
        Article
        "
	::= { pm10010ulhMonClientRmonCounter 432 }


pm10010ulhMondownRmonCrcErrorsCounterClientOutputEntry OBJECT-TYPE
	SYNTAX Pm10010ulhMondownRmonCrcErrorsCounterClientOutputEntry
	MAX-ACCESS not-accessible
	STATUS current
	DESCRIPTION
        "
        Row definition for the pm10010ulhMondownRmonCrcErrorsCounterClientOutput 
        table
        "
	INDEX   { pm10010ulhMondownRmonCrcErrorsCounterClientOutputIndex }
	::= { pm10010ulhMondownRmonCrcErrorsCounterClientOutputTable 1 }


Pm10010ulhMondownRmonCrcErrorsCounterClientOutputEntry ::=
	SEQUENCE {
	pm10010ulhMondownRmonCrcErrorsCounterClientOutputIndex
		INTEGER,
	pm10010ulhMondownRmonCrcErrorsCounterClientOutputValuePortn
		Counter64,
	pm10010ulhMondownRmonCrcErrorsCounterClientOutputErrorPortn
		EkiOnOff,
	pm10010ulhMondownRmonCrcErrorsCounterClientOutputOverloadPortn
		EkiOnOff
	}


pm10010ulhMondownRmonCrcErrorsCounterClientOutputIndex OBJECT-TYPE
	SYNTAX  INTEGER(0..128)
	MAX-ACCESS  read-only
	STATUS current
	DESCRIPTION
        "
        Index definition for the pm10010ulhMondownRmonCrcErrorsCounterClientOutput 
        table
        "
	::= { pm10010ulhMondownRmonCrcErrorsCounterClientOutputEntry 1 }


pm10010ulhMondownRmonCrcErrorsCounterClientOutputValuePortn OBJECT-TYPE
	SYNTAX  Counter64
	MAX-ACCESS read-only
	STATUS current
	DESCRIPTION
        "
        Client Output CRC Errors :This 
        counter is increased each time
         a CRC error is detected on the 
        transmit client port  <Help>  This 
        counter gives the number of CRC 
        Errors transmitted on the client 
        port
        "
	::= { pm10010ulhMondownRmonCrcErrorsCounterClientOutputEntry 2 }


pm10010ulhMondownRmonCrcErrorsCounterClientOutputErrorPortn OBJECT-TYPE
	SYNTAX  EkiOnOff
	MAX-ACCESS read-only
	STATUS current
	DESCRIPTION
        "
        CRC Errors Counter Error :This 
        OID when set indicates the CRC
         Errors counter value is invalid 
        on client port
        "
	::= { pm10010ulhMondownRmonCrcErrorsCounterClientOutputEntry 3 }


pm10010ulhMondownRmonCrcErrorsCounterClientOutputOverloadPortn OBJECT-TYPE
	SYNTAX  EkiOnOff
	MAX-ACCESS read-only
	STATUS current
	DESCRIPTION
        "
        CRC Errors Counter Overload :This 
        OID when set indicates a CRC Errors 
        counter overload on client port
        "
	::= { pm10010ulhMondownRmonCrcErrorsCounterClientOutputEntry 4 }


--- *********************************************************
---     TABLE for the pm10010ulhMondownRmonPacketsCounterClientOutput articles
--- *********************************************************

pm10010ulhMondownRmonPacketsCounterClientOutputTable OBJECT-TYPE
	SYNTAX  SEQUENCE OF Pm10010ulhMondownRmonPacketsCounterClientOutputEntry
	MAX-ACCESS not-accessible
	STATUS current
	DESCRIPTION
        "
        List of pm10010ulhMondownRmonPacketsCounterClientOutput 
        Article
        "
	::= { pm10010ulhMonClientRmonCounter 464 }


pm10010ulhMondownRmonPacketsCounterClientOutputEntry OBJECT-TYPE
	SYNTAX Pm10010ulhMondownRmonPacketsCounterClientOutputEntry
	MAX-ACCESS not-accessible
	STATUS current
	DESCRIPTION
        "
        Row definition for the pm10010ulhMondownRmonPacketsCounterClientOutput 
        table
        "
	INDEX   { pm10010ulhMondownRmonPacketsCounterClientOutputIndex }
	::= { pm10010ulhMondownRmonPacketsCounterClientOutputTable 1 }


Pm10010ulhMondownRmonPacketsCounterClientOutputEntry ::=
	SEQUENCE {
	pm10010ulhMondownRmonPacketsCounterClientOutputIndex
		INTEGER,
	pm10010ulhMondownRmonPacketsCounterClientOutputValuePortn
		Counter64,
	pm10010ulhMondownRmonPacketsCounterClientOutputErrorPortn
		EkiOnOff,
	pm10010ulhMondownRmonPacketsCounterClientOutputOverloadPortn
		EkiOnOff
	}


pm10010ulhMondownRmonPacketsCounterClientOutputIndex OBJECT-TYPE
	SYNTAX  INTEGER(0..128)
	MAX-ACCESS  read-only
	STATUS current
	DESCRIPTION
        "
        Index definition for the pm10010ulhMondownRmonPacketsCounterClientOutput 
        table
        "
	::= { pm10010ulhMondownRmonPacketsCounterClientOutputEntry 1 }


pm10010ulhMondownRmonPacketsCounterClientOutputValuePortn OBJECT-TYPE
	SYNTAX  Counter64
	MAX-ACCESS read-only
	STATUS current
	DESCRIPTION
        "
        Client Output Packets :This counter 
        is increased each time a packet 
        is transmitted on the client port 
         <Help>  This counter gives the 
        number of packets transmitted on 
        the client port
        "
	::= { pm10010ulhMondownRmonPacketsCounterClientOutputEntry 2 }


pm10010ulhMondownRmonPacketsCounterClientOutputErrorPortn OBJECT-TYPE
	SYNTAX  EkiOnOff
	MAX-ACCESS read-only
	STATUS current
	DESCRIPTION
        "
        Packets Counter Error :This OID 
        when set indicates the Packets
         counter value is invalid on client 
        port
        "
	::= { pm10010ulhMondownRmonPacketsCounterClientOutputEntry 3 }


pm10010ulhMondownRmonPacketsCounterClientOutputOverloadPortn OBJECT-TYPE
	SYNTAX  EkiOnOff
	MAX-ACCESS read-only
	STATUS current
	DESCRIPTION
        "
        Packets Counter Overload :This 
        OID when set indicates a Packets 
        counter overload on client port
        "
	::= { pm10010ulhMondownRmonPacketsCounterClientOutputEntry 4 }


--- *********************************************************
---     TABLE for the pm10010ulhMondownRmonBroadcastCounterClientOutput articles
--- *********************************************************

pm10010ulhMondownRmonBroadcastCounterClientOutputTable OBJECT-TYPE
	SYNTAX  SEQUENCE OF Pm10010ulhMondownRmonBroadcastCounterClientOutputEntry
	MAX-ACCESS not-accessible
	STATUS current
	DESCRIPTION
        "
        List of pm10010ulhMondownRmonBroadcastCounterClientOutput 
        Article
        "
	::= { pm10010ulhMonClientRmonCounter 496 }


pm10010ulhMondownRmonBroadcastCounterClientOutputEntry OBJECT-TYPE
	SYNTAX Pm10010ulhMondownRmonBroadcastCounterClientOutputEntry
	MAX-ACCESS not-accessible
	STATUS current
	DESCRIPTION
        "
        Row definition for the pm10010ulhMondownRmonBroadcastCounterClientOutput 
        table
        "
	INDEX   { pm10010ulhMondownRmonBroadcastCounterClientOutputIndex }
	::= { pm10010ulhMondownRmonBroadcastCounterClientOutputTable 1 }


Pm10010ulhMondownRmonBroadcastCounterClientOutputEntry ::=
	SEQUENCE {
	pm10010ulhMondownRmonBroadcastCounterClientOutputIndex
		INTEGER,
	pm10010ulhMondownRmonBroadcastCounterClientOutputValuePortn
		Counter64,
	pm10010ulhMondownRmonBroadcastCounterClientOutputErrorPortn
		EkiOnOff,
	pm10010ulhMondownRmonBroadcastCounterClientOutputOverloadPortn
		EkiOnOff
	}


pm10010ulhMondownRmonBroadcastCounterClientOutputIndex OBJECT-TYPE
	SYNTAX  INTEGER(0..128)
	MAX-ACCESS  read-only
	STATUS current
	DESCRIPTION
        "
        Index definition for the pm10010ulhMondownRmonBroadcastCounterClientOutput 
        table
        "
	::= { pm10010ulhMondownRmonBroadcastCounterClientOutputEntry 1 }


pm10010ulhMondownRmonBroadcastCounterClientOutputValuePortn OBJECT-TYPE
	SYNTAX  Counter64
	MAX-ACCESS read-only
	STATUS current
	DESCRIPTION
        "
        Client Output Broadcast Packets 
        :This counter is increased each 
        time a broadcast packet is transmitted 
        on the client port  <Help>  This 
        counter gives the number of Broadcast 
        packets transmitted on the client 
        port
        "
	::= { pm10010ulhMondownRmonBroadcastCounterClientOutputEntry 2 }


pm10010ulhMondownRmonBroadcastCounterClientOutputErrorPortn OBJECT-TYPE
	SYNTAX  EkiOnOff
	MAX-ACCESS read-only
	STATUS current
	DESCRIPTION
        "
        Broadcast Counter Error :This
         OID when set indicates the Broadcast 
        counter value is invalid on client 
        port
        "
	::= { pm10010ulhMondownRmonBroadcastCounterClientOutputEntry 3 }


pm10010ulhMondownRmonBroadcastCounterClientOutputOverloadPortn OBJECT-TYPE
	SYNTAX  EkiOnOff
	MAX-ACCESS read-only
	STATUS current
	DESCRIPTION
        "
        Broadcast Counter Overload :This 
        OID when set indicates a Broadcast 
        counter overload on client port
        "
	::= { pm10010ulhMondownRmonBroadcastCounterClientOutputEntry 4 }


--- *********************************************************
---     TABLE for the pm10010ulhMondownRmonMulticastCounterClientOutput articles
--- *********************************************************

pm10010ulhMondownRmonMulticastCounterClientOutputTable OBJECT-TYPE
	SYNTAX  SEQUENCE OF Pm10010ulhMondownRmonMulticastCounterClientOutputEntry
	MAX-ACCESS not-accessible
	STATUS current
	DESCRIPTION
        "
        List of pm10010ulhMondownRmonMulticastCounterClientOutput 
        Article
        "
	::= { pm10010ulhMonClientRmonCounter 528 }


pm10010ulhMondownRmonMulticastCounterClientOutputEntry OBJECT-TYPE
	SYNTAX Pm10010ulhMondownRmonMulticastCounterClientOutputEntry
	MAX-ACCESS not-accessible
	STATUS current
	DESCRIPTION
        "
        Row definition for the pm10010ulhMondownRmonMulticastCounterClientOutput 
        table
        "
	INDEX   { pm10010ulhMondownRmonMulticastCounterClientOutputIndex }
	::= { pm10010ulhMondownRmonMulticastCounterClientOutputTable 1 }


Pm10010ulhMondownRmonMulticastCounterClientOutputEntry ::=
	SEQUENCE {
	pm10010ulhMondownRmonMulticastCounterClientOutputIndex
		INTEGER,
	pm10010ulhMondownRmonMulticastCounterClientOutputValuePortn
		Counter64,
	pm10010ulhMondownRmonMulticastCounterClientOutputErrorPortn
		EkiOnOff,
	pm10010ulhMondownRmonMulticastCounterClientOutputOverloadPortn
		EkiOnOff
	}


pm10010ulhMondownRmonMulticastCounterClientOutputIndex OBJECT-TYPE
	SYNTAX  INTEGER(0..128)
	MAX-ACCESS  read-only
	STATUS current
	DESCRIPTION
        "
        Index definition for the pm10010ulhMondownRmonMulticastCounterClientOutput 
        table
        "
	::= { pm10010ulhMondownRmonMulticastCounterClientOutputEntry 1 }


pm10010ulhMondownRmonMulticastCounterClientOutputValuePortn OBJECT-TYPE
	SYNTAX  Counter64
	MAX-ACCESS read-only
	STATUS current
	DESCRIPTION
        "
        Client Output Multicast Packets 
        :This counter is increased each 
        time a Multicast packet is transmitted 
        on the client port  <Help>  This 
        counter gives the number of Multicast 
        packets transmitted on the client 
        port
        "
	::= { pm10010ulhMondownRmonMulticastCounterClientOutputEntry 2 }


pm10010ulhMondownRmonMulticastCounterClientOutputErrorPortn OBJECT-TYPE
	SYNTAX  EkiOnOff
	MAX-ACCESS read-only
	STATUS current
	DESCRIPTION
        "
        Multicast Counter Error :This
         OID when set indicates the Multicast 
        counter value is invalid on client 
        port
        "
	::= { pm10010ulhMondownRmonMulticastCounterClientOutputEntry 3 }


pm10010ulhMondownRmonMulticastCounterClientOutputOverloadPortn OBJECT-TYPE
	SYNTAX  EkiOnOff
	MAX-ACCESS read-only
	STATUS current
	DESCRIPTION
        "
        Multicast Counter Overload :This 
        OID when set indicates a Multicast 
        counter overload on client port
        "
	::= { pm10010ulhMondownRmonMulticastCounterClientOutputEntry 4 }


--- *********************************************************
---     TABLE for the pm10010ulhMondownRmonPauseFrameCounterClientOutput articles
--- *********************************************************

pm10010ulhMondownRmonPauseFrameCounterClientOutputTable OBJECT-TYPE
	SYNTAX  SEQUENCE OF Pm10010ulhMondownRmonPauseFrameCounterClientOutputEntry
	MAX-ACCESS not-accessible
	STATUS current
	DESCRIPTION
        "
        List of pm10010ulhMondownRmonPauseFrameCounterClientOutput 
        Article
        "
	::= { pm10010ulhMonClientRmonCounter 560 }


pm10010ulhMondownRmonPauseFrameCounterClientOutputEntry OBJECT-TYPE
	SYNTAX Pm10010ulhMondownRmonPauseFrameCounterClientOutputEntry
	MAX-ACCESS not-accessible
	STATUS current
	DESCRIPTION
        "
        Row definition for the pm10010ulhMondownRmonPauseFrameCounterClientOutput 
        table
        "
	INDEX   { pm10010ulhMondownRmonPauseFrameCounterClientOutputIndex }
	::= { pm10010ulhMondownRmonPauseFrameCounterClientOutputTable 1 }


Pm10010ulhMondownRmonPauseFrameCounterClientOutputEntry ::=
	SEQUENCE {
	pm10010ulhMondownRmonPauseFrameCounterClientOutputIndex
		INTEGER,
	pm10010ulhMondownRmonPauseFrameCounterClientOutputValuePortn
		Counter64,
	pm10010ulhMondownRmonPauseFrameCounterClientOutputErrorPortn
		EkiOnOff,
	pm10010ulhMondownRmonPauseFrameCounterClientOutputOverloadPortn
		EkiOnOff
	}


pm10010ulhMondownRmonPauseFrameCounterClientOutputIndex OBJECT-TYPE
	SYNTAX  INTEGER(0..128)
	MAX-ACCESS  read-only
	STATUS current
	DESCRIPTION
        "
        Index definition for the pm10010ulhMondownRmonPauseFrameCounterClientOutput 
        table
        "
	::= { pm10010ulhMondownRmonPauseFrameCounterClientOutputEntry 1 }


pm10010ulhMondownRmonPauseFrameCounterClientOutputValuePortn OBJECT-TYPE
	SYNTAX  Counter64
	MAX-ACCESS read-only
	STATUS current
	DESCRIPTION
        "
        Client Output Pause Frames :This 
        counter is increased each time
         a Pause frame is transmitted on 
        the client port  <Help>  This counter 
        gives the number of Pause frames 
        transmitted on the client port
        "
	::= { pm10010ulhMondownRmonPauseFrameCounterClientOutputEntry 2 }


pm10010ulhMondownRmonPauseFrameCounterClientOutputErrorPortn OBJECT-TYPE
	SYNTAX  EkiOnOff
	MAX-ACCESS read-only
	STATUS current
	DESCRIPTION
        "
        Pause Counter Error :This OID
         when set indicates the Pause counter 
        value is invalid on client port
        "
	::= { pm10010ulhMondownRmonPauseFrameCounterClientOutputEntry 3 }


pm10010ulhMondownRmonPauseFrameCounterClientOutputOverloadPortn OBJECT-TYPE
	SYNTAX  EkiOnOff
	MAX-ACCESS read-only
	STATUS current
	DESCRIPTION
        "
        Pause Counter Overload :This OID 
        when set indicates a Pause counter 
        overload on client port
        "
	::= { pm10010ulhMondownRmonPauseFrameCounterClientOutputEntry 4 }


--- *********************************************************
---     TABLE for the pm10010ulhMondownRmonUnicastCounterClientOutput articles
--- *********************************************************

pm10010ulhMondownRmonUnicastCounterClientOutputTable OBJECT-TYPE
	SYNTAX  SEQUENCE OF Pm10010ulhMondownRmonUnicastCounterClientOutputEntry
	MAX-ACCESS not-accessible
	STATUS current
	DESCRIPTION
        "
        List of pm10010ulhMondownRmonUnicastCounterClientOutput 
        Article
        "
	::= { pm10010ulhMonClientRmonCounter 688 }


pm10010ulhMondownRmonUnicastCounterClientOutputEntry OBJECT-TYPE
	SYNTAX Pm10010ulhMondownRmonUnicastCounterClientOutputEntry
	MAX-ACCESS not-accessible
	STATUS current
	DESCRIPTION
        "
        Row definition for the pm10010ulhMondownRmonUnicastCounterClientOutput 
        table
        "
	INDEX   { pm10010ulhMondownRmonUnicastCounterClientOutputIndex }
	::= { pm10010ulhMondownRmonUnicastCounterClientOutputTable 1 }


Pm10010ulhMondownRmonUnicastCounterClientOutputEntry ::=
	SEQUENCE {
	pm10010ulhMondownRmonUnicastCounterClientOutputIndex
		INTEGER,
	pm10010ulhMondownRmonUnicastCounterClientOutputValuePortn
		Counter64,
	pm10010ulhMondownRmonUnicastCounterClientOutputErrorPortn
		EkiOnOff,
	pm10010ulhMondownRmonUnicastCounterClientOutputOverloadPortn
		EkiOnOff
	}


pm10010ulhMondownRmonUnicastCounterClientOutputIndex OBJECT-TYPE
	SYNTAX  INTEGER(0..128)
	MAX-ACCESS  read-only
	STATUS current
	DESCRIPTION
        "
        Index definition for the pm10010ulhMondownRmonUnicastCounterClientOutput 
        table
        "
	::= { pm10010ulhMondownRmonUnicastCounterClientOutputEntry 1 }


pm10010ulhMondownRmonUnicastCounterClientOutputValuePortn OBJECT-TYPE
	SYNTAX  Counter64
	MAX-ACCESS read-only
	STATUS current
	DESCRIPTION
        "
        Client Output Unicast Packets
         :This counter is increased each 
        time a Unicast packet is transmitted 
        on the client port  <Help>  This 
        counter gives the number of Unicast 
        packets transmitted on the client 
        port
        "
	::= { pm10010ulhMondownRmonUnicastCounterClientOutputEntry 2 }


pm10010ulhMondownRmonUnicastCounterClientOutputErrorPortn OBJECT-TYPE
	SYNTAX  EkiOnOff
	MAX-ACCESS read-only
	STATUS current
	DESCRIPTION
        "
        Unicast Counter Error :This OID 
        when set indicates the Unicast
         counter value is invalid on client 
        port
        "
	::= { pm10010ulhMondownRmonUnicastCounterClientOutputEntry 3 }


pm10010ulhMondownRmonUnicastCounterClientOutputOverloadPortn OBJECT-TYPE
	SYNTAX  EkiOnOff
	MAX-ACCESS read-only
	STATUS current
	DESCRIPTION
        "
        Unicast Counter Overload :This 
        OID when set indicates a Unicast 
        counter overload on client port
        "
	::= { pm10010ulhMondownRmonUnicastCounterClientOutputEntry 4 }


--- *********************************************************
---     TABLE for the pm10010ulhMondownRmonNonunicastCounterClientOutput articles
--- *********************************************************

pm10010ulhMondownRmonNonunicastCounterClientOutputTable OBJECT-TYPE
	SYNTAX  SEQUENCE OF Pm10010ulhMondownRmonNonunicastCounterClientOutputEntry
	MAX-ACCESS not-accessible
	STATUS current
	DESCRIPTION
        "
        List of pm10010ulhMondownRmonNonunicastCounterClientOutput 
        Article
        "
	::= { pm10010ulhMonClientRmonCounter 720 }


pm10010ulhMondownRmonNonunicastCounterClientOutputEntry OBJECT-TYPE
	SYNTAX Pm10010ulhMondownRmonNonunicastCounterClientOutputEntry
	MAX-ACCESS not-accessible
	STATUS current
	DESCRIPTION
        "
        Row definition for the pm10010ulhMondownRmonNonunicastCounterClientOutput 
        table
        "
	INDEX   { pm10010ulhMondownRmonNonunicastCounterClientOutputIndex }
	::= { pm10010ulhMondownRmonNonunicastCounterClientOutputTable 1 }


Pm10010ulhMondownRmonNonunicastCounterClientOutputEntry ::=
	SEQUENCE {
	pm10010ulhMondownRmonNonunicastCounterClientOutputIndex
		INTEGER,
	pm10010ulhMondownRmonNonunicastCounterClientOutputValuePortn
		Counter64,
	pm10010ulhMondownRmonNonunicastCounterClientOutputErrorPortn
		EkiOnOff,
	pm10010ulhMondownRmonNonunicastCounterClientOutputOverloadPortn
		EkiOnOff
	}


pm10010ulhMondownRmonNonunicastCounterClientOutputIndex OBJECT-TYPE
	SYNTAX  INTEGER(0..128)
	MAX-ACCESS  read-only
	STATUS current
	DESCRIPTION
        "
        Index definition for the pm10010ulhMondownRmonNonunicastCounterClientOutput 
        table
        "
	::= { pm10010ulhMondownRmonNonunicastCounterClientOutputEntry 1 }


pm10010ulhMondownRmonNonunicastCounterClientOutputValuePortn OBJECT-TYPE
	SYNTAX  Counter64
	MAX-ACCESS read-only
	STATUS current
	DESCRIPTION
        "
        Client Output Non Unicast Packets 
        :This counter is increased each 
        time a Non-Unicast packet is transmitted 
        on the client port  <Help>  This 
        counter gives the number of Non-Unicast 
        packets transmitted on the client 
        port
        "
	::= { pm10010ulhMondownRmonNonunicastCounterClientOutputEntry 2 }


pm10010ulhMondownRmonNonunicastCounterClientOutputErrorPortn OBJECT-TYPE
	SYNTAX  EkiOnOff
	MAX-ACCESS read-only
	STATUS current
	DESCRIPTION
        "
        Non Unicast Counter Error :This 
        OID when set indicates the Non-Unicast 
        counter value is invalid on client 
        port
        "
	::= { pm10010ulhMondownRmonNonunicastCounterClientOutputEntry 3 }


pm10010ulhMondownRmonNonunicastCounterClientOutputOverloadPortn OBJECT-TYPE
	SYNTAX  EkiOnOff
	MAX-ACCESS read-only
	STATUS current
	DESCRIPTION
        "
        Non Unicast Counter Overload :This 
        OID when set indicates a Non-Unicast 
        counter overload on client port
        "
	::= { pm10010ulhMondownRmonNonunicastCounterClientOutputEntry 4 }







--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm10010ulhMesrsynth0 OBJECT-TYPE
	  SYNTAX EkiMeasureType
	  MAX-ACCESS read-only
	  STATUS deprecated
	  DESCRIPTION
        "
        Not Used :
        "
	  ::= { pm10010ulhMesrOther 0 }



pm10010ulhMesrsynth1 OBJECT-TYPE
	  SYNTAX EkiMeasureType
	  MAX-ACCESS read-only
	  STATUS deprecated
	  DESCRIPTION
        "
        Not Used :
        "
	  ::= { pm10010ulhMesrOther 1 }



--- *****************************************************
---     LEAF for the pmIntervalNumber article
--- *****************************************************

pm10010ulhMesrpmIntervalNumber OBJECT-TYPE
	  SYNTAX Unsigned32 (0..65535)
	  MAX-ACCESS read-only
	  STATUS current
	  DESCRIPTION
        "
        PM Interval Counter :
        "
	  ::= { pm10010ulhMesrOther 7 }



--- *****************************************************
---     LEAF for the clientCfpTemp article
--- *****************************************************

pm10010ulhMesrclientCfpTemp OBJECT-TYPE
	  SYNTAX Unsigned32 (0..65535)
	  MAX-ACCESS read-only
	  STATUS current
	  DESCRIPTION
        "
        Client Trscv Temperature :This 
        OID gives the temperature value 
        of the Client Transceiver, read 
        from the DDM (Digital Diagnostic 
        Monitoring) (Temperature = AV_S16/256) 
        (Unit = C) <Help> This Measure
         gives the temperature value of 
        the Client Transceiver
        "
	  ::= { pm10010ulhMesrClient 8 }



--- *****************************************************
---     LEAF for the clientCfp3v3Voltage article
--- *****************************************************

pm10010ulhMesrclientCfp3v3Voltage OBJECT-TYPE
	  SYNTAX Unsigned32 (0..65535)
	  MAX-ACCESS read-only
	  STATUS current
	  DESCRIPTION
        "
        Client Trscv Voltage :This OID 
        gives the 3V3 voltage value of
         the Client Transceiver, read from 
        the DDM (Digital Diagnostic Monitoring) 
         (Voltage = AV_U16/10000) (Unit 
        = V) <Help> This Measure gives
         the 3V3 voltage value of the Client 
        Transceiver
        "
	  ::= { pm10010ulhMesrClient 9 }



--- *****************************************************
---     LEAF for the clientSoaBiasCurrent article
--- *****************************************************

pm10010ulhMesrclientSoaBiasCurrent OBJECT-TYPE
	  SYNTAX Unsigned32 (0..65535)
	  MAX-ACCESS read-only
	  STATUS current
	  DESCRIPTION
        "
        Client Trscv SOA Bias :This OID 
        gives the SOA bias value of the 
        Client Transceiver, read from the 
        DDM (Digital Diagnostic Monitoring) 
         (Bias = AV_U16/500) (Unit = mA) 
        <Help> This Measure gives the SOA 
        bias value of the Client Transceiver
        "
	  ::= { pm10010ulhMesrClient 10 }



--- *****************************************************
---     LEAF for the lineMsaTemp article
--- *****************************************************

pm10010ulhMesrlineMsaTemp OBJECT-TYPE
	  SYNTAX Unsigned32 (0..65535)
	  MAX-ACCESS read-only
	  STATUS current
	  DESCRIPTION
        "
        Line Trscv Temperature :This OID 
        gives the temperature value of
         the Line Transceiver, read from 
        the DDM (Digital Diagnostic Monitoring) 
         (Temperature = AV_S16/256) (Unit 
        = C) <Help> This Measure gives
         the temperature value of the Line 
        Transceiver.This temperature must 
        remain below 95 C for proper operation
        "
	  ::= { pm10010ulhMesrLine 12 }



--- *****************************************************
---     LEAF for the lineMsa3v3Voltage article
--- *****************************************************

pm10010ulhMesrlineMsa3v3Voltage OBJECT-TYPE
	  SYNTAX Unsigned32 (0..65535)
	  MAX-ACCESS read-only
	  STATUS current
	  DESCRIPTION
        "
        Line Trscv Voltage :This OID gives 
        the 3V3 voltage value of the Line 
        Transceiver, read from the DDM
         (Digital Diagnostic Monitoring) 
        (Voltage = AV_U16/10000) (Unit
         = V) <Help> This Measure gives 
        the 3V3 voltage value of the Line 
        Transceiver
        "
	  ::= { pm10010ulhMesrLine 13 }



--- *****************************************************
---     LEAF for the lineSoaBiasCurrent article
--- *****************************************************

pm10010ulhMesrlineSoaBiasCurrent OBJECT-TYPE
	  SYNTAX Unsigned32 (0..65535)
	  MAX-ACCESS read-only
	  STATUS current
	  DESCRIPTION
        "
        Line Trscv SOA Bias :This OID
         gives the SOA bias value of the 
        Line Transceiver,read from the
         DDM (Digital Diagnostic Monitoring) 
         (Bias = AV_U16/500) (Unit = mA) 
        <Help> This Measure gives the SOA 
        bias value of the Line Transceiver
        "
	  ::= { pm10010ulhMesrLine 14 }



--- *********************************************************
---     TABLE for the pm10010ulhMesrclientNetTxTemp articles
--- *********************************************************

pm10010ulhMesrclientNetTxTempTable OBJECT-TYPE
	SYNTAX  SEQUENCE OF Pm10010ulhMesrclientNetTxTempEntry
	MAX-ACCESS not-accessible
	STATUS current
	DESCRIPTION
        "
        List of pm10010ulhMesrclientNetTxTemp 
        Article
        "
	::= { pm10010ulhMesrClient 16 }


pm10010ulhMesrclientNetTxTempEntry OBJECT-TYPE
	SYNTAX Pm10010ulhMesrclientNetTxTempEntry
	MAX-ACCESS not-accessible
	STATUS current
	DESCRIPTION
        "
        Row definition for the pm10010ulhMesrclientNetTxTemp 
        table
        "
	INDEX   { pm10010ulhMesrclientNetTxTempIndex }
	::= { pm10010ulhMesrclientNetTxTempTable 1 }


Pm10010ulhMesrclientNetTxTempEntry ::=
	SEQUENCE {
	pm10010ulhMesrclientNetTxTempIndex
		INTEGER,
	pm10010ulhMesrclientNetTxTempPortn
		INTEGER 
	}


pm10010ulhMesrclientNetTxTempIndex OBJECT-TYPE
	SYNTAX  INTEGER(0..128)
	MAX-ACCESS  read-only
	STATUS current
	DESCRIPTION
        "
        Index definition for the pm10010ulhMesrclientNetTxTemp 
        table
        "
	::= { pm10010ulhMesrclientNetTxTempEntry 1 }


pm10010ulhMesrclientNetTxTempPortn OBJECT-TYPE
	SYNTAX  INTEGER (0..65535)
	MAX-ACCESS read-only
	STATUS current
	DESCRIPTION
        "
        Client Trscv Temperature :This 
        OID gives the Laser temperature 
        value of the Client Transceiver, 
        read from the DDM (Digital Diagnostic 
        Monitoring) (Temperature = AV_S16/256) 
        (Unit = C) <Help> This Measure
         gives the Laser temperature value 
        of the Client Transceiver
        "
	::= { pm10010ulhMesrclientNetTxTempEntry 2 }


--- *********************************************************
---     TABLE for the pm10010ulhMesrclientNetTxBias articles
--- *********************************************************

pm10010ulhMesrclientNetTxBiasTable OBJECT-TYPE
	SYNTAX  SEQUENCE OF Pm10010ulhMesrclientNetTxBiasEntry
	MAX-ACCESS not-accessible
	STATUS current
	DESCRIPTION
        "
        List of pm10010ulhMesrclientNetTxBias 
        Article
        "
	::= { pm10010ulhMesrClient 48 }


pm10010ulhMesrclientNetTxBiasEntry OBJECT-TYPE
	SYNTAX Pm10010ulhMesrclientNetTxBiasEntry
	MAX-ACCESS not-accessible
	STATUS current
	DESCRIPTION
        "
        Row definition for the pm10010ulhMesrclientNetTxBias 
        table
        "
	INDEX   { pm10010ulhMesrclientNetTxBiasIndex }
	::= { pm10010ulhMesrclientNetTxBiasTable 1 }


Pm10010ulhMesrclientNetTxBiasEntry ::=
	SEQUENCE {
	pm10010ulhMesrclientNetTxBiasIndex
		INTEGER,
	pm10010ulhMesrclientNetTxBiasPortn
		INTEGER 
	}


pm10010ulhMesrclientNetTxBiasIndex OBJECT-TYPE
	SYNTAX  INTEGER(0..128)
	MAX-ACCESS  read-only
	STATUS current
	DESCRIPTION
        "
        Index definition for the pm10010ulhMesrclientNetTxBias 
        table
        "
	::= { pm10010ulhMesrclientNetTxBiasEntry 1 }


pm10010ulhMesrclientNetTxBiasPortn OBJECT-TYPE
	SYNTAX  INTEGER (0..65535)
	MAX-ACCESS read-only
	STATUS current
	DESCRIPTION
        "
        Client Trscv Laser Bias :This
         OID gives the Laser bias value 
        of the Client Transceiver, read 
        from the DDM (Digital Diagnostic 
        Monitoring) (Bias = AV_U16/500) 
        (Unit = mA) <Help> This Measure 
        gives the Laser bias value of the 
        Client Transceiver
        "
	::= { pm10010ulhMesrclientNetTxBiasEntry 2 }


--- *********************************************************
---     TABLE for the pm10010ulhMesrclientNetTxPwr articles
--- *********************************************************

pm10010ulhMesrclientNetTxPwrTable OBJECT-TYPE
	SYNTAX  SEQUENCE OF Pm10010ulhMesrclientNetTxPwrEntry
	MAX-ACCESS not-accessible
	STATUS current
	DESCRIPTION
        "
        List of pm10010ulhMesrclientNetTxPwr 
        Article
        "
	::= { pm10010ulhMesrClient 80 }


pm10010ulhMesrclientNetTxPwrEntry OBJECT-TYPE
	SYNTAX Pm10010ulhMesrclientNetTxPwrEntry
	MAX-ACCESS not-accessible
	STATUS current
	DESCRIPTION
        "
        Row definition for the pm10010ulhMesrclientNetTxPwr 
        table
        "
	INDEX   { pm10010ulhMesrclientNetTxPwrIndex }
	::= { pm10010ulhMesrclientNetTxPwrTable 1 }


Pm10010ulhMesrclientNetTxPwrEntry ::=
	SEQUENCE {
	pm10010ulhMesrclientNetTxPwrIndex
		INTEGER,
	pm10010ulhMesrclientNetTxPwrPortn
		INTEGER 
	}


pm10010ulhMesrclientNetTxPwrIndex OBJECT-TYPE
	SYNTAX  INTEGER(0..128)
	MAX-ACCESS  read-only
	STATUS current
	DESCRIPTION
        "
        Index definition for the pm10010ulhMesrclientNetTxPwr 
        table
        "
	::= { pm10010ulhMesrclientNetTxPwrEntry 1 }


pm10010ulhMesrclientNetTxPwrPortn OBJECT-TYPE
	SYNTAX  INTEGER (0..65535)
	MAX-ACCESS read-only
	STATUS current
	DESCRIPTION
        "
        Client Trscv Tx Power :This OID 
        gives the transmit power value
         of the Client Transceiver, read 
        from the DDM (Digital Diagnostic 
        Monitoring) (Power = 10*log(AV_U16)-40) 
        (Unit = dBm) <Help> This Measure 
        gives the transmit power value
         of the Client Transceiver
        "
	::= { pm10010ulhMesrclientNetTxPwrEntry 2 }


--- *********************************************************
---     TABLE for the pm10010ulhMesrclientNetRxPwr articles
--- *********************************************************

pm10010ulhMesrclientNetRxPwrTable OBJECT-TYPE
	SYNTAX  SEQUENCE OF Pm10010ulhMesrclientNetRxPwrEntry
	MAX-ACCESS not-accessible
	STATUS current
	DESCRIPTION
        "
        List of pm10010ulhMesrclientNetRxPwr 
        Article
        "
	::= { pm10010ulhMesrClient 112 }


pm10010ulhMesrclientNetRxPwrEntry OBJECT-TYPE
	SYNTAX Pm10010ulhMesrclientNetRxPwrEntry
	MAX-ACCESS not-accessible
	STATUS current
	DESCRIPTION
        "
        Row definition for the pm10010ulhMesrclientNetRxPwr 
        table
        "
	INDEX   { pm10010ulhMesrclientNetRxPwrIndex }
	::= { pm10010ulhMesrclientNetRxPwrTable 1 }


Pm10010ulhMesrclientNetRxPwrEntry ::=
	SEQUENCE {
	pm10010ulhMesrclientNetRxPwrIndex
		INTEGER,
	pm10010ulhMesrclientNetRxPwrPortn
		INTEGER 
	}


pm10010ulhMesrclientNetRxPwrIndex OBJECT-TYPE
	SYNTAX  INTEGER(0..128)
	MAX-ACCESS  read-only
	STATUS current
	DESCRIPTION
        "
        Index definition for the pm10010ulhMesrclientNetRxPwr 
        table
        "
	::= { pm10010ulhMesrclientNetRxPwrEntry 1 }


pm10010ulhMesrclientNetRxPwrPortn OBJECT-TYPE
	SYNTAX  INTEGER (0..65535)
	MAX-ACCESS read-only
	STATUS current
	DESCRIPTION
        "
        Client Trscv Rx Power :This OID 
        gives the receive power value of 
        the Client Transceiver, read in 
        the DDM (Digital Diagnostic Monitoring) 
        (Power = 10*log(AV_U16)-40) (Unit 
        = dBm) <Help> This Measure gives 
        the receive power value of the
         Client Transceiver
        "
	::= { pm10010ulhMesrclientNetRxPwrEntry 2 }


--- *********************************************************
---     TABLE for the pm10010ulhMesrlineNetTxLaserOutputPwr articles
--- *********************************************************

pm10010ulhMesrlineNetTxLaserOutputPwrTable OBJECT-TYPE
	SYNTAX  SEQUENCE OF Pm10010ulhMesrlineNetTxLaserOutputPwrEntry
	MAX-ACCESS not-accessible
	STATUS current
	DESCRIPTION
        "
        List of pm10010ulhMesrlineNetTxLaserOutputPwr 
        Article
        "
	::= { pm10010ulhMesrLine 144 }


pm10010ulhMesrlineNetTxLaserOutputPwrEntry OBJECT-TYPE
	SYNTAX Pm10010ulhMesrlineNetTxLaserOutputPwrEntry
	MAX-ACCESS not-accessible
	STATUS current
	DESCRIPTION
        "
        Row definition for the pm10010ulhMesrlineNetTxLaserOutputPwr 
        table
        "
	INDEX   { pm10010ulhMesrlineNetTxLaserOutputPwrIndex }
	::= { pm10010ulhMesrlineNetTxLaserOutputPwrTable 1 }


Pm10010ulhMesrlineNetTxLaserOutputPwrEntry ::=
	SEQUENCE {
	pm10010ulhMesrlineNetTxLaserOutputPwrIndex
		INTEGER,
	pm10010ulhMesrlineNetTxLaserOutputPwrPortn
		INTEGER 
	}


pm10010ulhMesrlineNetTxLaserOutputPwrIndex OBJECT-TYPE
	SYNTAX  INTEGER(0..128)
	MAX-ACCESS  read-only
	STATUS current
	DESCRIPTION
        "
        Index definition for the pm10010ulhMesrlineNetTxLaserOutputPwr 
        table
        "
	::= { pm10010ulhMesrlineNetTxLaserOutputPwrEntry 1 }


pm10010ulhMesrlineNetTxLaserOutputPwrPortn OBJECT-TYPE
	SYNTAX  INTEGER (0..65535)
	MAX-ACCESS read-only
	STATUS current
	DESCRIPTION
        "
        Current Line Trscv Tx Power :This 
        OID gives the Tx Laser transmit 
        power value of the Line Transceiver, 
        read in the DDM (Digital Diagnostic 
        Monitoring) (Power = AV_S16/100) 
        (Unit = dBm) <Help> This Measure 
        gives the Tx Laser transmit power 
        value of the Line Transceiver
        "
	::= { pm10010ulhMesrlineNetTxLaserOutputPwrEntry 2 }


--- *********************************************************
---     TABLE for the pm10010ulhMesrlineNetTxLaserTemp articles
--- *********************************************************

pm10010ulhMesrlineNetTxLaserTempTable OBJECT-TYPE
	SYNTAX  SEQUENCE OF Pm10010ulhMesrlineNetTxLaserTempEntry
	MAX-ACCESS not-accessible
	STATUS current
	DESCRIPTION
        "
        List of pm10010ulhMesrlineNetTxLaserTemp 
        Article
        "
	::= { pm10010ulhMesrLine 148 }


pm10010ulhMesrlineNetTxLaserTempEntry OBJECT-TYPE
	SYNTAX Pm10010ulhMesrlineNetTxLaserTempEntry
	MAX-ACCESS not-accessible
	STATUS current
	DESCRIPTION
        "
        Row definition for the pm10010ulhMesrlineNetTxLaserTemp 
        table
        "
	INDEX   { pm10010ulhMesrlineNetTxLaserTempIndex }
	::= { pm10010ulhMesrlineNetTxLaserTempTable 1 }


Pm10010ulhMesrlineNetTxLaserTempEntry ::=
	SEQUENCE {
	pm10010ulhMesrlineNetTxLaserTempIndex
		INTEGER,
	pm10010ulhMesrlineNetTxLaserTempPortn
		INTEGER 
	}


pm10010ulhMesrlineNetTxLaserTempIndex OBJECT-TYPE
	SYNTAX  INTEGER(0..128)
	MAX-ACCESS  read-only
	STATUS current
	DESCRIPTION
        "
        Index definition for the pm10010ulhMesrlineNetTxLaserTemp 
        table
        "
	::= { pm10010ulhMesrlineNetTxLaserTempEntry 1 }


pm10010ulhMesrlineNetTxLaserTempPortn OBJECT-TYPE
	SYNTAX  INTEGER (0..65535)
	MAX-ACCESS read-only
	STATUS current
	DESCRIPTION
        "
        Current Line Trscv Tx Laser Temperature 
        :This OID gives the Tx Laser Temperature 
        value of the Line Transceiver,
         read from the DDM (Digital Diagnostic 
        Monitoring) (Temperature = AV_S16/256) 
        (Unit = C) <Help> This Measure
         gives the Tx Laser Temperature 
        value of the Line Transceiver
        "
	::= { pm10010ulhMesrlineNetTxLaserTempEntry 2 }


--- *********************************************************
---     TABLE for the pm10010ulhMesrlineNetTxBiasCurrent articles
--- *********************************************************

pm10010ulhMesrlineNetTxBiasCurrentTable OBJECT-TYPE
	SYNTAX  SEQUENCE OF Pm10010ulhMesrlineNetTxBiasCurrentEntry
	MAX-ACCESS not-accessible
	STATUS current
	DESCRIPTION
        "
        List of pm10010ulhMesrlineNetTxBiasCurrent 
        Article
        "
	::= { pm10010ulhMesrLine 152 }


pm10010ulhMesrlineNetTxBiasCurrentEntry OBJECT-TYPE
	SYNTAX Pm10010ulhMesrlineNetTxBiasCurrentEntry
	MAX-ACCESS not-accessible
	STATUS current
	DESCRIPTION
        "
        Row definition for the pm10010ulhMesrlineNetTxBiasCurrent 
        table
        "
	INDEX   { pm10010ulhMesrlineNetTxBiasCurrentIndex }
	::= { pm10010ulhMesrlineNetTxBiasCurrentTable 1 }


Pm10010ulhMesrlineNetTxBiasCurrentEntry ::=
	SEQUENCE {
	pm10010ulhMesrlineNetTxBiasCurrentIndex
		INTEGER,
	pm10010ulhMesrlineNetTxBiasCurrentPortn
		INTEGER 
	}


pm10010ulhMesrlineNetTxBiasCurrentIndex OBJECT-TYPE
	SYNTAX  INTEGER(0..128)
	MAX-ACCESS  read-only
	STATUS current
	DESCRIPTION
        "
        Index definition for the pm10010ulhMesrlineNetTxBiasCurrent 
        table
        "
	::= { pm10010ulhMesrlineNetTxBiasCurrentEntry 1 }


pm10010ulhMesrlineNetTxBiasCurrentPortn OBJECT-TYPE
	SYNTAX  INTEGER (0..65535)
	MAX-ACCESS read-only
	STATUS current
	DESCRIPTION
        "
        Current Line Trscv Tx Laser Bias 
        :This OID gives the Tx Laser Bias 
        value of the Line Transceiver,
         read from the DDM (Digital Diagnostic 
        Monitoring) (Bias = AV_S16/10)
         (Unit = mA) <Help> This Measure 
        gives the Tx Laser Bias value of 
        the Line Transceiver
        "
	::= { pm10010ulhMesrlineNetTxBiasCurrentEntry 2 }


--- *********************************************************
---     TABLE for the pm10010ulhMesrlineNetRxInputPwr articles
--- *********************************************************

pm10010ulhMesrlineNetRxInputPwrTable OBJECT-TYPE
	SYNTAX  SEQUENCE OF Pm10010ulhMesrlineNetRxInputPwrEntry
	MAX-ACCESS not-accessible
	STATUS current
	DESCRIPTION
        "
        List of pm10010ulhMesrlineNetRxInputPwr 
        Article
        "
	::= { pm10010ulhMesrLine 156 }


pm10010ulhMesrlineNetRxInputPwrEntry OBJECT-TYPE
	SYNTAX Pm10010ulhMesrlineNetRxInputPwrEntry
	MAX-ACCESS not-accessible
	STATUS current
	DESCRIPTION
        "
        Row definition for the pm10010ulhMesrlineNetRxInputPwr 
        table
        "
	INDEX   { pm10010ulhMesrlineNetRxInputPwrIndex }
	::= { pm10010ulhMesrlineNetRxInputPwrTable 1 }


Pm10010ulhMesrlineNetRxInputPwrEntry ::=
	SEQUENCE {
	pm10010ulhMesrlineNetRxInputPwrIndex
		INTEGER,
	pm10010ulhMesrlineNetRxInputPwrPortn
		INTEGER 
	}


pm10010ulhMesrlineNetRxInputPwrIndex OBJECT-TYPE
	SYNTAX  INTEGER(0..128)
	MAX-ACCESS  read-only
	STATUS current
	DESCRIPTION
        "
        Index definition for the pm10010ulhMesrlineNetRxInputPwr 
        table
        "
	::= { pm10010ulhMesrlineNetRxInputPwrEntry 1 }


pm10010ulhMesrlineNetRxInputPwrPortn OBJECT-TYPE
	SYNTAX  INTEGER (0..65535)
	MAX-ACCESS read-only
	STATUS current
	DESCRIPTION
        "
        Current Line Trscv Rx Power :This 
        OID gives the Receive power value 
        of the Line Transceiver, read in 
        the DDM (Digital Diagnostic Monitoring) 
        (Power = AV_S16/100) (Unit = dBm) 
        <Help> This Measure gives the Receive 
        power value of the Line Transceiver
        "
	::= { pm10010ulhMesrlineNetRxInputPwrEntry 2 }


--- *********************************************************
---     TABLE for the pm10010ulhMesrlineResidualChromaticDisp articles
--- *********************************************************

pm10010ulhMesrlineResidualChromaticDispTable OBJECT-TYPE
	SYNTAX  SEQUENCE OF Pm10010ulhMesrlineResidualChromaticDispEntry
	MAX-ACCESS not-accessible
	STATUS current
	DESCRIPTION
        "
        List of pm10010ulhMesrlineResidualChromaticDisp 
        Article
        "
	::= { pm10010ulhMesrLine 160 }


pm10010ulhMesrlineResidualChromaticDispEntry OBJECT-TYPE
	SYNTAX Pm10010ulhMesrlineResidualChromaticDispEntry
	MAX-ACCESS not-accessible
	STATUS current
	DESCRIPTION
        "
        Row definition for the pm10010ulhMesrlineResidualChromaticDisp 
        table
        "
	INDEX   { pm10010ulhMesrlineResidualChromaticDispIndex }
	::= { pm10010ulhMesrlineResidualChromaticDispTable 1 }


Pm10010ulhMesrlineResidualChromaticDispEntry ::=
	SEQUENCE {
	pm10010ulhMesrlineResidualChromaticDispIndex
		INTEGER,
	pm10010ulhMesrlineResidualChromaticDispPortn
		INTEGER 
	}


pm10010ulhMesrlineResidualChromaticDispIndex OBJECT-TYPE
	SYNTAX  INTEGER(0..128)
	MAX-ACCESS  read-only
	STATUS current
	DESCRIPTION
        "
        Index definition for the pm10010ulhMesrlineResidualChromaticDisp 
        table
        "
	::= { pm10010ulhMesrlineResidualChromaticDispEntry 1 }


pm10010ulhMesrlineResidualChromaticDispPortn OBJECT-TYPE
	SYNTAX  INTEGER (0..65535)
	MAX-ACCESS read-only
	STATUS current
	DESCRIPTION
        "
        Current Residual Chromatic Dispersion 
        :This OID gives the current Residual 
        Chromatic Dispersion on the Line 
        interface (Dispersion = AV_S16*(-2)) 
          (Unit = ps/nm)<Help> This measure 
        gives the current Residual Chromatic 
        Dispersion on the Line interface.
        "
	::= { pm10010ulhMesrlineResidualChromaticDispEntry 2 }


--- *********************************************************
---     TABLE for the pm10010ulhMesrlineDiffGroupDelay articles
--- *********************************************************

pm10010ulhMesrlineDiffGroupDelayTable OBJECT-TYPE
	SYNTAX  SEQUENCE OF Pm10010ulhMesrlineDiffGroupDelayEntry
	MAX-ACCESS not-accessible
	STATUS current
	DESCRIPTION
        "
        List of pm10010ulhMesrlineDiffGroupDelay 
        Article
        "
	::= { pm10010ulhMesrLine 164 }


pm10010ulhMesrlineDiffGroupDelayEntry OBJECT-TYPE
	SYNTAX Pm10010ulhMesrlineDiffGroupDelayEntry
	MAX-ACCESS not-accessible
	STATUS current
	DESCRIPTION
        "
        Row definition for the pm10010ulhMesrlineDiffGroupDelay 
        table
        "
	INDEX   { pm10010ulhMesrlineDiffGroupDelayIndex }
	::= { pm10010ulhMesrlineDiffGroupDelayTable 1 }


Pm10010ulhMesrlineDiffGroupDelayEntry ::=
	SEQUENCE {
	pm10010ulhMesrlineDiffGroupDelayIndex
		INTEGER,
	pm10010ulhMesrlineDiffGroupDelayPortn
		INTEGER 
	}


pm10010ulhMesrlineDiffGroupDelayIndex OBJECT-TYPE
	SYNTAX  INTEGER(0..128)
	MAX-ACCESS  read-only
	STATUS current
	DESCRIPTION
        "
        Index definition for the pm10010ulhMesrlineDiffGroupDelay 
        table
        "
	::= { pm10010ulhMesrlineDiffGroupDelayEntry 1 }


pm10010ulhMesrlineDiffGroupDelayPortn OBJECT-TYPE
	SYNTAX  INTEGER (0..65535)
	MAX-ACCESS read-only
	STATUS current
	DESCRIPTION
        "
        Current Differential Group Delay 
        :This OID gives the current Differential 
        Group Delay on the Line interface 
         (Delay = AV_S16)    (Unit = ps)<Help> 
        This measure gives the current
         Differential Group Delay on the 
        Line interface.
        "
	::= { pm10010ulhMesrlineDiffGroupDelayEntry 2 }


--- *********************************************************
---     TABLE for the pm10010ulhMesrlineQFactor articles
--- *********************************************************

pm10010ulhMesrlineQFactorTable OBJECT-TYPE
	SYNTAX  SEQUENCE OF Pm10010ulhMesrlineQFactorEntry
	MAX-ACCESS not-accessible
	STATUS current
	DESCRIPTION
        "
        List of pm10010ulhMesrlineQFactor 
        Article
        "
	::= { pm10010ulhMesrLine 168 }


pm10010ulhMesrlineQFactorEntry OBJECT-TYPE
	SYNTAX Pm10010ulhMesrlineQFactorEntry
	MAX-ACCESS not-accessible
	STATUS current
	DESCRIPTION
        "
        Row definition for the pm10010ulhMesrlineQFactor 
        table
        "
	INDEX   { pm10010ulhMesrlineQFactorIndex }
	::= { pm10010ulhMesrlineQFactorTable 1 }


Pm10010ulhMesrlineQFactorEntry ::=
	SEQUENCE {
	pm10010ulhMesrlineQFactorIndex
		INTEGER,
	pm10010ulhMesrlineQFactorPortn
		INTEGER 
	}


pm10010ulhMesrlineQFactorIndex OBJECT-TYPE
	SYNTAX  INTEGER(0..128)
	MAX-ACCESS  read-only
	STATUS current
	DESCRIPTION
        "
        Index definition for the pm10010ulhMesrlineQFactor 
        table
        "
	::= { pm10010ulhMesrlineQFactorEntry 1 }


pm10010ulhMesrlineQFactorPortn OBJECT-TYPE
	SYNTAX  INTEGER (0..65535)
	MAX-ACCESS read-only
	STATUS current
	DESCRIPTION
        "
        Current Q Factor :This OID gives 
        the current Q Factor on the Line 
        interface  (Q Factor = AV_U16)
           (Unit = dB) <Help> This measure 
        gives the current Q Factor on the 
        Line interface.
        "
	::= { pm10010ulhMesrlineQFactorEntry 2 }


--- *********************************************************
---     TABLE for the pm10010ulhMesrlineCarrierFreqOffset articles
--- *********************************************************

pm10010ulhMesrlineCarrierFreqOffsetTable OBJECT-TYPE
	SYNTAX  SEQUENCE OF Pm10010ulhMesrlineCarrierFreqOffsetEntry
	MAX-ACCESS not-accessible
	STATUS current
	DESCRIPTION
        "
        List of pm10010ulhMesrlineCarrierFreqOffset 
        Article
        "
	::= { pm10010ulhMesrLine 172 }


pm10010ulhMesrlineCarrierFreqOffsetEntry OBJECT-TYPE
	SYNTAX Pm10010ulhMesrlineCarrierFreqOffsetEntry
	MAX-ACCESS not-accessible
	STATUS current
	DESCRIPTION
        "
        Row definition for the pm10010ulhMesrlineCarrierFreqOffset 
        table
        "
	INDEX   { pm10010ulhMesrlineCarrierFreqOffsetIndex }
	::= { pm10010ulhMesrlineCarrierFreqOffsetTable 1 }


Pm10010ulhMesrlineCarrierFreqOffsetEntry ::=
	SEQUENCE {
	pm10010ulhMesrlineCarrierFreqOffsetIndex
		INTEGER,
	pm10010ulhMesrlineCarrierFreqOffsetPortn
		INTEGER 
	}


pm10010ulhMesrlineCarrierFreqOffsetIndex OBJECT-TYPE
	SYNTAX  INTEGER(0..128)
	MAX-ACCESS  read-only
	STATUS current
	DESCRIPTION
        "
        Index definition for the pm10010ulhMesrlineCarrierFreqOffset 
        table
        "
	::= { pm10010ulhMesrlineCarrierFreqOffsetEntry 1 }


pm10010ulhMesrlineCarrierFreqOffsetPortn OBJECT-TYPE
	SYNTAX  INTEGER (0..65535)
	MAX-ACCESS read-only
	STATUS current
	DESCRIPTION
        "
        Current Carrier Frequency Offset 
        :This OID gives the current Carrier 
        Frequency Offset on the Line interface 
         (Offset = AV_S16)   (Unit = MHz)<Help> 
        This measure gives the current
         Carrier Frequency Offset on the 
        Line interface.
        "
	::= { pm10010ulhMesrlineCarrierFreqOffsetEntry 2 }


--- *********************************************************
---     TABLE for the pm10010ulhMesrlineOsnr articles
--- *********************************************************

pm10010ulhMesrlineOsnrTable OBJECT-TYPE
	SYNTAX  SEQUENCE OF Pm10010ulhMesrlineOsnrEntry
	MAX-ACCESS not-accessible
	STATUS current
	DESCRIPTION
        "
        List of pm10010ulhMesrlineOsnr 
        Article
        "
	::= { pm10010ulhMesrLine 176 }


pm10010ulhMesrlineOsnrEntry OBJECT-TYPE
	SYNTAX Pm10010ulhMesrlineOsnrEntry
	MAX-ACCESS not-accessible
	STATUS current
	DESCRIPTION
        "
        Row definition for the pm10010ulhMesrlineOsnr 
        table
        "
	INDEX   { pm10010ulhMesrlineOsnrIndex }
	::= { pm10010ulhMesrlineOsnrTable 1 }


Pm10010ulhMesrlineOsnrEntry ::=
	SEQUENCE {
	pm10010ulhMesrlineOsnrIndex
		INTEGER,
	pm10010ulhMesrlineOsnrPortn
		INTEGER 
	}


pm10010ulhMesrlineOsnrIndex OBJECT-TYPE
	SYNTAX  INTEGER(0..128)
	MAX-ACCESS  read-only
	STATUS current
	DESCRIPTION
        "
        Index definition for the pm10010ulhMesrlineOsnr 
        table
        "
	::= { pm10010ulhMesrlineOsnrEntry 1 }


pm10010ulhMesrlineOsnrPortn OBJECT-TYPE
	SYNTAX  INTEGER (0..65535)
	MAX-ACCESS read-only
	STATUS current
	DESCRIPTION
        "
        Current OSNR :This OID gives the 
        current OSNR on the Line interface 
          (OSNR = AV_S16/10) (Unit = dB)<Help> 
        This measure gives the current
         OSNR on the Line interface.
        "
	::= { pm10010ulhMesrlineOsnrEntry 2 }


--- *****************************************************
---     LEAF for the lineNetTxLaserOutputPwrAverage article
--- *****************************************************

pm10010ulhMesrlineNetTxLaserOutputPwrAverage OBJECT-TYPE
	  SYNTAX Unsigned32 (0..65535)
	  MAX-ACCESS read-only
	  STATUS current
	  DESCRIPTION
        "
        Average Line Trscv Tx Power :This 
        OID gives the average Tx Laser
         transmit power value among the 
        network lanes of the Line Transceiver, 
        read in the DDM (Digital Diagnostic 
        Monitoring)  (Power = AV_S16/100) 
        (Unit = dBm) <Help> This Measure 
        gives the average Tx Laser transmit 
        power value among the network lanes 
        of the Line Transceiver
        "
	  ::= { pm10010ulhMesrOther 196 }



--- *****************************************************
---     LEAF for the lineNetTxLaserTempAverage article
--- *****************************************************

pm10010ulhMesrlineNetTxLaserTempAverage OBJECT-TYPE
	  SYNTAX Unsigned32 (0..65535)
	  MAX-ACCESS read-only
	  STATUS current
	  DESCRIPTION
        "
        Average Line Trscv Tx Laser Temperature 
        :This OID gives the average Tx
         Laser Temperature value among
         the network lanes of the Line
         Transceiver, read from the DDM 
        (Digital Diagnostic Monitoring) 
        (Temperature = AV_S16/256) (Unit 
        = C) <Help> This Measure gives
         the average Tx Laser Temperature 
        value among the network lanes of 
        the Line Transceiver
        "
	  ::= { pm10010ulhMesrOther 197 }



--- *****************************************************
---     LEAF for the lineNetTxBiasCurrentAverage article
--- *****************************************************

pm10010ulhMesrlineNetTxBiasCurrentAverage OBJECT-TYPE
	  SYNTAX Unsigned32 (0..65535)
	  MAX-ACCESS read-only
	  STATUS current
	  DESCRIPTION
        "
        Average Line Trscv Tx Laser Bias 
        :This OID gives the average Tx
         Laser Bias value among the network 
        lanes of the Line Transceiver,
         read from the DDM (Digital Diagnostic 
        Monitoring) (Bias = AV_S16/10)
         (Unit = mA) <Help> This Measure 
        gives the average Tx Laser Bias 
        value among the network lanes of 
        the Line Transceiver
        "
	  ::= { pm10010ulhMesrOther 198 }



--- *****************************************************
---     LEAF for the lineNetRxInputPwrAverage article
--- *****************************************************

pm10010ulhMesrlineNetRxInputPwrAverage OBJECT-TYPE
	  SYNTAX Unsigned32 (0..65535)
	  MAX-ACCESS read-only
	  STATUS current
	  DESCRIPTION
        "
        Average Line Trscv Rx Power :This 
        OID gives the average Receive power 
        value among the network lanes of 
        the Line Transceiver, read in the 
        DDM (Digital Diagnostic Monitoring) 
        (Power = AV_S16/100) (Unit = dBm) 
        <Help> This Measure gives the average 
        Receive power value among the network 
        lanes of the Line Transceiver
        "
	  ::= { pm10010ulhMesrOther 199 }



--- *****************************************************
---     LEAF for the lineResidualChromaticDispAverage article
--- *****************************************************

pm10010ulhMesrlineResidualChromaticDispAverage OBJECT-TYPE
	  SYNTAX Unsigned32 (0..65535)
	  MAX-ACCESS read-only
	  STATUS current
	  DESCRIPTION
        "
        Average Residual Chromatic Dispersion 
        :This OID gives the average Residual 
        Chromatic Dispersion on the Line 
        interface since the last measure 
        reset  (Dispersion = AV_S16*(-2)) 
         (Unit = ps/nm)<Help> This measure 
        gives the average Residual Chromatic 
        Dispersion on the Line interface 
        since the last measure reset.
        "
	  ::= { pm10010ulhMesrOther 200 }



--- *****************************************************
---     LEAF for the lineDiffGroupDelayAverage article
--- *****************************************************

pm10010ulhMesrlineDiffGroupDelayAverage OBJECT-TYPE
	  SYNTAX Unsigned32 (0..65535)
	  MAX-ACCESS read-only
	  STATUS current
	  DESCRIPTION
        "
        Average Differential Group Delay 
        :This OID gives the average Group 
        Delay on the Line interface since 
        the last measure reset (Delay = 
        AV_S16)  (Unit = ps)<Help> This 
        measure gives the average Differential 
        Group Delay on the Line interface 
        since the last measure reset.
        "
	  ::= { pm10010ulhMesrOther 201 }



--- *****************************************************
---     LEAF for the lineQFactorAverage article
--- *****************************************************

pm10010ulhMesrlineQFactorAverage OBJECT-TYPE
	  SYNTAX Unsigned32 (0..65535)
	  MAX-ACCESS read-only
	  STATUS current
	  DESCRIPTION
        "
        Average Q Factor :This OID gives 
        the average Q Factor on the Line 
        interface since the last measure 
        reset (Q Factor = AV_U16)   (Unit 
        = dB) <Help> This measure gives 
        the average Q Factor on the Line 
        interface since the last measure 
        reset.
        "
	  ::= { pm10010ulhMesrOther 202 }



--- *****************************************************
---     LEAF for the lineCarrierFreqOffsetAverage article
--- *****************************************************

pm10010ulhMesrlineCarrierFreqOffsetAverage OBJECT-TYPE
	  SYNTAX Unsigned32 (0..65535)
	  MAX-ACCESS read-only
	  STATUS current
	  DESCRIPTION
        "
        Average Carrier Frequency Offset 
        :This OID gives the average Carrier 
        Frequency Offset on the Line interface 
        since the last measure reset (Offset 
        = AV_S16)  (Unit = MHz)<Help> This 
        measure gives the average Carrier 
        Frequency Offset on the Line interface 
        since the last measure reset
        "
	  ::= { pm10010ulhMesrOther 203 }



--- *****************************************************
---     LEAF for the lineOsnrAverage article
--- *****************************************************

pm10010ulhMesrlineOsnrAverage OBJECT-TYPE
	  SYNTAX Unsigned32 (0..65535)
	  MAX-ACCESS read-only
	  STATUS current
	  DESCRIPTION
        "
        Average OSNR :This OID gives the 
        average OSNR on the Line interface 
        since the last measure reset (OSNR 
        = AV_S16/10) (Unit = dB)<Help>
         This measure gives the average 
        OSNR on the Line interface since 
        the last measure reset.
        "
	  ::= { pm10010ulhMesrOther 204 }



--- *****************************************************
---     LEAF for the clientNetTxTempMin article
--- *****************************************************

pm10010ulhMesrclientNetTxTempMin OBJECT-TYPE
	  SYNTAX Unsigned32 (0..65535)
	  MAX-ACCESS read-only
	  STATUS current
	  DESCRIPTION
        "
        Min Client Trscv Laser Temperature 
        :This OID gives the minimum Laser 
        temperature value among the network 
        lanes of the Client Transceiver, 
        read from the DDM (Digital Diagnostic 
        Monitoring) (Temperature = AV_S16/256) 
        (Unit = C) <Help> This Measure
         gives the minimum Laser temperature 
        value among the network lanes of 
        the Client Transceiver
        "
	  ::= { pm10010ulhMesrOther 208 }



--- *****************************************************
---     LEAF for the clientNetTxBiasMin article
--- *****************************************************

pm10010ulhMesrclientNetTxBiasMin OBJECT-TYPE
	  SYNTAX Unsigned32 (0..65535)
	  MAX-ACCESS read-only
	  STATUS current
	  DESCRIPTION
        "
        Min Client Trscv Laser Bias :This 
        OID gives the minimum Laser bias 
        value among the network lanes of 
        the Client Transceiver, read from 
        the DDM (Digital Diagnostic Monitoring) 
        (Bias = AV_U16/500) (Unit = mA) 
        <Help> This Measure gives the minimum 
        Laser bias value among the network 
        lanes of the Client Transceiver
        "
	  ::= { pm10010ulhMesrOther 209 }



--- *****************************************************
---     LEAF for the clientNetTxPwrMin article
--- *****************************************************

pm10010ulhMesrclientNetTxPwrMin OBJECT-TYPE
	  SYNTAX Unsigned32 (0..65535)
	  MAX-ACCESS read-only
	  STATUS current
	  DESCRIPTION
        "
        Min Client Trscv Tx Power :This 
        OID gives the minimum transmit
         power value among the network
         lanes of the Client Transceiver, 
        read from the DDM (Digital Diagnostic 
        Monitoring) (Power = 10*log(AV_U16)-40) 
        (Unit = dBm) <Help> This Measure 
        gives the minimum transmit power 
        value among the network lanes of 
        the Client Transceiver
        "
	  ::= { pm10010ulhMesrOther 210 }



--- *****************************************************
---     LEAF for the clientNetRxPwrMin article
--- *****************************************************

pm10010ulhMesrclientNetRxPwrMin OBJECT-TYPE
	  SYNTAX Unsigned32 (0..65535)
	  MAX-ACCESS read-only
	  STATUS current
	  DESCRIPTION
        "
        Min Client Trscv Rx Power :This 
        OID gives the minimum receive power 
        value among the network lanes of 
        the Client Transceiver, read in 
        the DDM (Digital Diagnostic Monitoring) 
        (Power = 10*log(AV_U16)-40) (Unit 
        = dBm) <Help> This Measure gives 
        the minimum receive power value 
        among the network lanes of the
         Client Transceiver
        "
	  ::= { pm10010ulhMesrOther 211 }



--- *****************************************************
---     LEAF for the lineNetTxLaserOutputPwrMin article
--- *****************************************************

pm10010ulhMesrlineNetTxLaserOutputPwrMin OBJECT-TYPE
	  SYNTAX Unsigned32 (0..65535)
	  MAX-ACCESS read-only
	  STATUS current
	  DESCRIPTION
        "
        Min Line Trscv Tx Power :This
         OID gives the minimum Tx Laser 
        transmit power value among the
         network lanes of the Line Transceiver, 
        read in the DDM (Digital Diagnostic 
        Monitoring)  (Power = AV_S16/100) 
        (Unit = dBm) <Help> This Measure 
        gives the minimum Tx Laser transmit 
        power value among the network lanes 
        of the Line Transceiver
        "
	  ::= { pm10010ulhMesrOther 212 }



--- *****************************************************
---     LEAF for the lineNetTxLaserTempMin article
--- *****************************************************

pm10010ulhMesrlineNetTxLaserTempMin OBJECT-TYPE
	  SYNTAX Unsigned32 (0..65535)
	  MAX-ACCESS read-only
	  STATUS current
	  DESCRIPTION
        "
        Min Line Trscv Tx Laser Temperature 
        :This OID gives the minimum Tx
         Laser Temperature value among
         the network lanes of the Line
         Transceiver, read from the DDM 
        (Digital Diagnostic Monitoring) 
        (Temperature = AV_S16/256) (Unit 
        = C) <Help> This Measure gives
         the minimum Tx Laser Temperature 
        value among the network lanes of 
        the Line Transceiver
        "
	  ::= { pm10010ulhMesrOther 213 }



--- *****************************************************
---     LEAF for the lineNetTxBiasCurrentMin article
--- *****************************************************

pm10010ulhMesrlineNetTxBiasCurrentMin OBJECT-TYPE
	  SYNTAX Unsigned32 (0..65535)
	  MAX-ACCESS read-only
	  STATUS current
	  DESCRIPTION
        "
        Min Line Trscv Tx Laser Bias :This 
        OID gives the minimum Tx Laser
         Bias value among the network lanes 
        of the Line Transceiver, read from 
        the DDM (Digital Diagnostic Monitoring) 
        (Bias = AV_S16/10) (Unit = mA)
         <Help> This Measure gives the
         minimum Tx Laser Bias value among 
        the network lanes of the Line Transceiver
        "
	  ::= { pm10010ulhMesrOther 214 }



--- *****************************************************
---     LEAF for the lineNetRxInputPwrMin article
--- *****************************************************

pm10010ulhMesrlineNetRxInputPwrMin OBJECT-TYPE
	  SYNTAX Unsigned32 (0..65535)
	  MAX-ACCESS read-only
	  STATUS current
	  DESCRIPTION
        "
        Min Line Trscv Rx Power :This
         OID gives the minimum Receive
         power value among the network
         lanes of the Line Transceiver, 
        read in the DDM (Digital Diagnostic 
        Monitoring) (Power = AV_S16/100) 
        (Unit = dBm) <Help> This Measure 
        gives the minimum Receive power 
        value among the network lanes of 
        the Line Transceiver
        "
	  ::= { pm10010ulhMesrOther 215 }



--- *****************************************************
---     LEAF for the lineResidualChromaticDispMin article
--- *****************************************************

pm10010ulhMesrlineResidualChromaticDispMin OBJECT-TYPE
	  SYNTAX Unsigned32 (0..65535)
	  MAX-ACCESS read-only
	  STATUS current
	  DESCRIPTION
        "
        Min Residual Chromatic Dispersion 
        :This OID gives the minimum Residual 
        Chromatic Dispersion on the Line 
        interface since the last measure 
        reset (Dispersion = AV_S16*(-2)) 
          (Unit = ps/nm)<Help> This measure 
        gives the minimum Residual Chromatic 
        Dispersion on the Line interface 
        since the last measure reset.
        "
	  ::= { pm10010ulhMesrOther 216 }



--- *****************************************************
---     LEAF for the lineDiffGroupDelayMin article
--- *****************************************************

pm10010ulhMesrlineDiffGroupDelayMin OBJECT-TYPE
	  SYNTAX Unsigned32 (0..65535)
	  MAX-ACCESS read-only
	  STATUS current
	  DESCRIPTION
        "
        Min Differential Group Delay :This 
        OID gives the minimum Differential 
        Group Delay  on the Line interface 
        since the last measure reset (Delay 
        = AV_S16)  (Unit = ps)<Help> This 
        measure gives the minimum Differential 
        Group Delay on the Line interface 
        since the last measure reset.
        "
	  ::= { pm10010ulhMesrOther 217 }



--- *****************************************************
---     LEAF for the lineQFactorMin article
--- *****************************************************

pm10010ulhMesrlineQFactorMin OBJECT-TYPE
	  SYNTAX Unsigned32 (0..65535)
	  MAX-ACCESS read-only
	  STATUS current
	  DESCRIPTION
        "
        Min Q Factor :This OID gives the 
        minimum Q Factor on the Line interface 
        since the last measure reset (Q 
        Factor = AV_U16)  (Unit = dB)<Help> 
        This measure gives the minimum
         Q Factor on the Line interface 
        since the last measure reset.
        "
	  ::= { pm10010ulhMesrOther 218 }



--- *****************************************************
---     LEAF for the lineCarrierFreqOffsetMin article
--- *****************************************************

pm10010ulhMesrlineCarrierFreqOffsetMin OBJECT-TYPE
	  SYNTAX Unsigned32 (0..65535)
	  MAX-ACCESS read-only
	  STATUS current
	  DESCRIPTION
        "
        Min Carrier Frequency Offset :This 
        OID gives the minimum Carrier Frequency 
        Offset on the Line interface since 
        the last measure reset  (Offset 
        = AV_S16)   (Unit = MHz)<Help>
         This measure gives the minimum 
        Carrier Frequency Offset on the 
        Line interface since the last measure 
        reset
        "
	  ::= { pm10010ulhMesrOther 219 }



--- *****************************************************
---     LEAF for the lineOsnrMin article
--- *****************************************************

pm10010ulhMesrlineOsnrMin OBJECT-TYPE
	  SYNTAX Unsigned32 (0..65535)
	  MAX-ACCESS read-only
	  STATUS current
	  DESCRIPTION
        "
        Min OSNR :This OID gives the minimum 
        OSNR on the Line interface since 
        the last measure reset  (OSNR = 
        AV_S16/10) (Unit = dB)<Help> This 
        measure gives the minimum OSNR
         on the Line interface since the 
        last measure reset.
        "
	  ::= { pm10010ulhMesrOther 220 }



--- *****************************************************
---     LEAF for the clientNetTxTempMax article
--- *****************************************************

pm10010ulhMesrclientNetTxTempMax OBJECT-TYPE
	  SYNTAX Unsigned32 (0..65535)
	  MAX-ACCESS read-only
	  STATUS current
	  DESCRIPTION
        "
        Max Client Trscv Laser Temperature 
        :This OID gives the maximum Laser 
        temperature value among the network 
        lanes of the Client Transceiver, 
        read from the DDM (Digital Diagnostic 
        Monitoring) (Temperature = AV_S16/256) 
        (Unit = C) <Help> This Measure
         gives the maximum Laser temperature 
        value among the network lanes of 
        the Client Transceiver
        "
	  ::= { pm10010ulhMesrOther 224 }



--- *****************************************************
---     LEAF for the clientNetTxBiasMax article
--- *****************************************************

pm10010ulhMesrclientNetTxBiasMax OBJECT-TYPE
	  SYNTAX Unsigned32 (0..65535)
	  MAX-ACCESS read-only
	  STATUS current
	  DESCRIPTION
        "
        Max Client Trscv Laser Bias :This 
        OID gives the maximum Laser bias 
        value among the network lanes of 
        the Client Transceiver, read from 
        the DDM (Digital Diagnostic Monitoring) 
        (Bias = AV_U16/500) (Unit = mA) 
        <Help> This Measure gives the maximum 
        Laser bias value among the network 
        lanes of the Client Transceiver
        "
	  ::= { pm10010ulhMesrOther 225 }



--- *****************************************************
---     LEAF for the clientNetTxPwrMax article
--- *****************************************************

pm10010ulhMesrclientNetTxPwrMax OBJECT-TYPE
	  SYNTAX Unsigned32 (0..65535)
	  MAX-ACCESS read-only
	  STATUS current
	  DESCRIPTION
        "
        Max Client Trscv Tx Power :This 
        OID gives the maximum transmit
         power value among the network
         lanes of the Client Transceiver, 
        read from the DDM (Digital Diagnostic 
        Monitoring) (Power = 10*log(AV_U16)-40) 
        (Unit = dBm) <Help> This Measure 
        gives the maximum transmit power 
        value among the network lanes of 
        the Client Transceiver
        "
	  ::= { pm10010ulhMesrOther 226 }



--- *****************************************************
---     LEAF for the clientNetRxPwrMax article
--- *****************************************************

pm10010ulhMesrclientNetRxPwrMax OBJECT-TYPE
	  SYNTAX Unsigned32 (0..65535)
	  MAX-ACCESS read-only
	  STATUS current
	  DESCRIPTION
        "
        Max Client Trscv Rx Power :This 
        OID gives the maximum receive power 
        value among the network lanes of 
        the Client Transceiver, read in 
        the DDM (Digital Diagnostic Monitoring) 
        (Power = 10*log(AV_U16)-40) (Unit 
        = dBm) <Help> This Measure gives 
        the maximum receive power value 
        among the network lanes of the
         Client Transceiver
        "
	  ::= { pm10010ulhMesrOther 227 }



--- *****************************************************
---     LEAF for the lineNetTxLaserOutputPwrMax article
--- *****************************************************

pm10010ulhMesrlineNetTxLaserOutputPwrMax OBJECT-TYPE
	  SYNTAX Unsigned32 (0..65535)
	  MAX-ACCESS read-only
	  STATUS current
	  DESCRIPTION
        "
        Max Line Trscv Tx Power :This
         OID gives the maximum Tx Laser 
        transmit power value among the
         network lanes of the Line Transceiver, 
        read in the DDM (Digital Diagnostic 
        Monitoring) (Power = AV_S16/100) 
        (Unit = dBm) <Help> This Measure 
        gives the maximum Tx Laser transmit 
        power value among the network lanes 
        of the Line Transceiver
        "
	  ::= { pm10010ulhMesrOther 228 }



--- *****************************************************
---     LEAF for the lineNetTxLaserTempMax article
--- *****************************************************

pm10010ulhMesrlineNetTxLaserTempMax OBJECT-TYPE
	  SYNTAX Unsigned32 (0..65535)
	  MAX-ACCESS read-only
	  STATUS current
	  DESCRIPTION
        "
        Max Line Trscv Tx Laser Temperature 
        :This OID gives the maximum Tx
         Laser Temperature value among
         the network lanes of the Line
         Transceiver, read from the DDM 
        (Digital Diagnostic Monitoring) 
        (Temperature = AV_S16/256) (Unit 
        = C) <Help> This Measure gives
         the maximum Tx Laser Temperature 
        value among the network lanes of 
        the Line Transceiver
        "
	  ::= { pm10010ulhMesrOther 229 }



--- *****************************************************
---     LEAF for the lineNetTxBiasCurrentMax article
--- *****************************************************

pm10010ulhMesrlineNetTxBiasCurrentMax OBJECT-TYPE
	  SYNTAX Unsigned32 (0..65535)
	  MAX-ACCESS read-only
	  STATUS current
	  DESCRIPTION
        "
        Max Line Trscv Tx Laser Bias :This 
        OID gives the maximum Tx Laser
         Bias value among the network lanes 
        of the Line Transceiver, read from 
        the DDM (Digital Diagnostic Monitoring) 
        (Bias = AV_S16/10) (Unit = mA)
         <Help> This Measure gives the
         maximum Tx Laser Bias value among 
        the network lanes of the Line Transceiver
        "
	  ::= { pm10010ulhMesrOther 230 }



--- *****************************************************
---     LEAF for the lineNetRxInputPwrMax article
--- *****************************************************

pm10010ulhMesrlineNetRxInputPwrMax OBJECT-TYPE
	  SYNTAX Unsigned32 (0..65535)
	  MAX-ACCESS read-only
	  STATUS current
	  DESCRIPTION
        "
        Max Line Trscv Rx Power :This
         OID gives the maximum Receive
         power value among the network
         lanes of the Line Transceiver, 
        read in the DDM (Digital Diagnostic 
        Monitoring) (Power = AV_S16/100) 
        (Unit = dBm) <Help> This Measure 
        gives the maximum Receive power 
        value among the network lanes of 
        the Line Transceiver
        "
	  ::= { pm10010ulhMesrOther 231 }



--- *****************************************************
---     LEAF for the lineResidualChromaticDispMax article
--- *****************************************************

pm10010ulhMesrlineResidualChromaticDispMax OBJECT-TYPE
	  SYNTAX Unsigned32 (0..65535)
	  MAX-ACCESS read-only
	  STATUS current
	  DESCRIPTION
        "
        Max Residual Chromatic Dispersion 
        :This OID gives the maximum Residual 
        Chromatic Dispersion on the Line 
        interface since the last measure 
        reset (Dispersion = AV_S16*(-2)) 
          (Unit = ps/nm)<Help> This measure 
        gives the maximum Residual Chromatic 
        Dispersion on the Line interface 
        since the last measure reset.
        "
	  ::= { pm10010ulhMesrOther 232 }



--- *****************************************************
---     LEAF for the lineDiffGroupDelayMax article
--- *****************************************************

pm10010ulhMesrlineDiffGroupDelayMax OBJECT-TYPE
	  SYNTAX Unsigned32 (0..65535)
	  MAX-ACCESS read-only
	  STATUS current
	  DESCRIPTION
        "
        Max Differential Group Delay :This 
        OID gives the maximum Differential 
        Group Delay  on the Line interface 
        since the last measure reset  (Delay 
        = AV_S16)   (Unit = ps)<Help> This 
        measure gives the maximum Differential 
        Group Delay on the Line interface 
        since the last measure reset.
        "
	  ::= { pm10010ulhMesrOther 233 }



--- *****************************************************
---     LEAF for the lineQFactorMax article
--- *****************************************************

pm10010ulhMesrlineQFactorMax OBJECT-TYPE
	  SYNTAX Unsigned32 (0..65535)
	  MAX-ACCESS read-only
	  STATUS current
	  DESCRIPTION
        "
        Max Q Factor :This OID gives the 
        maximum Q Factor on the Line interface 
        since the last measure reset (Q 
        Factor = AV_U16)    (Unit = dB)<Help> 
        This measure gives the maximum
         Q Factor on the Line interface 
        since the last measure reset.
        "
	  ::= { pm10010ulhMesrOther 234 }



--- *****************************************************
---     LEAF for the lineCarrierFreqOffsetMax article
--- *****************************************************

pm10010ulhMesrlineCarrierFreqOffsetMax OBJECT-TYPE
	  SYNTAX Unsigned32 (0..65535)
	  MAX-ACCESS read-only
	  STATUS current
	  DESCRIPTION
        "
        Max Carrier Frequency Offset :This 
        OID gives the maximum Carrier Frequency 
        Offset on the Line interface since 
        the last measure reset  (Offset 
        = AV_S16)   (Unit = MHz)<Help>
         This measure gives the maximum 
        Carrier Frequency Offset on the 
        Line interface since the last measure 
        reset.
        "
	  ::= { pm10010ulhMesrOther 235 }



--- *****************************************************
---     LEAF for the lineOsnrMax article
--- *****************************************************

pm10010ulhMesrlineOsnrMax OBJECT-TYPE
	  SYNTAX Unsigned32 (0..65535)
	  MAX-ACCESS read-only
	  STATUS current
	  DESCRIPTION
        "
        Max OSNR :This OID gives the maximum 
        OSNR on the Line interface since 
        the last measure reset   (OSNR
         = AV_S16/10) (Unit = dB)<Help> 
        This measure gives the maximum
         OSNR on the Line interface since 
        the last measure reset
        "
	  ::= { pm10010ulhMesrOther 236 }








--- *****************************************************
--- $$$$$$$$$$$$$$$$$$$$$$$$$$$$$$$$$$$$$$$$$$$$$$$$$$$$$
---     PERFORMANCE
--- $$$$$$$$$$$$$$$$$$$$$$$$$$$$$$$$$$$$$$$$$$$$$$$$$$$$$
--- *****************************************************



--- *****************************************************
---     Leaf of the telecomInputClientCurrent15Stat
--- *****************************************************
--- *********************************************************
---     TABLE for the pm10010ulhPerfTelecomInputClientCurrent15Stat articles
--- *********************************************************

pm10010ulhPerfTelecomInputClientCurrent15StatTable OBJECT-TYPE
	SYNTAX  SEQUENCE OF Pm10010ulhPerfTelecomInputClientCurrent15StatEntry
	MAX-ACCESS not-accessible
	STATUS current
	DESCRIPTION
        "
        List of pm10010ulhPerfTelecomInputClientCurrent15Stat 
        Article
        "
	::= { pm10010ulhMonPerfClient 16 }


pm10010ulhPerfTelecomInputClientCurrent15StatEntry OBJECT-TYPE
	SYNTAX Pm10010ulhPerfTelecomInputClientCurrent15StatEntry
	MAX-ACCESS not-accessible
	STATUS current
	DESCRIPTION
        "
        Row definition for the pm10010ulhPerfTelecomInputClientCurrent15Stat 
        table
        "
	INDEX   { pm10010ulhPerfTelecomInputClientCurrent15StatIndex }
	::= { pm10010ulhPerfTelecomInputClientCurrent15StatTable 1 }


Pm10010ulhPerfTelecomInputClientCurrent15StatEntry ::=
	SEQUENCE {
	pm10010ulhPerfTelecomInputClientCurrent15StatIndex
		INTEGER,
	pm10010ulhPerfTelecomInputClientCurrent15StatInvCvPortn
		EkiOnOff,
	pm10010ulhPerfTelecomInputClientCurrent15StatCvValuePortn
		Unsigned32,
	pm10010ulhPerfTelecomInputClientCurrent15StatInvEsPortn
		EkiOnOff,
	pm10010ulhPerfTelecomInputClientCurrent15StatEsValuePortn
		Unsigned32,
	pm10010ulhPerfTelecomInputClientCurrent15StatInvSesPortn
		EkiOnOff,
	pm10010ulhPerfTelecomInputClientCurrent15StatSesValuePortn
		Unsigned32,
	pm10010ulhPerfTelecomInputClientCurrent15StatInvSefsPortn
		EkiOnOff,
	pm10010ulhPerfTelecomInputClientCurrent15StatSefsValuePortn
		Unsigned32,
	pm10010ulhPerfTelecomInputClientCurrent15StatInvUasPortn
		EkiOnOff,
	pm10010ulhPerfTelecomInputClientCurrent15StatUasValuePortn
		Unsigned32
	}


pm10010ulhPerfTelecomInputClientCurrent15StatIndex OBJECT-TYPE
	SYNTAX  INTEGER(0..128)
	MAX-ACCESS  read-only
	STATUS current
	DESCRIPTION
        "
        Index definition for the pm10010ulhPerfTelecomInputClientCurrent15Stat 
        table
        "
	::= { pm10010ulhPerfTelecomInputClientCurrent15StatEntry 1 }


pm10010ulhPerfTelecomInputClientCurrent15StatInvCvPortn OBJECT-TYPE
	SYNTAX  EkiOnOff
	MAX-ACCESS read-only
	STATUS current
	DESCRIPTION
        "
        Current 15-min EBC counter inv. 
        :This OID indicates that the current 
        15-min Coding Violation counter 
        is invalid
        "
	::= { pm10010ulhPerfTelecomInputClientCurrent15StatEntry 2 }


pm10010ulhPerfTelecomInputClientCurrent15StatCvValuePortn OBJECT-TYPE
	SYNTAX  Unsigned32
	MAX-ACCESS read-only
	STATUS current
	DESCRIPTION
        "
        Current 15-min EBC counter :This 
        OID gives the current 15-min Coding 
        Violation counter value
        "
	::= { pm10010ulhPerfTelecomInputClientCurrent15StatEntry 3 }


pm10010ulhPerfTelecomInputClientCurrent15StatInvEsPortn OBJECT-TYPE
	SYNTAX  EkiOnOff
	MAX-ACCESS read-only
	STATUS current
	DESCRIPTION
        "
        Current 15-min ES counter inv. 
        :This OID indicates that the current 
        15-min Errored Second counter is 
        invalid
        "
	::= { pm10010ulhPerfTelecomInputClientCurrent15StatEntry 4 }


pm10010ulhPerfTelecomInputClientCurrent15StatEsValuePortn OBJECT-TYPE
	SYNTAX  Unsigned32
	MAX-ACCESS read-only
	STATUS current
	DESCRIPTION
        "
        Current 15-min ES counter :This 
        OID gives the current 15-min Errored 
        Second counter value
        "
	::= { pm10010ulhPerfTelecomInputClientCurrent15StatEntry 5 }


pm10010ulhPerfTelecomInputClientCurrent15StatInvSesPortn OBJECT-TYPE
	SYNTAX  EkiOnOff
	MAX-ACCESS read-only
	STATUS current
	DESCRIPTION
        "
        Current 15-min SES counter inv. 
        :This OID indicates that the current 
        15-min severely Errored Second
         counter is invalid
        "
	::= { pm10010ulhPerfTelecomInputClientCurrent15StatEntry 6 }


pm10010ulhPerfTelecomInputClientCurrent15StatSesValuePortn OBJECT-TYPE
	SYNTAX  Unsigned32
	MAX-ACCESS read-only
	STATUS current
	DESCRIPTION
        "
        Current 15-min SES counter :This 
        OID gives the current 15-min severely 
        Errored Second counter value
        "
	::= { pm10010ulhPerfTelecomInputClientCurrent15StatEntry 7 }


pm10010ulhPerfTelecomInputClientCurrent15StatInvSefsPortn OBJECT-TYPE
	SYNTAX  EkiOnOff
	MAX-ACCESS read-only
	STATUS current
	DESCRIPTION
        "
        Current 15-min SEFS counter inv. 
        :This OID indicates that the current 
        15-min severely Errored Framing 
        Second counter is invalid
        "
	::= { pm10010ulhPerfTelecomInputClientCurrent15StatEntry 8 }


pm10010ulhPerfTelecomInputClientCurrent15StatSefsValuePortn OBJECT-TYPE
	SYNTAX  Unsigned32
	MAX-ACCESS read-only
	STATUS current
	DESCRIPTION
        "
        Current 15-min SEFS counter :This 
        OID gives the current 15-min severely 
        Errored Framing Second counter
         value
        "
	::= { pm10010ulhPerfTelecomInputClientCurrent15StatEntry 9 }


pm10010ulhPerfTelecomInputClientCurrent15StatInvUasPortn OBJECT-TYPE
	SYNTAX  EkiOnOff
	MAX-ACCESS read-only
	STATUS current
	DESCRIPTION
        "
        Current 15-min UAS counter inv. 
        :This OID indicates that the current 
        15-min UnAvailable Second counter 
        is invalid
        "
	::= { pm10010ulhPerfTelecomInputClientCurrent15StatEntry 10 }


pm10010ulhPerfTelecomInputClientCurrent15StatUasValuePortn OBJECT-TYPE
	SYNTAX  Unsigned32
	MAX-ACCESS read-only
	STATUS current
	DESCRIPTION
        "
        Current 15-min UAS counter :This 
        OID gives the current 15-min UnAvailable 
        Second counter value
        "
	::= { pm10010ulhPerfTelecomInputClientCurrent15StatEntry 11 }


--- *****************************************************
---     Leaf of the telecomInputClientPast15Stat
--- *****************************************************
--- *********************************************************
---     TABLE for the pm10010ulhPerfTelecomInputClientPast15StatHistory articles
--- *********************************************************

pm10010ulhPerfTelecomInputClientPast15StatHistoryPort1Table OBJECT-TYPE
	SYNTAX  SEQUENCE OF Pm10010ulhPerfTelecomInputClientPast15StatHistoryPort1Entry
	MAX-ACCESS not-accessible
	STATUS current
	DESCRIPTION
        "
        List of pm10010ulhPerfTelecomInputClientPast15StatHistory 
        Article
        "
	::= { pm10010ulhMonPerfClient 48 }


pm10010ulhPerfTelecomInputClientPast15StatHistoryPort1Entry OBJECT-TYPE
	SYNTAX Pm10010ulhPerfTelecomInputClientPast15StatHistoryPort1Entry
	MAX-ACCESS not-accessible
	STATUS current
	DESCRIPTION
        "
        Row definition for the pm10010ulhPerfTelecomInputClientPast15StatHistory 
        table
        "
	INDEX   { pm10010ulhPerfTelecomInputClientPast15StatHistoryPort1Index }
	::= { pm10010ulhPerfTelecomInputClientPast15StatHistoryPort1Table 1 }


Pm10010ulhPerfTelecomInputClientPast15StatHistoryPort1Entry ::=
	SEQUENCE {
	pm10010ulhPerfTelecomInputClientPast15StatHistoryPort1Index
		INTEGER,
	pm10010ulhPerfTelecomInputClientPast15StatHistoryInvCvPort1
		EkiOnOff,
	pm10010ulhPerfTelecomInputClientPast15StatHistoryCvValuePort1
		Unsigned32,
	pm10010ulhPerfTelecomInputClientPast15StatHistoryInvEsPort1
		EkiOnOff,
	pm10010ulhPerfTelecomInputClientPast15StatHistoryEsValuePort1
		Unsigned32,
	pm10010ulhPerfTelecomInputClientPast15StatHistoryInvSesPort1
		EkiOnOff,
	pm10010ulhPerfTelecomInputClientPast15StatHistorySesValuePort1
		Unsigned32,
	pm10010ulhPerfTelecomInputClientPast15StatHistoryInvSefsPort1
		EkiOnOff,
	pm10010ulhPerfTelecomInputClientPast15StatHistorySefsValuePort1
		Unsigned32,
	pm10010ulhPerfTelecomInputClientPast15StatHistoryInvUasPort1
		EkiOnOff,
	pm10010ulhPerfTelecomInputClientPast15StatHistoryUasValuePort1
		Unsigned32
	}


pm10010ulhPerfTelecomInputClientPast15StatHistoryPort1Index OBJECT-TYPE
	SYNTAX  INTEGER(0..128)
	MAX-ACCESS  read-only
	STATUS current
	DESCRIPTION
        "
        Index definition for the pm10010ulhPerfTelecomInputClientPast15StatHistory 
        table
        "
	::= { pm10010ulhPerfTelecomInputClientPast15StatHistoryPort1Entry 1 }


pm10010ulhPerfTelecomInputClientPast15StatHistoryInvCvPort1 OBJECT-TYPE
	SYNTAX  EkiOnOff
	MAX-ACCESS read-only
	STATUS current
	DESCRIPTION
        "
        Previous 15-min EBC counter inv. 
        :This OID indicates that the previous 
        15-min Coding Violation counter 
        is invalid
        "
	::= { pm10010ulhPerfTelecomInputClientPast15StatHistoryPort1Entry 2 }


pm10010ulhPerfTelecomInputClientPast15StatHistoryCvValuePort1 OBJECT-TYPE
	SYNTAX  Unsigned32
	MAX-ACCESS read-only
	STATUS current
	DESCRIPTION
        "
        Previous 15-min EBC counter :This 
        OID gives the previous 15-min Coding 
        Violation counter value
        "
	::= { pm10010ulhPerfTelecomInputClientPast15StatHistoryPort1Entry 3 }


pm10010ulhPerfTelecomInputClientPast15StatHistoryInvEsPort1 OBJECT-TYPE
	SYNTAX  EkiOnOff
	MAX-ACCESS read-only
	STATUS current
	DESCRIPTION
        "
        Previous 15-min ES counter inv. 
        :This OID indicates that the previous 
        15-min Errored Second counter is 
        invalid
        "
	::= { pm10010ulhPerfTelecomInputClientPast15StatHistoryPort1Entry 4 }


pm10010ulhPerfTelecomInputClientPast15StatHistoryEsValuePort1 OBJECT-TYPE
	SYNTAX  Unsigned32
	MAX-ACCESS read-only
	STATUS current
	DESCRIPTION
        "
        Previous 15-min ES counter :This 
        OID gives the previous 15-min Errored 
        Second counter value
        "
	::= { pm10010ulhPerfTelecomInputClientPast15StatHistoryPort1Entry 5 }


pm10010ulhPerfTelecomInputClientPast15StatHistoryInvSesPort1 OBJECT-TYPE
	SYNTAX  EkiOnOff
	MAX-ACCESS read-only
	STATUS current
	DESCRIPTION
        "
        Previous 15-min SES counter inv. 
        :This OID indicates that the previous 
        15-min severely Errored Second
         counter is invalid
        "
	::= { pm10010ulhPerfTelecomInputClientPast15StatHistoryPort1Entry 6 }


pm10010ulhPerfTelecomInputClientPast15StatHistorySesValuePort1 OBJECT-TYPE
	SYNTAX  Unsigned32
	MAX-ACCESS read-only
	STATUS current
	DESCRIPTION
        "
        Previous 15-min SES counter :This 
        OID gives the previous 15-min severely 
        Errored Second counter value
        "
	::= { pm10010ulhPerfTelecomInputClientPast15StatHistoryPort1Entry 7 }


pm10010ulhPerfTelecomInputClientPast15StatHistoryInvSefsPort1 OBJECT-TYPE
	SYNTAX  EkiOnOff
	MAX-ACCESS read-only
	STATUS current
	DESCRIPTION
        "
        Previous 15-min SEFS counter inv. 
        :This OID indicates that the previous 
        15-min severely Errored Framing 
        Second counter is invalid
        "
	::= { pm10010ulhPerfTelecomInputClientPast15StatHistoryPort1Entry 8 }


pm10010ulhPerfTelecomInputClientPast15StatHistorySefsValuePort1 OBJECT-TYPE
	SYNTAX  Unsigned32
	MAX-ACCESS read-only
	STATUS current
	DESCRIPTION
        "
        Previous 15-min SEFS counter :This 
        OID gives the previous 15-min severely 
        Errored Framing Second counter
         value
        "
	::= { pm10010ulhPerfTelecomInputClientPast15StatHistoryPort1Entry 9 }


pm10010ulhPerfTelecomInputClientPast15StatHistoryInvUasPort1 OBJECT-TYPE
	SYNTAX  EkiOnOff
	MAX-ACCESS read-only
	STATUS current
	DESCRIPTION
        "
        Previous 15-min UAS counter inv. 
        :This OID indicates that the previous 
        15-min UnAvailable Second counter 
        is invalid
        "
	::= { pm10010ulhPerfTelecomInputClientPast15StatHistoryPort1Entry 10 }


pm10010ulhPerfTelecomInputClientPast15StatHistoryUasValuePort1 OBJECT-TYPE
	SYNTAX  Unsigned32
	MAX-ACCESS read-only
	STATUS current
	DESCRIPTION
        "
        Previous 15-min UAS counter :This 
        OID gives the previous 15-min UnAvailable 
        Second counter value
        "
	::= { pm10010ulhPerfTelecomInputClientPast15StatHistoryPort1Entry 11 }


--- *****************************************************
---     Leaf of the telecomInputClientCurrent24Stat
--- *****************************************************
--- *********************************************************
---     TABLE for the pm10010ulhPerfTelecomInputClientCurrent24Stat articles
--- *********************************************************

pm10010ulhPerfTelecomInputClientCurrent24StatTable OBJECT-TYPE
	SYNTAX  SEQUENCE OF Pm10010ulhPerfTelecomInputClientCurrent24StatEntry
	MAX-ACCESS not-accessible
	STATUS current
	DESCRIPTION
        "
        List of pm10010ulhPerfTelecomInputClientCurrent24Stat 
        Article
        "
	::= { pm10010ulhMonPerfClient 80 }


pm10010ulhPerfTelecomInputClientCurrent24StatEntry OBJECT-TYPE
	SYNTAX Pm10010ulhPerfTelecomInputClientCurrent24StatEntry
	MAX-ACCESS not-accessible
	STATUS current
	DESCRIPTION
        "
        Row definition for the pm10010ulhPerfTelecomInputClientCurrent24Stat 
        table
        "
	INDEX   { pm10010ulhPerfTelecomInputClientCurrent24StatIndex }
	::= { pm10010ulhPerfTelecomInputClientCurrent24StatTable 1 }


Pm10010ulhPerfTelecomInputClientCurrent24StatEntry ::=
	SEQUENCE {
	pm10010ulhPerfTelecomInputClientCurrent24StatIndex
		INTEGER,
	pm10010ulhPerfTelecomInputClientCurrent24StatInvCvPortn
		EkiOnOff,
	pm10010ulhPerfTelecomInputClientCurrent24StatCvValuePortn
		Unsigned32,
	pm10010ulhPerfTelecomInputClientCurrent24StatInvEsPortn
		EkiOnOff,
	pm10010ulhPerfTelecomInputClientCurrent24StatEsValuePortn
		Unsigned32,
	pm10010ulhPerfTelecomInputClientCurrent24StatInvSesPortn
		EkiOnOff,
	pm10010ulhPerfTelecomInputClientCurrent24StatSesValuePortn
		Unsigned32,
	pm10010ulhPerfTelecomInputClientCurrent24StatInvSefsPortn
		EkiOnOff,
	pm10010ulhPerfTelecomInputClientCurrent24StatSefsValuePortn
		Unsigned32,
	pm10010ulhPerfTelecomInputClientCurrent24StatInvUasPortn
		EkiOnOff,
	pm10010ulhPerfTelecomInputClientCurrent24StatUasValuePortn
		Unsigned32
	}


pm10010ulhPerfTelecomInputClientCurrent24StatIndex OBJECT-TYPE
	SYNTAX  INTEGER(0..128)
	MAX-ACCESS  read-only
	STATUS current
	DESCRIPTION
        "
        Index definition for the pm10010ulhPerfTelecomInputClientCurrent24Stat 
        table
        "
	::= { pm10010ulhPerfTelecomInputClientCurrent24StatEntry 1 }


pm10010ulhPerfTelecomInputClientCurrent24StatInvCvPortn OBJECT-TYPE
	SYNTAX  EkiOnOff
	MAX-ACCESS read-only
	STATUS current
	DESCRIPTION
        "
        Current 24-hours EBC counter inv. 
        :This OID indicates that the current 
        24-hours Coding Violation counter 
        is invalid
        "
	::= { pm10010ulhPerfTelecomInputClientCurrent24StatEntry 2 }


pm10010ulhPerfTelecomInputClientCurrent24StatCvValuePortn OBJECT-TYPE
	SYNTAX  Unsigned32
	MAX-ACCESS read-only
	STATUS current
	DESCRIPTION
        "
        Current 24-hours EBC counter :This 
        OID gives the current 24-hours
         Coding Violation counter value
        "
	::= { pm10010ulhPerfTelecomInputClientCurrent24StatEntry 3 }


pm10010ulhPerfTelecomInputClientCurrent24StatInvEsPortn OBJECT-TYPE
	SYNTAX  EkiOnOff
	MAX-ACCESS read-only
	STATUS current
	DESCRIPTION
        "
        Current 24-hours ES counter inv. 
        :This OID indicates that the current 
        24-hours Errored Second counter 
        is invalid
        "
	::= { pm10010ulhPerfTelecomInputClientCurrent24StatEntry 4 }


pm10010ulhPerfTelecomInputClientCurrent24StatEsValuePortn OBJECT-TYPE
	SYNTAX  Unsigned32
	MAX-ACCESS read-only
	STATUS current
	DESCRIPTION
        "
        Current 24-hours ES counter :This 
        OID gives the current 24-hours
         Errored Second counter value
        "
	::= { pm10010ulhPerfTelecomInputClientCurrent24StatEntry 5 }


pm10010ulhPerfTelecomInputClientCurrent24StatInvSesPortn OBJECT-TYPE
	SYNTAX  EkiOnOff
	MAX-ACCESS read-only
	STATUS current
	DESCRIPTION
        "
        Current 24-hours SES counter inv. 
        :This OID indicates that the current 
        24-hours severely Errored Second 
        counter is invalid
        "
	::= { pm10010ulhPerfTelecomInputClientCurrent24StatEntry 6 }


pm10010ulhPerfTelecomInputClientCurrent24StatSesValuePortn OBJECT-TYPE
	SYNTAX  Unsigned32
	MAX-ACCESS read-only
	STATUS current
	DESCRIPTION
        "
        Current 24-hours SES counter :This 
        OID gives the current 24-hours
         severely Errored Second counter 
        value
        "
	::= { pm10010ulhPerfTelecomInputClientCurrent24StatEntry 7 }


pm10010ulhPerfTelecomInputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter 
        is invalid
        "
	::= { pm10010ulhPerfTelecomInputClientCurrent24StatEntry 8 }


pm10010ulhPerfTelecomInputClientCurrent24StatSefsValuePortn OBJECT-TYPE
	SYNTAX  Unsigned32
	MAX-ACCESS read-only
	STATUS current
	DESCRIPTION
        "
        Current 24-hours SEFS counter
         :This OID gives the current 24-hours 
        severely Errored Framing Second 
        counter value
        "
	::= { pm10010ulhPerfTelecomInputClientCurrent24StatEntry 9 }


pm10010ulhPerfTelecomInputClientCurrent24StatInvUasPortn OBJECT-TYPE
	SYNTAX  EkiOnOff
	MAX-ACCESS read-only
	STATUS current
	DESCRIPTION
        "
        Current 24-hours UAS counter inv. 
        :This OID indicates that the current 
        24-hours UnAvailable Second counter 
        is invalid
        "
	::= { pm10010ulhPerfTelecomInputClientCurrent24StatEntry 10 }


pm10010ulhPerfTelecomInputClientCurrent24StatUasValuePortn OBJECT-TYPE
	SYNTAX  Unsigned32
	MAX-ACCESS read-only
	STATUS current
	DESCRIPTION
        "
        Current 24-hours UAS counter :This 
        OID gives the current 24-hours
         UnAvailable Second counter value
        "
	::= { pm10010ulhPerfTelecomInputClientCurrent24StatEntry 11 }


--- *****************************************************
---     Leaf of the telecomInputClientPast24Stat
--- *****************************************************
--- *********************************************************
---     TABLE for the pm10010ulhPerfTelecomInputClientPast24StatHistory articles
--- *********************************************************

pm10010ulhPerfTelecomInputClientPast24StatHistoryPort1Table OBJECT-TYPE
	SYNTAX  SEQUENCE OF Pm10010ulhPerfTelecomInputClientPast24StatHistoryPort1Entry
	MAX-ACCESS not-accessible
	STATUS current
	DESCRIPTION
        "
        List of pm10010ulhPerfTelecomInputClientPast24StatHistory 
        Article
        "
	::= { pm10010ulhMonPerfClient 112 }


pm10010ulhPerfTelecomInputClientPast24StatHistoryPort1Entry OBJECT-TYPE
	SYNTAX Pm10010ulhPerfTelecomInputClientPast24StatHistoryPort1Entry
	MAX-ACCESS not-accessible
	STATUS current
	DESCRIPTION
        "
        Row definition for the pm10010ulhPerfTelecomInputClientPast24StatHistory 
        table
        "
	INDEX   { pm10010ulhPerfTelecomInputClientPast24StatHistoryPort1Index }
	::= { pm10010ulhPerfTelecomInputClientPast24StatHistoryPort1Table 1 }


Pm10010ulhPerfTelecomInputClientPast24StatHistoryPort1Entry ::=
	SEQUENCE {
	pm10010ulhPerfTelecomInputClientPast24StatHistoryPort1Index
		INTEGER,
	pm10010ulhPerfTelecomInputClientPast24StatHistoryInvCvPort1
		EkiOnOff,
	pm10010ulhPerfTelecomInputClientPast24StatHistoryCvValuePort1
		Unsigned32,
	pm10010ulhPerfTelecomInputClientPast24StatHistoryInvEsPort1
		EkiOnOff,
	pm10010ulhPerfTelecomInputClientPast24StatHistoryEsValuePort1
		Unsigned32,
	pm10010ulhPerfTelecomInputClientPast24StatHistoryInvSesPort1
		EkiOnOff,
	pm10010ulhPerfTelecomInputClientPast24StatHistorySesValuePort1
		Unsigned32,
	pm10010ulhPerfTelecomInputClientPast24StatHistoryInvSefsPort1
		EkiOnOff,
	pm10010ulhPerfTelecomInputClientPast24StatHistorySefsValuePort1
		Unsigned32,
	pm10010ulhPerfTelecomInputClientPast24StatHistoryInvUasPort1
		EkiOnOff,
	pm10010ulhPerfTelecomInputClientPast24StatHistoryUasValuePort1
		Unsigned32
	}


pm10010ulhPerfTelecomInputClientPast24StatHistoryPort1Index OBJECT-TYPE
	SYNTAX  INTEGER(0..128)
	MAX-ACCESS  read-only
	STATUS current
	DESCRIPTION
        "
        Index definition for the pm10010ulhPerfTelecomInputClientPast24StatHistory 
        table
        "
	::= { pm10010ulhPerfTelecomInputClientPast24StatHistoryPort1Entry 1 }


pm10010ulhPerfTelecomInputClientPast24StatHistoryInvCvPort1 OBJECT-TYPE
	SYNTAX  EkiOnOff
	MAX-ACCESS read-only
	STATUS current
	DESCRIPTION
        "
        Previous 24-hours EBC counter
         inv. :This OID indicates that
         the previous 24-hours Coding Violation 
        counter is invalid
        "
	::= { pm10010ulhPerfTelecomInputClientPast24StatHistoryPort1Entry 2 }


pm10010ulhPerfTelecomInputClientPast24StatHistoryCvValuePort1 OBJECT-TYPE
	SYNTAX  Unsigned32
	MAX-ACCESS read-only
	STATUS current
	DESCRIPTION
        "
        Previous 24-hours EBC counter
         :This OID gives the previous 24-hours 
        Coding Violation counter value
        "
	::= { pm10010ulhPerfTelecomInputClientPast24StatHistoryPort1Entry 3 }


pm10010ulhPerfTelecomInputClientPast24StatHistoryInvEsPort1 OBJECT-TYPE
	SYNTAX  EkiOnOff
	MAX-ACCESS read-only
	STATUS current
	DESCRIPTION
        "
        Previous 24-hours ES counter inv. 
        :This OID indicates that the previous 
        24-hours Errored Second counter 
        is invalid
        "
	::= { pm10010ulhPerfTelecomInputClientPast24StatHistoryPort1Entry 4 }


pm10010ulhPerfTelecomInputClientPast24StatHistoryEsValuePort1 OBJECT-TYPE
	SYNTAX  Unsigned32
	MAX-ACCESS read-only
	STATUS current
	DESCRIPTION
        "
        Previous 24-hours ES counter :This 
        OID gives the previous 24-hours 
        Errored Second counter value
        "
	::= { pm10010ulhPerfTelecomInputClientPast24StatHistoryPort1Entry 5 }


pm10010ulhPerfTelecomInputClientPast24StatHistoryInvSesPort1 OBJECT-TYPE
	SYNTAX  EkiOnOff
	MAX-ACCESS read-only
	STATUS current
	DESCRIPTION
        "
        Previous 24-hours SES counter
         inv. :This OID indicates that
         the previous 24-hours severely 
        Errored Second counter is invalid
        "
	::= { pm10010ulhPerfTelecomInputClientPast24StatHistoryPort1Entry 6 }


pm10010ulhPerfTelecomInputClientPast24StatHistorySesValuePort1 OBJECT-TYPE
	SYNTAX  Unsigned32
	MAX-ACCESS read-only
	STATUS current
	DESCRIPTION
        "
        Previous 24-hours SES counter
         :This OID gives the previous 24-hours 
        severely Errored Second counter 
        value
        "
	::= { pm10010ulhPerfTelecomInputClientPast24StatHistoryPort1Entry 7 }


pm10010ulhPerfTelecomInputClientPast24StatHistoryInvSefsPort1 OBJECT-TYPE
	SYNTAX  EkiOnOff
	MAX-ACCESS read-only
	STATUS current
	DESCRIPTION
        "
        Previous 24-hours SEFS counter 
        inv. :This OID indicates that the 
        previous 24-hours severely Errored 
        Framing Second counter is invalid
        "
	::= { pm10010ulhPerfTelecomInputClientPast24StatHistoryPort1Entry 8 }


pm10010ulhPerfTelecomInputClientPast24StatHistorySefsValuePort1 OBJECT-TYPE
	SYNTAX  Unsigned32
	MAX-ACCESS read-only
	STATUS current
	DESCRIPTION
        "
        Previous 24-hours SEFS counter 
        :This OID gives the previous 24-hours 
        severely Errored Framing Second 
        counter value
        "
	::= { pm10010ulhPerfTelecomInputClientPast24StatHistoryPort1Entry 9 }


pm10010ulhPerfTelecomInputClientPast24StatHistoryInvUasPort1 OBJECT-TYPE
	SYNTAX  EkiOnOff
	MAX-ACCESS read-only
	STATUS current
	DESCRIPTION
        "
        Previous 24-hours UAS counter
         inv. :This OID indicates that
         the previous 24-hours UnAvailable 
        Second counter is invalid
        "
	::= { pm10010ulhPerfTelecomInputClientPast24StatHistoryPort1Entry 10 }


pm10010ulhPerfTelecomInputClientPast24StatHistoryUasValuePort1 OBJECT-TYPE
	SYNTAX  Unsigned32
	MAX-ACCESS read-only
	STATUS current
	DESCRIPTION
        "
        Previous 24-hours UAS counter
         :This OID gives the previous 24-hours 
        UnAvailable Second counter value
        "
	::= { pm10010ulhPerfTelecomInputClientPast24StatHistoryPort1Entry 11 }


--- *****************************************************
---     Leaf of the telecomOutputClientCurrent15Stat
--- *****************************************************
--- *********************************************************
---     TABLE for the pm10010ulhPerfTelecomOutputClientCurrent15Stat articles
--- *********************************************************

pm10010ulhPerfTelecomOutputClientCurrent15StatTable OBJECT-TYPE
	SYNTAX  SEQUENCE OF Pm10010ulhPerfTelecomOutputClientCurrent15StatEntry
	MAX-ACCESS not-accessible
	STATUS current
	DESCRIPTION
        "
        List of pm10010ulhPerfTelecomOutputClientCurrent15Stat 
        Article
        "
	::= { pm10010ulhMonPerfClient 144 }


pm10010ulhPerfTelecomOutputClientCurrent15StatEntry OBJECT-TYPE
	SYNTAX Pm10010ulhPerfTelecomOutputClientCurrent15StatEntry
	MAX-ACCESS not-accessible
	STATUS current
	DESCRIPTION
        "
        Row definition for the pm10010ulhPerfTelecomOutputClientCurrent15Stat 
        table
        "
	INDEX   { pm10010ulhPerfTelecomOutputClientCurrent15StatIndex }
	::= { pm10010ulhPerfTelecomOutputClientCurrent15StatTable 1 }


Pm10010ulhPerfTelecomOutputClientCurrent15StatEntry ::=
	SEQUENCE {
	pm10010ulhPerfTelecomOutputClientCurrent15StatIndex
		INTEGER,
	pm10010ulhPerfTelecomOutputClientCurrent15StatInvCvPortn
		EkiOnOff,
	pm10010ulhPerfTelecomOutputClientCurrent15StatCvValuePortn
		Unsigned32,
	pm10010ulhPerfTelecomOutputClientCurrent15StatInvEsPortn
		EkiOnOff,
	pm10010ulhPerfTelecomOutputClientCurrent15StatEsValuePortn
		Unsigned32,
	pm10010ulhPerfTelecomOutputClientCurrent15StatInvSesPortn
		EkiOnOff,
	pm10010ulhPerfTelecomOutputClientCurrent15StatSesValuePortn
		Unsigned32,
	pm10010ulhPerfTelecomOutputClientCurrent15StatInvSefsPortn
		EkiOnOff,
	pm10010ulhPerfTelecomOutputClientCurrent15StatSefsValuePortn
		Unsigned32,
	pm10010ulhPerfTelecomOutputClientCurrent15StatInvUasPortn
		EkiOnOff,
	pm10010ulhPerfTelecomOutputClientCurrent15StatUasValuePortn
		Unsigned32
	}


pm10010ulhPerfTelecomOutputClientCurrent15StatIndex OBJECT-TYPE
	SYNTAX  INTEGER(0..128)
	MAX-ACCESS  read-only
	STATUS current
	DESCRIPTION
        "
        Index definition for the pm10010ulhPerfTelecomOutputClientCurrent15Stat 
        table
        "
	::= { pm10010ulhPerfTelecomOutputClientCurrent15StatEntry 1 }


pm10010ulhPerfTelecomOutputClientCurrent15StatInvCvPortn OBJECT-TYPE
	SYNTAX  EkiOnOff
	MAX-ACCESS read-only
	STATUS current
	DESCRIPTION
        "
        Current 15-min EBC counter inv. 
        :This OID indicates that the current 
        15-min Coding Violation counter 
        is invalid
        "
	::= { pm10010ulhPerfTelecomOutputClientCurrent15StatEntry 2 }


pm10010ulhPerfTelecomOutputClientCurrent15StatCvValuePortn OBJECT-TYPE
	SYNTAX  Unsigned32
	MAX-ACCESS read-only
	STATUS current
	DESCRIPTION
        "
        Current 15-min EBC counter :This 
        OID gives the current 15-min Coding 
        Violation counter value
        "
	::= { pm10010ulhPerfTelecomOutputClientCurrent15StatEntry 3 }


pm10010ulhPerfTelecomOutputClientCurrent15StatInvEsPortn OBJECT-TYPE
	SYNTAX  EkiOnOff
	MAX-ACCESS read-only
	STATUS current
	DESCRIPTION
        "
        Current 15-min ES counter inv. 
        :This OID indicates that the current 
        15-min Errored Second counter is 
        invalid
        "
	::= { pm10010ulhPerfTelecomOutputClientCurrent15StatEntry 4 }


pm10010ulhPerfTelecomOutputClientCurrent15StatEsValuePortn OBJECT-TYPE
	SYNTAX  Unsigned32
	MAX-ACCESS read-only
	STATUS current
	DESCRIPTION
        "
        Current 15-min ES counter :This 
        OID gives the current 15-min Errored 
        Second counter value
        "
	::= { pm10010ulhPerfTelecomOutputClientCurrent15StatEntry 5 }


pm10010ulhPerfTelecomOutputClientCurrent15StatInvSesPortn OBJECT-TYPE
	SYNTAX  EkiOnOff
	MAX-ACCESS read-only
	STATUS current
	DESCRIPTION
        "
        Current 15-min SES counter inv. 
        :This OID indicates that the current 
        15-min severely Errored Second
         counter is invalid
        "
	::= { pm10010ulhPerfTelecomOutputClientCurrent15StatEntry 6 }


pm10010ulhPerfTelecomOutputClientCurrent15StatSesValuePortn OBJECT-TYPE
	SYNTAX  Unsigned32
	MAX-ACCESS read-only
	STATUS current
	DESCRIPTION
        "
        Current 15-min SES counter :This 
        OID gives the current 15-min severely 
        Errored Second counter value
        "
	::= { pm10010ulhPerfTelecomOutputClientCurrent15StatEntry 7 }


pm10010ulhPerfTelecomOutputClientCurrent15StatInvSefsPortn OBJECT-TYPE
	SYNTAX  EkiOnOff
	MAX-ACCESS read-only
	STATUS current
	DESCRIPTION
        "
        Current 15-min SEFS counter inv. 
        :This OID indicates that the current 
        15-min severely Errored Framing 
        Second counter is invalid
        "
	::= { pm10010ulhPerfTelecomOutputClientCurrent15StatEntry 8 }


pm10010ulhPerfTelecomOutputClientCurrent15StatSefsValuePortn OBJECT-TYPE
	SYNTAX  Unsigned32
	MAX-ACCESS read-only
	STATUS current
	DESCRIPTION
        "
        Current 15-min SEFS counter :This 
        OID gives the current 15-min severely 
        Errored Framing Second counter
         value
        "
	::= { pm10010ulhPerfTelecomOutputClientCurrent15StatEntry 9 }


pm10010ulhPerfTelecomOutputClientCurrent15StatInvUasPortn OBJECT-TYPE
	SYNTAX  EkiOnOff
	MAX-ACCESS read-only
	STATUS current
	DESCRIPTION
        "
        Current 15-min UAS counter inv. 
        :This OID indicates that the current 
        15-min UnAvailable Second counter 
        is invalid
        "
	::= { pm10010ulhPerfTelecomOutputClientCurrent15StatEntry 10 }


pm10010ulhPerfTelecomOutputClientCurrent15StatUasValuePortn OBJECT-TYPE
	SYNTAX  Unsigned32
	MAX-ACCESS read-only
	STATUS current
	DESCRIPTION
        "
        Current 15-min UAS counter :This 
        OID gives the current 15-min UnAvailable 
        Second counter value
        "
	::= { pm10010ulhPerfTelecomOutputClientCurrent15StatEntry 11 }


--- *****************************************************
---     Leaf of the telecomOutputClientPast15Stat
--- *****************************************************
--- *********************************************************
---     TABLE for the pm10010ulhPerfTelecomOutputClientPast15StatHistory articles
--- *********************************************************

pm10010ulhPerfTelecomOutputClientPast15StatHistoryPort1Table OBJECT-TYPE
	SYNTAX  SEQUENCE OF Pm10010ulhPerfTelecomOutputClientPast15StatHistoryPort1Entry
	MAX-ACCESS not-accessible
	STATUS current
	DESCRIPTION
        "
        List of pm10010ulhPerfTelecomOutputClientPast15StatHistory 
        Article
        "
	::= { pm10010ulhMonPerfClient 176 }


pm10010ulhPerfTelecomOutputClientPast15StatHistoryPort1Entry OBJECT-TYPE
	SYNTAX Pm10010ulhPerfTelecomOutputClientPast15StatHistoryPort1Entry
	MAX-ACCESS not-accessible
	STATUS current
	DESCRIPTION
        "
        Row definition for the pm10010ulhPerfTelecomOutputClientPast15StatHistory 
        table
        "
	INDEX   { pm10010ulhPerfTelecomOutputClientPast15StatHistoryPort1Index }
	::= { pm10010ulhPerfTelecomOutputClientPast15StatHistoryPort1Table 1 }


Pm10010ulhPerfTelecomOutputClientPast15StatHistoryPort1Entry ::=
	SEQUENCE {
	pm10010ulhPerfTelecomOutputClientPast15StatHistoryPort1Index
		INTEGER,
	pm10010ulhPerfTelecomOutputClientPast15StatHistoryInvCvPort1
		EkiOnOff,
	pm10010ulhPerfTelecomOutputClientPast15StatHistoryCvValuePort1
		Unsigned32,
	pm10010ulhPerfTelecomOutputClientPast15StatHistoryInvEsPort1
		EkiOnOff,
	pm10010ulhPerfTelecomOutputClientPast15StatHistoryEsValuePort1
		Unsigned32,
	pm10010ulhPerfTelecomOutputClientPast15StatHistoryInvSesPort1
		EkiOnOff,
	pm10010ulhPerfTelecomOutputClientPast15StatHistorySesValuePort1
		Unsigned32,
	pm10010ulhPerfTelecomOutputClientPast15StatHistoryInvSefsPort1
		EkiOnOff,
	pm10010ulhPerfTelecomOutputClientPast15StatHistorySefsValuePort1
		Unsigned32,
	pm10010ulhPerfTelecomOutputClientPast15StatHistoryInvUasPort1
		EkiOnOff,
	pm10010ulhPerfTelecomOutputClientPast15StatHistoryUasValuePort1
		Unsigned32
	}


pm10010ulhPerfTelecomOutputClientPast15StatHistoryPort1Index OBJECT-TYPE
	SYNTAX  INTEGER(0..128)
	MAX-ACCESS  read-only
	STATUS current
	DESCRIPTION
        "
        Index definition for the pm10010ulhPerfTelecomOutputClientPast15StatHistory 
        table
        "
	::= { pm10010ulhPerfTelecomOutputClientPast15StatHistoryPort1Entry 1 }


pm10010ulhPerfTelecomOutputClientPast15StatHistoryInvCvPort1 OBJECT-TYPE
	SYNTAX  EkiOnOff
	MAX-ACCESS read-only
	STATUS current
	DESCRIPTION
        "
        Previous 15-min EBC counter inv. 
        :This OID indicates that the previous 
        15-min Coding Violation counter 
        is invalid
        "
	::= { pm10010ulhPerfTelecomOutputClientPast15StatHistoryPort1Entry 2 }


pm10010ulhPerfTelecomOutputClientPast15StatHistoryCvValuePort1 OBJECT-TYPE
	SYNTAX  Unsigned32
	MAX-ACCESS read-only
	STATUS current
	DESCRIPTION
        "
        Previous 15-min EBC counter :This 
        OID gives the previous 15-min Coding 
        Violation counter value
        "
	::= { pm10010ulhPerfTelecomOutputClientPast15StatHistoryPort1Entry 3 }


pm10010ulhPerfTelecomOutputClientPast15StatHistoryInvEsPort1 OBJECT-TYPE
	SYNTAX  EkiOnOff
	MAX-ACCESS read-only
	STATUS current
	DESCRIPTION
        "
        Previous 15-min ES counter inv. 
        :This OID indicates that the previous 
        15-min Errored Second counter is 
        invalid
        "
	::= { pm10010ulhPerfTelecomOutputClientPast15StatHistoryPort1Entry 4 }


pm10010ulhPerfTelecomOutputClientPast15StatHistoryEsValuePort1 OBJECT-TYPE
	SYNTAX  Unsigned32
	MAX-ACCESS read-only
	STATUS current
	DESCRIPTION
        "
        Previous 15-min ES counter :This 
        OID gives the previous 15-min Errored 
        Second counter value
        "
	::= { pm10010ulhPerfTelecomOutputClientPast15StatHistoryPort1Entry 5 }


pm10010ulhPerfTelecomOutputClientPast15StatHistoryInvSesPort1 OBJECT-TYPE
	SYNTAX  EkiOnOff
	MAX-ACCESS read-only
	STATUS current
	DESCRIPTION
        "
        Previous 15-min SES counter inv. 
        :This OID indicates that the previous 
        15-min severely Errored Second
         counter is invalid
        "
	::= { pm10010ulhPerfTelecomOutputClientPast15StatHistoryPort1Entry 6 }


pm10010ulhPerfTelecomOutputClientPast15StatHistorySesValuePort1 OBJECT-TYPE
	SYNTAX  Unsigned32
	MAX-ACCESS read-only
	STATUS current
	DESCRIPTION
        "
        Previous 15-min SES counter :This 
        OID gives the previous 15-min severely 
        Errored Second counter value
        "
	::= { pm10010ulhPerfTelecomOutputClientPast15StatHistoryPort1Entry 7 }


pm10010ulhPerfTelecomOutputClientPast15StatHistoryInvSefsPort1 OBJECT-TYPE
	SYNTAX  EkiOnOff
	MAX-ACCESS read-only
	STATUS current
	DESCRIPTION
        "
        Previous 15-min SEFS counter inv. 
        :This OID indicates that the previous 
        15-min severely Errored Framing 
        Second counter is invalid
        "
	::= { pm10010ulhPerfTelecomOutputClientPast15StatHistoryPort1Entry 8 }


pm10010ulhPerfTelecomOutputClientPast15StatHistorySefsValuePort1 OBJECT-TYPE
	SYNTAX  Unsigned32
	MAX-ACCESS read-only
	STATUS current
	DESCRIPTION
        "
        Previous 15-min SEFS counter :This 
        OID gives the previous 15-min severely 
        Errored Framing Second counter
         value
        "
	::= { pm10010ulhPerfTelecomOutputClientPast15StatHistoryPort1Entry 9 }


pm10010ulhPerfTelecomOutputClientPast15StatHistoryInvUasPort1 OBJECT-TYPE
	SYNTAX  EkiOnOff
	MAX-ACCESS read-only
	STATUS current
	DESCRIPTION
        "
        Previous 15-min UAS counter inv. 
        :This OID indicates that the previous 
        15-min UnAvailable Second counter 
        is invalid
        "
	::= { pm10010ulhPerfTelecomOutputClientPast15StatHistoryPort1Entry 10 }


pm10010ulhPerfTelecomOutputClientPast15StatHistoryUasValuePort1 OBJECT-TYPE
	SYNTAX  Unsigned32
	MAX-ACCESS read-only
	STATUS current
	DESCRIPTION
        "
        Previous 15-min UAS counter :This 
        OID gives the previous 15-min UnAvailable 
        Second counter value
        "
	::= { pm10010ulhPerfTelecomOutputClientPast15StatHistoryPort1Entry 11 }


--- *****************************************************
---     Leaf of the telecomOutputClientCurrent24Stat
--- *****************************************************
--- *********************************************************
---     TABLE for the pm10010ulhPerfTelecomOutputClientCurrent24Stat articles
--- *********************************************************

pm10010ulhPerfTelecomOutputClientCurrent24StatTable OBJECT-TYPE
	SYNTAX  SEQUENCE OF Pm10010ulhPerfTelecomOutputClientCurrent24StatEntry
	MAX-ACCESS not-accessible
	STATUS current
	DESCRIPTION
        "
        List of pm10010ulhPerfTelecomOutputClientCurrent24Stat 
        Article
        "
	::= { pm10010ulhMonPerfClient 208 }


pm10010ulhPerfTelecomOutputClientCurrent24StatEntry OBJECT-TYPE
	SYNTAX Pm10010ulhPerfTelecomOutputClientCurrent24StatEntry
	MAX-ACCESS not-accessible
	STATUS current
	DESCRIPTION
        "
        Row definition for the pm10010ulhPerfTelecomOutputClientCurrent24Stat 
        table
        "
	INDEX   { pm10010ulhPerfTelecomOutputClientCurrent24StatIndex }
	::= { pm10010ulhPerfTelecomOutputClientCurrent24StatTable 1 }


Pm10010ulhPerfTelecomOutputClientCurrent24StatEntry ::=
	SEQUENCE {
	pm10010ulhPerfTelecomOutputClientCurrent24StatIndex
		INTEGER,
	pm10010ulhPerfTelecomOutputClientCurrent24StatInvCvPortn
		EkiOnOff,
	pm10010ulhPerfTelecomOutputClientCurrent24StatCvValuePortn
		Unsigned32,
	pm10010ulhPerfTelecomOutputClientCurrent24StatInvEsPortn
		EkiOnOff,
	pm10010ulhPerfTelecomOutputClientCurrent24StatEsValuePortn
		Unsigned32,
	pm10010ulhPerfTelecomOutputClientCurrent24StatInvSesPortn
		EkiOnOff,
	pm10010ulhPerfTelecomOutputClientCurrent24StatSesValuePortn
		Unsigned32,
	pm10010ulhPerfTelecomOutputClientCurrent24StatInvSefsPortn
		EkiOnOff,
	pm10010ulhPerfTelecomOutputClientCurrent24StatSefsValuePortn
		Unsigned32,
	pm10010ulhPerfTelecomOutputClientCurrent24StatInvUasPortn
		EkiOnOff,
	pm10010ulhPerfTelecomOutputClientCurrent24StatUasValuePortn
		Unsigned32
	}


pm10010ulhPerfTelecomOutputClientCurrent24StatIndex OBJECT-TYPE
	SYNTAX  INTEGER(0..128)
	MAX-ACCESS  read-only
	STATUS current
	DESCRIPTION
        "
        Index definition for the pm10010ulhPerfTelecomOutputClientCurrent24Stat 
        table
        "
	::= { pm10010ulhPerfTelecomOutputClientCurrent24StatEntry 1 }


pm10010ulhPerfTelecomOutputClientCurrent24StatInvCvPortn OBJECT-TYPE
	SYNTAX  EkiOnOff
	MAX-ACCESS read-only
	STATUS current
	DESCRIPTION
        "
        Current 24-hours EBC counter inv. 
        :This OID indicates that the current 
        24-hours Coding Violation counter 
        is invalid
        "
	::= { pm10010ulhPerfTelecomOutputClientCurrent24StatEntry 2 }


pm10010ulhPerfTelecomOutputClientCurrent24StatCvValuePortn OBJECT-TYPE
	SYNTAX  Unsigned32
	MAX-ACCESS read-only
	STATUS current
	DESCRIPTION
        "
        Current 24-hours EBC counter :This 
        OID gives the current 24-hours
         Coding Violation counter value
        "
	::= { pm10010ulhPerfTelecomOutputClientCurrent24StatEntry 3 }


pm10010ulhPerfTelecomOutputClientCurrent24StatInvEsPortn OBJECT-TYPE
	SYNTAX  EkiOnOff
	MAX-ACCESS read-only
	STATUS current
	DESCRIPTION
        "
        Current 24-hours ES counter inv. 
        :This OID indicates that the current 
        24-hours Errored Second counter 
        is invalid
        "
	::= { pm10010ulhPerfTelecomOutputClientCurrent24StatEntry 4 }


pm10010ulhPerfTelecomOutputClientCurrent24StatEsValuePortn OBJECT-TYPE
	SYNTAX  Unsigned32
	MAX-ACCESS read-only
	STATUS current
	DESCRIPTION
        "
        Current 24-hours ES counter :This 
        OID gives the current 24-hours
         Errored Second counter value
        "
	::= { pm10010ulhPerfTelecomOutputClientCurrent24StatEntry 5 }


pm10010ulhPerfTelecomOutputClientCurrent24StatInvSesPortn OBJECT-TYPE
	SYNTAX  EkiOnOff
	MAX-ACCESS read-only
	STATUS current
	DESCRIPTION
        "
        Current 24-hours SES counter inv. 
        :This OID indicates that the current 
        24-hours severely Errored Second 
        counter is invalid
        "
	::= { pm10010ulhPerfTelecomOutputClientCurrent24StatEntry 6 }


pm10010ulhPerfTelecomOutputClientCurrent24StatSesValuePortn OBJECT-TYPE
	SYNTAX  Unsigned32
	MAX-ACCESS read-only
	STATUS current
	DESCRIPTION
        "
        Current 24-hours SES counter :This 
        OID gives the current 24-hours
         severely Errored Second counter 
        value
        "
	::= { pm10010ulhPerfTelecomOutputClientCurrent24StatEntry 7 }


pm10010ulhPerfTelecomOutputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter 
        is invalid
        "
	::= { pm10010ulhPerfTelecomOutputClientCurrent24StatEntry 8 }


pm10010ulhPerfTelecomOutputClientCurrent24StatSefsValuePortn OBJECT-TYPE
	SYNTAX  Unsigned32
	MAX-ACCESS read-only
	STATUS current
	DESCRIPTION
        "
        Current 24-hours SEFS counter
         :This OID gives the current 24-hours 
        severely Errored Framing Second 
        counter value
        "
	::= { pm10010ulhPerfTelecomOutputClientCurrent24StatEntry 9 }


pm10010ulhPerfTelecomOutputClientCurrent24StatInvUasPortn OBJECT-TYPE
	SYNTAX  EkiOnOff
	MAX-ACCESS read-only
	STATUS current
	DESCRIPTION
        "
        Current 24-hours UAS counter inv. 
        :This OID indicates that the current 
        24-hours UnAvailable Second counter 
        is invalid
        "
	::= { pm10010ulhPerfTelecomOutputClientCurrent24StatEntry 10 }


pm10010ulhPerfTelecomOutputClientCurrent24StatUasValuePortn OBJECT-TYPE
	SYNTAX  Unsigned32
	MAX-ACCESS read-only
	STATUS current
	DESCRIPTION
        "
        Current 24-hours UAS counter :This 
        OID gives the current 24-hours
         UnAvailable Second counter value
        "
	::= { pm10010ulhPerfTelecomOutputClientCurrent24StatEntry 11 }


--- *****************************************************
---     Leaf of the telecomOutputClientPast24Stat
--- *****************************************************
--- *********************************************************
---     TABLE for the pm10010ulhPerfTelecomOutputClientPast24StatHistory articles
--- *********************************************************

pm10010ulhPerfTelecomOutputClientPast24StatHistoryPort1Table OBJECT-TYPE
	SYNTAX  SEQUENCE OF Pm10010ulhPerfTelecomOutputClientPast24StatHistoryPort1Entry
	MAX-ACCESS not-accessible
	STATUS current
	DESCRIPTION
        "
        List of pm10010ulhPerfTelecomOutputClientPast24StatHistory 
        Article
        "
	::= { pm10010ulhMonPerfClient 240 }


pm10010ulhPerfTelecomOutputClientPast24StatHistoryPort1Entry OBJECT-TYPE
	SYNTAX Pm10010ulhPerfTelecomOutputClientPast24StatHistoryPort1Entry
	MAX-ACCESS not-accessible
	STATUS current
	DESCRIPTION
        "
        Row definition for the pm10010ulhPerfTelecomOutputClientPast24StatHistory 
        table
        "
	INDEX   { pm10010ulhPerfTelecomOutputClientPast24StatHistoryPort1Index }
	::= { pm10010ulhPerfTelecomOutputClientPast24StatHistoryPort1Table 1 }


Pm10010ulhPerfTelecomOutputClientPast24StatHistoryPort1Entry ::=
	SEQUENCE {
	pm10010ulhPerfTelecomOutputClientPast24StatHistoryPort1Index
		INTEGER,
	pm10010ulhPerfTelecomOutputClientPast24StatHistoryInvCvPort1
		EkiOnOff,
	pm10010ulhPerfTelecomOutputClientPast24StatHistoryCvValuePort1
		Unsigned32,
	pm10010ulhPerfTelecomOutputClientPast24StatHistoryInvEsPort1
		EkiOnOff,
	pm10010ulhPerfTelecomOutputClientPast24StatHistoryEsValuePort1
		Unsigned32,
	pm10010ulhPerfTelecomOutputClientPast24StatHistoryInvSesPort1
		EkiOnOff,
	pm10010ulhPerfTelecomOutputClientPast24StatHistorySesValuePort1
		Unsigned32,
	pm10010ulhPerfTelecomOutputClientPast24StatHistoryInvSefsPort1
		EkiOnOff,
	pm10010ulhPerfTelecomOutputClientPast24StatHistorySefsValuePort1
		Unsigned32,
	pm10010ulhPerfTelecomOutputClientPast24StatHistoryInvUasPort1
		EkiOnOff,
	pm10010ulhPerfTelecomOutputClientPast24StatHistoryUasValuePort1
		Unsigned32
	}


pm10010ulhPerfTelecomOutputClientPast24StatHistoryPort1Index OBJECT-TYPE
	SYNTAX  INTEGER(0..128)
	MAX-ACCESS  read-only
	STATUS current
	DESCRIPTION
        "
        Index definition for the pm10010ulhPerfTelecomOutputClientPast24StatHistory 
        table
        "
	::= { pm10010ulhPerfTelecomOutputClientPast24StatHistoryPort1Entry 1 }


pm10010ulhPerfTelecomOutputClientPast24StatHistoryInvCvPort1 OBJECT-TYPE
	SYNTAX  EkiOnOff
	MAX-ACCESS read-only
	STATUS current
	DESCRIPTION
        "
        Previous 24-hours EBC counter
         inv. :This OID indicates that
         the previous 24-hours Coding Violation 
        counter is invalid
        "
	::= { pm10010ulhPerfTelecomOutputClientPast24StatHistoryPort1Entry 2 }


pm10010ulhPerfTelecomOutputClientPast24StatHistoryCvValuePort1 OBJECT-TYPE
	SYNTAX  Unsigned32
	MAX-ACCESS read-only
	STATUS current
	DESCRIPTION
        "
        Previous 24-hours EBC counter
         :This OID gives the previous 24-hours 
        Coding Violation counter value
        "
	::= { pm10010ulhPerfTelecomOutputClientPast24StatHistoryPort1Entry 3 }


pm10010ulhPerfTelecomOutputClientPast24StatHistoryInvEsPort1 OBJECT-TYPE
	SYNTAX  EkiOnOff
	MAX-ACCESS read-only
	STATUS current
	DESCRIPTION
        "
        Previous 24-hours ES counter inv. 
        :This OID indicates that the previous 
        24-hours Errored Second counter 
        is invalid
        "
	::= { pm10010ulhPerfTelecomOutputClientPast24StatHistoryPort1Entry 4 }


pm10010ulhPerfTelecomOutputClientPast24StatHistoryEsValuePort1 OBJECT-TYPE
	SYNTAX  Unsigned32
	MAX-ACCESS read-only
	STATUS current
	DESCRIPTION
        "
        Previous 24-hours ES counter :This 
        OID gives the previous 24-hours 
        Errored Second counter value
        "
	::= { pm10010ulhPerfTelecomOutputClientPast24StatHistoryPort1Entry 5 }


pm10010ulhPerfTelecomOutputClientPast24StatHistoryInvSesPort1 OBJECT-TYPE
	SYNTAX  EkiOnOff
	MAX-ACCESS read-only
	STATUS current
	DESCRIPTION
        "
        Previous 24-hours SES counter
         inv. :This OID indicates that
         the previous 24-hours severely 
        Errored Second counter is invalid
        "
	::= { pm10010ulhPerfTelecomOutputClientPast24StatHistoryPort1Entry 6 }


pm10010ulhPerfTelecomOutputClientPast24StatHistorySesValuePort1 OBJECT-TYPE
	SYNTAX  Unsigned32
	MAX-ACCESS read-only
	STATUS current
	DESCRIPTION
        "
        Previous 24-hours SES counter
         :This OID gives the previous 24-hours 
        severely Errored Second counter 
        value
        "
	::= { pm10010ulhPerfTelecomOutputClientPast24StatHistoryPort1Entry 7 }


pm10010ulhPerfTelecomOutputClientPast24StatHistoryInvSefsPort1 OBJECT-TYPE
	SYNTAX  EkiOnOff
	MAX-ACCESS read-only
	STATUS current
	DESCRIPTION
        "
        Previous 24-hours SEFS counter 
        inv. :This OID indicates that the 
        previous 24-hours severely Errored 
        Framing Second counter is invalid
        "
	::= { pm10010ulhPerfTelecomOutputClientPast24StatHistoryPort1Entry 8 }


pm10010ulhPerfTelecomOutputClientPast24StatHistorySefsValuePort1 OBJECT-TYPE
	SYNTAX  Unsigned32
	MAX-ACCESS read-only
	STATUS current
	DESCRIPTION
        "
        Previous 24-hours SEFS counter 
        :This OID gives the previous 24-hours 
        severely Errored Framing Second 
        counter value
        "
	::= { pm10010ulhPerfTelecomOutputClientPast24StatHistoryPort1Entry 9 }


pm10010ulhPerfTelecomOutputClientPast24StatHistoryInvUasPort1 OBJECT-TYPE
	SYNTAX  EkiOnOff
	MAX-ACCESS read-only
	STATUS current
	DESCRIPTION
        "
        Previous 24-hours UAS counter
         inv. :This OID indicates that
         the previous 24-hours UnAvailable 
        Second counter is invalid
        "
	::= { pm10010ulhPerfTelecomOutputClientPast24StatHistoryPort1Entry 10 }


pm10010ulhPerfTelecomOutputClientPast24StatHistoryUasValuePort1 OBJECT-TYPE
	SYNTAX  Unsigned32
	MAX-ACCESS read-only
	STATUS current
	DESCRIPTION
        "
        Previous 24-hours UAS counter
         :This OID gives the previous 24-hours 
        UnAvailable Second counter value
        "
	::= { pm10010ulhPerfTelecomOutputClientPast24StatHistoryPort1Entry 11 }


--- *****************************************************
---     Leaf of the telecomLinePostFecCurrent15Stat
--- *****************************************************
--- *********************************************************
---     TABLE for the pm10010ulhPerfTelecomLinePostFecCurrent15Stat articles
--- *********************************************************

pm10010ulhPerfTelecomLinePostFecCurrent15StatTable OBJECT-TYPE
	SYNTAX  SEQUENCE OF Pm10010ulhPerfTelecomLinePostFecCurrent15StatEntry
	MAX-ACCESS not-accessible
	STATUS current
	DESCRIPTION
        "
        List of pm10010ulhPerfTelecomLinePostFecCurrent15Stat 
        Article
        "
	::= { pm10010ulhMonPerfLine 336 }


pm10010ulhPerfTelecomLinePostFecCurrent15StatEntry OBJECT-TYPE
	SYNTAX Pm10010ulhPerfTelecomLinePostFecCurrent15StatEntry
	MAX-ACCESS not-accessible
	STATUS current
	DESCRIPTION
        "
        Row definition for the pm10010ulhPerfTelecomLinePostFecCurrent15Stat 
        table
        "
	INDEX   { pm10010ulhPerfTelecomLinePostFecCurrent15StatIndex }
	::= { pm10010ulhPerfTelecomLinePostFecCurrent15StatTable 1 }


Pm10010ulhPerfTelecomLinePostFecCurrent15StatEntry ::=
	SEQUENCE {
	pm10010ulhPerfTelecomLinePostFecCurrent15StatIndex
		INTEGER,
	pm10010ulhPerfTelecomLinePostFecCurrent15StatInvCvPortn
		EkiOnOff,
	pm10010ulhPerfTelecomLinePostFecCurrent15StatCvValuePortn
		Unsigned32,
	pm10010ulhPerfTelecomLinePostFecCurrent15StatInvEsPortn
		EkiOnOff,
	pm10010ulhPerfTelecomLinePostFecCurrent15StatEsValuePortn
		Unsigned32,
	pm10010ulhPerfTelecomLinePostFecCurrent15StatInvSesPortn
		EkiOnOff,
	pm10010ulhPerfTelecomLinePostFecCurrent15StatSesValuePortn
		Unsigned32,
	pm10010ulhPerfTelecomLinePostFecCurrent15StatInvSefsPortn
		EkiOnOff,
	pm10010ulhPerfTelecomLinePostFecCurrent15StatSefsValuePortn
		Unsigned32,
	pm10010ulhPerfTelecomLinePostFecCurrent15StatInvUasPortn
		EkiOnOff,
	pm10010ulhPerfTelecomLinePostFecCurrent15StatUasValuePortn
		Unsigned32
	}


pm10010ulhPerfTelecomLinePostFecCurrent15StatIndex OBJECT-TYPE
	SYNTAX  INTEGER(0..128)
	MAX-ACCESS  read-only
	STATUS current
	DESCRIPTION
        "
        Index definition for the pm10010ulhPerfTelecomLinePostFecCurrent15Stat 
        table
        "
	::= { pm10010ulhPerfTelecomLinePostFecCurrent15StatEntry 1 }


pm10010ulhPerfTelecomLinePostFecCurrent15StatInvCvPortn OBJECT-TYPE
	SYNTAX  EkiOnOff
	MAX-ACCESS read-only
	STATUS current
	DESCRIPTION
        "
        Current 15-min EBC counter inv. 
        :This OID indicates that the current 
        15-min Coding Violation counter 
        is invalid
        "
	::= { pm10010ulhPerfTelecomLinePostFecCurrent15StatEntry 2 }


pm10010ulhPerfTelecomLinePostFecCurrent15StatCvValuePortn OBJECT-TYPE
	SYNTAX  Unsigned32
	MAX-ACCESS read-only
	STATUS current
	DESCRIPTION
        "
        Current 15-min EBC counter :This 
        OID gives the current 15-min Coding 
        Violation counter value
        "
	::= { pm10010ulhPerfTelecomLinePostFecCurrent15StatEntry 3 }


pm10010ulhPerfTelecomLinePostFecCurrent15StatInvEsPortn OBJECT-TYPE
	SYNTAX  EkiOnOff
	MAX-ACCESS read-only
	STATUS current
	DESCRIPTION
        "
        Current 15-min ES counter inv. 
        :This OID indicates that the current 
        15-min Errored Second counter is 
        invalid
        "
	::= { pm10010ulhPerfTelecomLinePostFecCurrent15StatEntry 4 }


pm10010ulhPerfTelecomLinePostFecCurrent15StatEsValuePortn OBJECT-TYPE
	SYNTAX  Unsigned32
	MAX-ACCESS read-only
	STATUS current
	DESCRIPTION
        "
        Current 15-min ES counter :This 
        OID gives the current 15-min Errored 
        Second counter value
        "
	::= { pm10010ulhPerfTelecomLinePostFecCurrent15StatEntry 5 }


pm10010ulhPerfTelecomLinePostFecCurrent15StatInvSesPortn OBJECT-TYPE
	SYNTAX  EkiOnOff
	MAX-ACCESS read-only
	STATUS current
	DESCRIPTION
        "
        Current 15-min SES counter inv. 
        :This OID indicates that the current 
        15-min severely Errored Second
         counter is invalid
        "
	::= { pm10010ulhPerfTelecomLinePostFecCurrent15StatEntry 6 }


pm10010ulhPerfTelecomLinePostFecCurrent15StatSesValuePortn OBJECT-TYPE
	SYNTAX  Unsigned32
	MAX-ACCESS read-only
	STATUS current
	DESCRIPTION
        "
        Current 15-min SES counter :This 
        OID gives the current 15-min severely 
        Errored Second counter value
        "
	::= { pm10010ulhPerfTelecomLinePostFecCurrent15StatEntry 7 }


pm10010ulhPerfTelecomLinePostFecCurrent15StatInvSefsPortn OBJECT-TYPE
	SYNTAX  EkiOnOff
	MAX-ACCESS read-only
	STATUS current
	DESCRIPTION
        "
        Current 15-min SEFS counter inv. 
        :This OID indicates that the current 
        15-min severely Errored Framing 
        Second counter is invalid
        "
	::= { pm10010ulhPerfTelecomLinePostFecCurrent15StatEntry 8 }


pm10010ulhPerfTelecomLinePostFecCurrent15StatSefsValuePortn OBJECT-TYPE
	SYNTAX  Unsigned32
	MAX-ACCESS read-only
	STATUS current
	DESCRIPTION
        "
        Current 15-min SEFS counter :This 
        OID gives the current 15-min severely 
        Errored Framing Second counter
         value
        "
	::= { pm10010ulhPerfTelecomLinePostFecCurrent15StatEntry 9 }


pm10010ulhPerfTelecomLinePostFecCurrent15StatInvUasPortn OBJECT-TYPE
	SYNTAX  EkiOnOff
	MAX-ACCESS read-only
	STATUS current
	DESCRIPTION
        "
        Current 15-min UAS counter inv. 
        :This OID indicates that the current 
        15-min UnAvailable Second counter 
        is invalid
        "
	::= { pm10010ulhPerfTelecomLinePostFecCurrent15StatEntry 10 }


pm10010ulhPerfTelecomLinePostFecCurrent15StatUasValuePortn OBJECT-TYPE
	SYNTAX  Unsigned32
	MAX-ACCESS read-only
	STATUS current
	DESCRIPTION
        "
        Current 15-min UAS counter :This 
        OID gives the current 15-min UnAvailable 
        Second counter value
        "
	::= { pm10010ulhPerfTelecomLinePostFecCurrent15StatEntry 11 }


--- *****************************************************
---     Leaf of the telecomLinePostFecPast15Stat
--- *****************************************************
--- *********************************************************
---     TABLE for the pm10010ulhPerfTelecomLinePostFecPast15StatHistory articles
--- *********************************************************

pm10010ulhPerfTelecomLinePostFecPast15StatHistoryPort1Table OBJECT-TYPE
	SYNTAX  SEQUENCE OF Pm10010ulhPerfTelecomLinePostFecPast15StatHistoryPort1Entry
	MAX-ACCESS not-accessible
	STATUS current
	DESCRIPTION
        "
        List of pm10010ulhPerfTelecomLinePostFecPast15StatHistory 
        Article
        "
	::= { pm10010ulhMonPerfLine 337 }


pm10010ulhPerfTelecomLinePostFecPast15StatHistoryPort1Entry OBJECT-TYPE
	SYNTAX Pm10010ulhPerfTelecomLinePostFecPast15StatHistoryPort1Entry
	MAX-ACCESS not-accessible
	STATUS current
	DESCRIPTION
        "
        Row definition for the pm10010ulhPerfTelecomLinePostFecPast15StatHistory 
        table
        "
	INDEX   { pm10010ulhPerfTelecomLinePostFecPast15StatHistoryPort1Index }
	::= { pm10010ulhPerfTelecomLinePostFecPast15StatHistoryPort1Table 1 }


Pm10010ulhPerfTelecomLinePostFecPast15StatHistoryPort1Entry ::=
	SEQUENCE {
	pm10010ulhPerfTelecomLinePostFecPast15StatHistoryPort1Index
		INTEGER,
	pm10010ulhPerfTelecomLinePostFecPast15StatHistoryInvCvPort1
		EkiOnOff,
	pm10010ulhPerfTelecomLinePostFecPast15StatHistoryCvValuePort1
		Unsigned32,
	pm10010ulhPerfTelecomLinePostFecPast15StatHistoryInvEsPort1
		EkiOnOff,
	pm10010ulhPerfTelecomLinePostFecPast15StatHistoryEsValuePort1
		Unsigned32,
	pm10010ulhPerfTelecomLinePostFecPast15StatHistoryInvSesPort1
		EkiOnOff,
	pm10010ulhPerfTelecomLinePostFecPast15StatHistorySesValuePort1
		Unsigned32,
	pm10010ulhPerfTelecomLinePostFecPast15StatHistoryInvSefsPort1
		EkiOnOff,
	pm10010ulhPerfTelecomLinePostFecPast15StatHistorySefsValuePort1
		Unsigned32,
	pm10010ulhPerfTelecomLinePostFecPast15StatHistoryInvUasPort1
		EkiOnOff,
	pm10010ulhPerfTelecomLinePostFecPast15StatHistoryUasValuePort1
		Unsigned32
	}


pm10010ulhPerfTelecomLinePostFecPast15StatHistoryPort1Index OBJECT-TYPE
	SYNTAX  INTEGER(0..128)
	MAX-ACCESS  read-only
	STATUS current
	DESCRIPTION
        "
        Index definition for the pm10010ulhPerfTelecomLinePostFecPast15StatHistory 
        table
        "
	::= { pm10010ulhPerfTelecomLinePostFecPast15StatHistoryPort1Entry 1 }


pm10010ulhPerfTelecomLinePostFecPast15StatHistoryInvCvPort1 OBJECT-TYPE
	SYNTAX  EkiOnOff
	MAX-ACCESS read-only
	STATUS current
	DESCRIPTION
        "
        Previous 15-min EBC counter inv. 
        :This OID indicates that the previous 
        15-min Coding Violation counter 
        is invalid
        "
	::= { pm10010ulhPerfTelecomLinePostFecPast15StatHistoryPort1Entry 2 }


pm10010ulhPerfTelecomLinePostFecPast15StatHistoryCvValuePort1 OBJECT-TYPE
	SYNTAX  Unsigned32
	MAX-ACCESS read-only
	STATUS current
	DESCRIPTION
        "
        Previous 15-min EBC counter :This 
        OID gives the previous 15-min Coding 
        Violation counter value
        "
	::= { pm10010ulhPerfTelecomLinePostFecPast15StatHistoryPort1Entry 3 }


pm10010ulhPerfTelecomLinePostFecPast15StatHistoryInvEsPort1 OBJECT-TYPE
	SYNTAX  EkiOnOff
	MAX-ACCESS read-only
	STATUS current
	DESCRIPTION
        "
        Previous 15-min ES counter inv. 
        :This OID indicates that the previous 
        15-min Errored Second counter is 
        invalid
        "
	::= { pm10010ulhPerfTelecomLinePostFecPast15StatHistoryPort1Entry 4 }


pm10010ulhPerfTelecomLinePostFecPast15StatHistoryEsValuePort1 OBJECT-TYPE
	SYNTAX  Unsigned32
	MAX-ACCESS read-only
	STATUS current
	DESCRIPTION
        "
        Previous 15-min ES counter :This 
        OID gives the previous 15-min Errored 
        Second counter value
        "
	::= { pm10010ulhPerfTelecomLinePostFecPast15StatHistoryPort1Entry 5 }


pm10010ulhPerfTelecomLinePostFecPast15StatHistoryInvSesPort1 OBJECT-TYPE
	SYNTAX  EkiOnOff
	MAX-ACCESS read-only
	STATUS current
	DESCRIPTION
        "
        Previous 15-min SES counter inv. 
        :This OID indicates that the previous 
        15-min severely Errored Second
         counter is invalid
        "
	::= { pm10010ulhPerfTelecomLinePostFecPast15StatHistoryPort1Entry 6 }


pm10010ulhPerfTelecomLinePostFecPast15StatHistorySesValuePort1 OBJECT-TYPE
	SYNTAX  Unsigned32
	MAX-ACCESS read-only
	STATUS current
	DESCRIPTION
        "
        Previous 15-min SES counter :This 
        OID gives the previous 15-min severely 
        Errored Second counter value
        "
	::= { pm10010ulhPerfTelecomLinePostFecPast15StatHistoryPort1Entry 7 }


pm10010ulhPerfTelecomLinePostFecPast15StatHistoryInvSefsPort1 OBJECT-TYPE
	SYNTAX  EkiOnOff
	MAX-ACCESS read-only
	STATUS current
	DESCRIPTION
        "
        Previous 15-min SEFS counter inv. 
        :This OID indicates that the previous 
        15-min severely Errored Framing 
        Second counter is invalid
        "
	::= { pm10010ulhPerfTelecomLinePostFecPast15StatHistoryPort1Entry 8 }


pm10010ulhPerfTelecomLinePostFecPast15StatHistorySefsValuePort1 OBJECT-TYPE
	SYNTAX  Unsigned32
	MAX-ACCESS read-only
	STATUS current
	DESCRIPTION
        "
        Previous 15-min SEFS counter :This 
        OID gives the previous 15-min severely 
        Errored Framing Second counter
         value
        "
	::= { pm10010ulhPerfTelecomLinePostFecPast15StatHistoryPort1Entry 9 }


pm10010ulhPerfTelecomLinePostFecPast15StatHistoryInvUasPort1 OBJECT-TYPE
	SYNTAX  EkiOnOff
	MAX-ACCESS read-only
	STATUS current
	DESCRIPTION
        "
        Previous 15-min UAS counter inv. 
        :This OID indicates that the previous 
        15-min UnAvailable Second counter 
        is invalid
        "
	::= { pm10010ulhPerfTelecomLinePostFecPast15StatHistoryPort1Entry 10 }


pm10010ulhPerfTelecomLinePostFecPast15StatHistoryUasValuePort1 OBJECT-TYPE
	SYNTAX  Unsigned32
	MAX-ACCESS read-only
	STATUS current
	DESCRIPTION
        "
        Previous 15-min UAS counter :This 
        OID gives the previous 15-min UnAvailable 
        Second counter value
        "
	::= { pm10010ulhPerfTelecomLinePostFecPast15StatHistoryPort1Entry 11 }


--- *****************************************************
---     Leaf of the telecomLinePostFecCurrent24Stat
--- *****************************************************
--- *********************************************************
---     TABLE for the pm10010ulhPerfTelecomLinePostFecCurrent24Stat articles
--- *********************************************************

pm10010ulhPerfTelecomLinePostFecCurrent24StatTable OBJECT-TYPE
	SYNTAX  SEQUENCE OF Pm10010ulhPerfTelecomLinePostFecCurrent24StatEntry
	MAX-ACCESS not-accessible
	STATUS current
	DESCRIPTION
        "
        List of pm10010ulhPerfTelecomLinePostFecCurrent24Stat 
        Article
        "
	::= { pm10010ulhMonPerfLine 338 }


pm10010ulhPerfTelecomLinePostFecCurrent24StatEntry OBJECT-TYPE
	SYNTAX Pm10010ulhPerfTelecomLinePostFecCurrent24StatEntry
	MAX-ACCESS not-accessible
	STATUS current
	DESCRIPTION
        "
        Row definition for the pm10010ulhPerfTelecomLinePostFecCurrent24Stat 
        table
        "
	INDEX   { pm10010ulhPerfTelecomLinePostFecCurrent24StatIndex }
	::= { pm10010ulhPerfTelecomLinePostFecCurrent24StatTable 1 }


Pm10010ulhPerfTelecomLinePostFecCurrent24StatEntry ::=
	SEQUENCE {
	pm10010ulhPerfTelecomLinePostFecCurrent24StatIndex
		INTEGER,
	pm10010ulhPerfTelecomLinePostFecCurrent24StatInvCvPortn
		EkiOnOff,
	pm10010ulhPerfTelecomLinePostFecCurrent24StatCvValuePortn
		Unsigned32,
	pm10010ulhPerfTelecomLinePostFecCurrent24StatInvEsPortn
		EkiOnOff,
	pm10010ulhPerfTelecomLinePostFecCurrent24StatEsValuePortn
		Unsigned32,
	pm10010ulhPerfTelecomLinePostFecCurrent24StatInvSesPortn
		EkiOnOff,
	pm10010ulhPerfTelecomLinePostFecCurrent24StatSesValuePortn
		Unsigned32,
	pm10010ulhPerfTelecomLinePostFecCurrent24StatInvSefsPortn
		EkiOnOff,
	pm10010ulhPerfTelecomLinePostFecCurrent24StatSefsValuePortn
		Unsigned32,
	pm10010ulhPerfTelecomLinePostFecCurrent24StatInvUasPortn
		EkiOnOff,
	pm10010ulhPerfTelecomLinePostFecCurrent24StatUasValuePortn
		Unsigned32
	}


pm10010ulhPerfTelecomLinePostFecCurrent24StatIndex OBJECT-TYPE
	SYNTAX  INTEGER(0..128)
	MAX-ACCESS  read-only
	STATUS current
	DESCRIPTION
        "
        Index definition for the pm10010ulhPerfTelecomLinePostFecCurrent24Stat 
        table
        "
	::= { pm10010ulhPerfTelecomLinePostFecCurrent24StatEntry 1 }


pm10010ulhPerfTelecomLinePostFecCurrent24StatInvCvPortn OBJECT-TYPE
	SYNTAX  EkiOnOff
	MAX-ACCESS read-only
	STATUS current
	DESCRIPTION
        "
        Current 24-hours EBC counter inv. 
        :This OID indicates that the current 
        24-hours Coding Violation counter 
        is invalid
        "
	::= { pm10010ulhPerfTelecomLinePostFecCurrent24StatEntry 2 }


pm10010ulhPerfTelecomLinePostFecCurrent24StatCvValuePortn OBJECT-TYPE
	SYNTAX  Unsigned32
	MAX-ACCESS read-only
	STATUS current
	DESCRIPTION
        "
        Current 24-hours EBC counter :This 
        OID gives the current 24-hours
         Coding Violation counter value
        "
	::= { pm10010ulhPerfTelecomLinePostFecCurrent24StatEntry 3 }


pm10010ulhPerfTelecomLinePostFecCurrent24StatInvEsPortn OBJECT-TYPE
	SYNTAX  EkiOnOff
	MAX-ACCESS read-only
	STATUS current
	DESCRIPTION
        "
        Current 24-hours ES counter inv. 
        :This OID indicates that the current 
        24-hours Errored Second counter 
        is invalid
        "
	::= { pm10010ulhPerfTelecomLinePostFecCurrent24StatEntry 4 }


pm10010ulhPerfTelecomLinePostFecCurrent24StatEsValuePortn OBJECT-TYPE
	SYNTAX  Unsigned32
	MAX-ACCESS read-only
	STATUS current
	DESCRIPTION
        "
        Current 24-hours ES counter :This 
        OID gives the current 24-hours
         Errored Second counter value
        "
	::= { pm10010ulhPerfTelecomLinePostFecCurrent24StatEntry 5 }


pm10010ulhPerfTelecomLinePostFecCurrent24StatInvSesPortn OBJECT-TYPE
	SYNTAX  EkiOnOff
	MAX-ACCESS read-only
	STATUS current
	DESCRIPTION
        "
        Current 24-hours SES counter inv. 
        :This OID indicates that the current 
        24-hours severely Errored Second 
        counter is invalid
        "
	::= { pm10010ulhPerfTelecomLinePostFecCurrent24StatEntry 6 }


pm10010ulhPerfTelecomLinePostFecCurrent24StatSesValuePortn OBJECT-TYPE
	SYNTAX  Unsigned32
	MAX-ACCESS read-only
	STATUS current
	DESCRIPTION
        "
        Current 24-hours SES counter :This 
        OID gives the current 24-hours
         severely Errored Second counter 
        value
        "
	::= { pm10010ulhPerfTelecomLinePostFecCurrent24StatEntry 7 }


pm10010ulhPerfTelecomLinePostFecCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter 
        is invalid
        "
	::= { pm10010ulhPerfTelecomLinePostFecCurrent24StatEntry 8 }


pm10010ulhPerfTelecomLinePostFecCurrent24StatSefsValuePortn OBJECT-TYPE
	SYNTAX  Unsigned32
	MAX-ACCESS read-only
	STATUS current
	DESCRIPTION
        "
        Current 24-hours SEFS counter
         :This OID gives the current 24-hours 
        severely Errored Framing Second 
        counter value
        "
	::= { pm10010ulhPerfTelecomLinePostFecCurrent24StatEntry 9 }


pm10010ulhPerfTelecomLinePostFecCurrent24StatInvUasPortn OBJECT-TYPE
	SYNTAX  EkiOnOff
	MAX-ACCESS read-only
	STATUS current
	DESCRIPTION
        "
        Current 24-hours UAS counter inv. 
        :This OID indicates that the current 
        24-hours UnAvailable Second counter 
        is invalid
        "
	::= { pm10010ulhPerfTelecomLinePostFecCurrent24StatEntry 10 }


pm10010ulhPerfTelecomLinePostFecCurrent24StatUasValuePortn OBJECT-TYPE
	SYNTAX  Unsigned32
	MAX-ACCESS read-only
	STATUS current
	DESCRIPTION
        "
        Current 24-hours UAS counter :This 
        OID gives the current 24-hours
         UnAvailable Second counter value
        "
	::= { pm10010ulhPerfTelecomLinePostFecCurrent24StatEntry 11 }


--- *****************************************************
---     Leaf of the telecomLinePostFecPast24Stat
--- *****************************************************
--- *********************************************************
---     TABLE for the pm10010ulhPerfTelecomLinePostFecPast24StatHistory articles
--- *********************************************************

pm10010ulhPerfTelecomLinePostFecPast24StatHistoryPort1Table OBJECT-TYPE
	SYNTAX  SEQUENCE OF Pm10010ulhPerfTelecomLinePostFecPast24StatHistoryPort1Entry
	MAX-ACCESS not-accessible
	STATUS current
	DESCRIPTION
        "
        List of pm10010ulhPerfTelecomLinePostFecPast24StatHistory 
        Article
        "
	::= { pm10010ulhMonPerfLine 339 }


pm10010ulhPerfTelecomLinePostFecPast24StatHistoryPort1Entry OBJECT-TYPE
	SYNTAX Pm10010ulhPerfTelecomLinePostFecPast24StatHistoryPort1Entry
	MAX-ACCESS not-accessible
	STATUS current
	DESCRIPTION
        "
        Row definition for the pm10010ulhPerfTelecomLinePostFecPast24StatHistory 
        table
        "
	INDEX   { pm10010ulhPerfTelecomLinePostFecPast24StatHistoryPort1Index }
	::= { pm10010ulhPerfTelecomLinePostFecPast24StatHistoryPort1Table 1 }


Pm10010ulhPerfTelecomLinePostFecPast24StatHistoryPort1Entry ::=
	SEQUENCE {
	pm10010ulhPerfTelecomLinePostFecPast24StatHistoryPort1Index
		INTEGER,
	pm10010ulhPerfTelecomLinePostFecPast24StatHistoryInvCvPort1
		EkiOnOff,
	pm10010ulhPerfTelecomLinePostFecPast24StatHistoryCvValuePort1
		Unsigned32,
	pm10010ulhPerfTelecomLinePostFecPast24StatHistoryInvEsPort1
		EkiOnOff,
	pm10010ulhPerfTelecomLinePostFecPast24StatHistoryEsValuePort1
		Unsigned32,
	pm10010ulhPerfTelecomLinePostFecPast24StatHistoryInvSesPort1
		EkiOnOff,
	pm10010ulhPerfTelecomLinePostFecPast24StatHistorySesValuePort1
		Unsigned32,
	pm10010ulhPerfTelecomLinePostFecPast24StatHistoryInvSefsPort1
		EkiOnOff,
	pm10010ulhPerfTelecomLinePostFecPast24StatHistorySefsValuePort1
		Unsigned32,
	pm10010ulhPerfTelecomLinePostFecPast24StatHistoryInvUasPort1
		EkiOnOff,
	pm10010ulhPerfTelecomLinePostFecPast24StatHistoryUasValuePort1
		Unsigned32
	}


pm10010ulhPerfTelecomLinePostFecPast24StatHistoryPort1Index OBJECT-TYPE
	SYNTAX  INTEGER(0..128)
	MAX-ACCESS  read-only
	STATUS current
	DESCRIPTION
        "
        Index definition for the pm10010ulhPerfTelecomLinePostFecPast24StatHistory 
        table
        "
	::= { pm10010ulhPerfTelecomLinePostFecPast24StatHistoryPort1Entry 1 }


pm10010ulhPerfTelecomLinePostFecPast24StatHistoryInvCvPort1 OBJECT-TYPE
	SYNTAX  EkiOnOff
	MAX-ACCESS read-only
	STATUS current
	DESCRIPTION
        "
        Previous 24-hours EBC counter
         inv. :This OID indicates that
         the previous 24-hours Coding Violation 
        counter is invalid
        "
	::= { pm10010ulhPerfTelecomLinePostFecPast24StatHistoryPort1Entry 2 }


pm10010ulhPerfTelecomLinePostFecPast24StatHistoryCvValuePort1 OBJECT-TYPE
	SYNTAX  Unsigned32
	MAX-ACCESS read-only
	STATUS current
	DESCRIPTION
        "
        Previous 24-hours EBC counter
         :This OID gives the previous 24-hours 
        Coding Violation counter value
        "
	::= { pm10010ulhPerfTelecomLinePostFecPast24StatHistoryPort1Entry 3 }


pm10010ulhPerfTelecomLinePostFecPast24StatHistoryInvEsPort1 OBJECT-TYPE
	SYNTAX  EkiOnOff
	MAX-ACCESS read-only
	STATUS current
	DESCRIPTION
        "
        Previous 24-hours ES counter inv. 
        :This OID indicates that the previous 
        24-hours Errored Second counter 
        is invalid
        "
	::= { pm10010ulhPerfTelecomLinePostFecPast24StatHistoryPort1Entry 4 }


pm10010ulhPerfTelecomLinePostFecPast24StatHistoryEsValuePort1 OBJECT-TYPE
	SYNTAX  Unsigned32
	MAX-ACCESS read-only
	STATUS current
	DESCRIPTION
        "
        Previous 24-hours ES counter :This 
        OID gives the previous 24-hours 
        Errored Second counter value
        "
	::= { pm10010ulhPerfTelecomLinePostFecPast24StatHistoryPort1Entry 5 }


pm10010ulhPerfTelecomLinePostFecPast24StatHistoryInvSesPort1 OBJECT-TYPE
	SYNTAX  EkiOnOff
	MAX-ACCESS read-only
	STATUS current
	DESCRIPTION
        "
        Previous 24-hours SES counter
         inv. :This OID indicates that
         the previous 24-hours severely 
        Errored Second counter is invalid
        "
	::= { pm10010ulhPerfTelecomLinePostFecPast24StatHistoryPort1Entry 6 }


pm10010ulhPerfTelecomLinePostFecPast24StatHistorySesValuePort1 OBJECT-TYPE
	SYNTAX  Unsigned32
	MAX-ACCESS read-only
	STATUS current
	DESCRIPTION
        "
        Previous 24-hours SES counter
         :This OID gives the previous 24-hours 
        severely Errored Second counter 
        value
        "
	::= { pm10010ulhPerfTelecomLinePostFecPast24StatHistoryPort1Entry 7 }


pm10010ulhPerfTelecomLinePostFecPast24StatHistoryInvSefsPort1 OBJECT-TYPE
	SYNTAX  EkiOnOff
	MAX-ACCESS read-only
	STATUS current
	DESCRIPTION
        "
        Previous 24-hours SEFS counter 
        inv. :This OID indicates that the 
        previous 24-hours severely Errored 
        Framing Second counter is invalid
        "
	::= { pm10010ulhPerfTelecomLinePostFecPast24StatHistoryPort1Entry 8 }


pm10010ulhPerfTelecomLinePostFecPast24StatHistorySefsValuePort1 OBJECT-TYPE
	SYNTAX  Unsigned32
	MAX-ACCESS read-only
	STATUS current
	DESCRIPTION
        "
        Previous 24-hours SEFS counter 
        :This OID gives the previous 24-hours 
        severely Errored Framing Second 
        counter value
        "
	::= { pm10010ulhPerfTelecomLinePostFecPast24StatHistoryPort1Entry 9 }


pm10010ulhPerfTelecomLinePostFecPast24StatHistoryInvUasPort1 OBJECT-TYPE
	SYNTAX  EkiOnOff
	MAX-ACCESS read-only
	STATUS current
	DESCRIPTION
        "
        Previous 24-hours UAS counter
         inv. :This OID indicates that
         the previous 24-hours UnAvailable 
        Second counter is invalid
        "
	::= { pm10010ulhPerfTelecomLinePostFecPast24StatHistoryPort1Entry 10 }


pm10010ulhPerfTelecomLinePostFecPast24StatHistoryUasValuePort1 OBJECT-TYPE
	SYNTAX  Unsigned32
	MAX-ACCESS read-only
	STATUS current
	DESCRIPTION
        "
        Previous 24-hours UAS counter
         :This OID gives the previous 24-hours 
        UnAvailable Second counter value
        "
	::= { pm10010ulhPerfTelecomLinePostFecPast24StatHistoryPort1Entry 11 }


--- *****************************************************
---     Leaf of the telecomBerLinePreFecCurrent15Stat
--- *****************************************************
--- *********************************************************
---     TABLE for the pm10010ulhPerfTelecomBerLinePreFecCurrent15Stat articles
--- *********************************************************

pm10010ulhPerfTelecomBerLinePreFecCurrent15StatTable OBJECT-TYPE
	SYNTAX  SEQUENCE OF Pm10010ulhPerfTelecomBerLinePreFecCurrent15StatEntry
	MAX-ACCESS not-accessible
	STATUS current
	DESCRIPTION
        "
        List of pm10010ulhPerfTelecomBerLinePreFecCurrent15Stat 
        Article
        "
	::= { pm10010ulhMonPerfLine 352 }


pm10010ulhPerfTelecomBerLinePreFecCurrent15StatEntry OBJECT-TYPE
	SYNTAX Pm10010ulhPerfTelecomBerLinePreFecCurrent15StatEntry
	MAX-ACCESS not-accessible
	STATUS current
	DESCRIPTION
        "
        Row definition for the pm10010ulhPerfTelecomBerLinePreFecCurrent15Stat 
        table
        "
	INDEX   { pm10010ulhPerfTelecomBerLinePreFecCurrent15StatIndex }
	::= { pm10010ulhPerfTelecomBerLinePreFecCurrent15StatTable 1 }


Pm10010ulhPerfTelecomBerLinePreFecCurrent15StatEntry ::=
	SEQUENCE {
	pm10010ulhPerfTelecomBerLinePreFecCurrent15StatIndex
		INTEGER,
	pm10010ulhPerfTelecomBerLinePreFecCurrent15StatInvBerPortn
		EkiOnOff,
	pm10010ulhPerfTelecomBerLinePreFecCurrent15StatBerValuePortn
		Unsigned32,
	pm10010ulhPerfTelecomBerLinePreFecCurrent15StatInvMinBerPortn
		EkiOnOff,
	pm10010ulhPerfTelecomBerLinePreFecCurrent15StatMinBerValuePortn
		Unsigned32,
	pm10010ulhPerfTelecomBerLinePreFecCurrent15StatInvMaxBerPortn
		EkiOnOff,
	pm10010ulhPerfTelecomBerLinePreFecCurrent15StatMaxBerValuePortn
		Unsigned32
	}


pm10010ulhPerfTelecomBerLinePreFecCurrent15StatIndex OBJECT-TYPE
	SYNTAX  INTEGER(0..128)
	MAX-ACCESS  read-only
	STATUS current
	DESCRIPTION
        "
        Index definition for the pm10010ulhPerfTelecomBerLinePreFecCurrent15Stat 
        table
        "
	::= { pm10010ulhPerfTelecomBerLinePreFecCurrent15StatEntry 1 }


pm10010ulhPerfTelecomBerLinePreFecCurrent15StatInvBerPortn OBJECT-TYPE
	SYNTAX  EkiOnOff
	MAX-ACCESS read-only
	STATUS current
	DESCRIPTION
        "
        Current 15-min BER counter inv. 
        :This OID indicates that the current 
        15-min Coding Violation counter 
        is invalid
        "
	::= { pm10010ulhPerfTelecomBerLinePreFecCurrent15StatEntry 2 }


pm10010ulhPerfTelecomBerLinePreFecCurrent15StatBerValuePortn OBJECT-TYPE
	SYNTAX  Unsigned32
	MAX-ACCESS read-only
	STATUS current
	DESCRIPTION
        "
        Current 15-min BER counter :This 
        OID gives the current 15-min Coding 
        Violation counter value
        "
	::= { pm10010ulhPerfTelecomBerLinePreFecCurrent15StatEntry 3 }


pm10010ulhPerfTelecomBerLinePreFecCurrent15StatInvMinBerPortn OBJECT-TYPE
	SYNTAX  EkiOnOff
	MAX-ACCESS read-only
	STATUS current
	DESCRIPTION
        "
        Current 15-min MinBER counter
         inv. :This OID indicates that
         the current 15-min Errored Second 
        counter is invalid
        "
	::= { pm10010ulhPerfTelecomBerLinePreFecCurrent15StatEntry 4 }


pm10010ulhPerfTelecomBerLinePreFecCurrent15StatMinBerValuePortn OBJECT-TYPE
	SYNTAX  Unsigned32
	MAX-ACCESS read-only
	STATUS current
	DESCRIPTION
        "
        Current 15-min MinBER counter
         :This OID gives the current 15-min 
        Errored Second counter value
        "
	::= { pm10010ulhPerfTelecomBerLinePreFecCurrent15StatEntry 5 }


pm10010ulhPerfTelecomBerLinePreFecCurrent15StatInvMaxBerPortn OBJECT-TYPE
	SYNTAX  EkiOnOff
	MAX-ACCESS read-only
	STATUS current
	DESCRIPTION
        "
        Current 15-min MaxBER counter
         inv. :This OID indicates that
         the current 15-min severely Errored 
        Second counter is invalid
        "
	::= { pm10010ulhPerfTelecomBerLinePreFecCurrent15StatEntry 6 }


pm10010ulhPerfTelecomBerLinePreFecCurrent15StatMaxBerValuePortn OBJECT-TYPE
	SYNTAX  Unsigned32
	MAX-ACCESS read-only
	STATUS current
	DESCRIPTION
        "
        Current 15-min MaxBER counter
         :This OID gives the current 15-min 
        severely Errored Second counter 
        value
        "
	::= { pm10010ulhPerfTelecomBerLinePreFecCurrent15StatEntry 7 }


--- *****************************************************
---     Leaf of the telecomBerLinePreFecPast15Stat
--- *****************************************************
--- *********************************************************
---     TABLE for the pm10010ulhPerfTelecomBerLinePreFecPast15StatHistory articles
--- *********************************************************

pm10010ulhPerfTelecomBerLinePreFecPast15StatHistoryPort1Table OBJECT-TYPE
	SYNTAX  SEQUENCE OF Pm10010ulhPerfTelecomBerLinePreFecPast15StatHistoryPort1Entry
	MAX-ACCESS not-accessible
	STATUS current
	DESCRIPTION
        "
        List of pm10010ulhPerfTelecomBerLinePreFecPast15StatHistory 
        Article
        "
	::= { pm10010ulhMonPerfLine 353 }


pm10010ulhPerfTelecomBerLinePreFecPast15StatHistoryPort1Entry OBJECT-TYPE
	SYNTAX Pm10010ulhPerfTelecomBerLinePreFecPast15StatHistoryPort1Entry
	MAX-ACCESS not-accessible
	STATUS current
	DESCRIPTION
        "
        Row definition for the pm10010ulhPerfTelecomBerLinePreFecPast15StatHistory 
        table
        "
	INDEX   { pm10010ulhPerfTelecomBerLinePreFecPast15StatHistoryPort1Index }
	::= { pm10010ulhPerfTelecomBerLinePreFecPast15StatHistoryPort1Table 1 }


Pm10010ulhPerfTelecomBerLinePreFecPast15StatHistoryPort1Entry ::=
	SEQUENCE {
	pm10010ulhPerfTelecomBerLinePreFecPast15StatHistoryPort1Index
		INTEGER,
	pm10010ulhPerfTelecomBerLinePreFecPast15StatHistoryInvBerPort1
		EkiOnOff,
	pm10010ulhPerfTelecomBerLinePreFecPast15StatHistoryBerValuePort1
		Unsigned32,
	pm10010ulhPerfTelecomBerLinePreFecPast15StatHistoryInvMinBerPort1
		EkiOnOff,
	pm10010ulhPerfTelecomBerLinePreFecPast15StatHistoryMinBerValuePort1
		Unsigned32,
	pm10010ulhPerfTelecomBerLinePreFecPast15StatHistoryInvMaxBerPort1
		EkiOnOff,
	pm10010ulhPerfTelecomBerLinePreFecPast15StatHistoryMaxBerValuePort1
		Unsigned32
	}


pm10010ulhPerfTelecomBerLinePreFecPast15StatHistoryPort1Index OBJECT-TYPE
	SYNTAX  INTEGER(0..128)
	MAX-ACCESS  read-only
	STATUS current
	DESCRIPTION
        "
        Index definition for the pm10010ulhPerfTelecomBerLinePreFecPast15StatHistory 
        table
        "
	::= { pm10010ulhPerfTelecomBerLinePreFecPast15StatHistoryPort1Entry 1 }


pm10010ulhPerfTelecomBerLinePreFecPast15StatHistoryInvBerPort1 OBJECT-TYPE
	SYNTAX  EkiOnOff
	MAX-ACCESS read-only
	STATUS current
	DESCRIPTION
        "
        Previous 15-min BER counter inv. 
        :This OID indicates that the previous 
        15-min Coding Violation counter 
        is invalid
        "
	::= { pm10010ulhPerfTelecomBerLinePreFecPast15StatHistoryPort1Entry 2 }


pm10010ulhPerfTelecomBerLinePreFecPast15StatHistoryBerValuePort1 OBJECT-TYPE
	SYNTAX  Unsigned32
	MAX-ACCESS read-only
	STATUS current
	DESCRIPTION
        "
        Previous 15-min BER counter :This 
        OID gives the previous 15-min Coding 
        Violation counter value
        "
	::= { pm10010ulhPerfTelecomBerLinePreFecPast15StatHistoryPort1Entry 3 }


pm10010ulhPerfTelecomBerLinePreFecPast15StatHistoryInvMinBerPort1 OBJECT-TYPE
	SYNTAX  EkiOnOff
	MAX-ACCESS read-only
	STATUS current
	DESCRIPTION
        "
        Previous 15-min MinBER counter 
        inv. :This OID indicates that the 
        previous 15-min Errored Second
         counter is invalid
        "
	::= { pm10010ulhPerfTelecomBerLinePreFecPast15StatHistoryPort1Entry 4 }


pm10010ulhPerfTelecomBerLinePreFecPast15StatHistoryMinBerValuePort1 OBJECT-TYPE
	SYNTAX  Unsigned32
	MAX-ACCESS read-only
	STATUS current
	DESCRIPTION
        "
        Previous 15-min MinBER counter 
        :This OID gives the previous 15-min 
        Errored Second counter value
        "
	::= { pm10010ulhPerfTelecomBerLinePreFecPast15StatHistoryPort1Entry 5 }


pm10010ulhPerfTelecomBerLinePreFecPast15StatHistoryInvMaxBerPort1 OBJECT-TYPE
	SYNTAX  EkiOnOff
	MAX-ACCESS read-only
	STATUS current
	DESCRIPTION
        "
        Previous 15-min MaxBER counter 
        inv. :This OID indicates that the 
        previous 15-min severely Errored 
        Second counter is invalid
        "
	::= { pm10010ulhPerfTelecomBerLinePreFecPast15StatHistoryPort1Entry 6 }


pm10010ulhPerfTelecomBerLinePreFecPast15StatHistoryMaxBerValuePort1 OBJECT-TYPE
	SYNTAX  Unsigned32
	MAX-ACCESS read-only
	STATUS current
	DESCRIPTION
        "
        Previous 15-min MaxBER counter 
        :This OID gives the previous 15-min 
        severely Errored Second counter 
        value
        "
	::= { pm10010ulhPerfTelecomBerLinePreFecPast15StatHistoryPort1Entry 7 }


--- *****************************************************
---     Leaf of the telecomBerLinePreFecCurrent24Stat
--- *****************************************************
--- *********************************************************
---     TABLE for the pm10010ulhPerfTelecomBerLinePreFecCurrent24Stat articles
--- *********************************************************

pm10010ulhPerfTelecomBerLinePreFecCurrent24StatTable OBJECT-TYPE
	SYNTAX  SEQUENCE OF Pm10010ulhPerfTelecomBerLinePreFecCurrent24StatEntry
	MAX-ACCESS not-accessible
	STATUS current
	DESCRIPTION
        "
        List of pm10010ulhPerfTelecomBerLinePreFecCurrent24Stat 
        Article
        "
	::= { pm10010ulhMonPerfLine 354 }


pm10010ulhPerfTelecomBerLinePreFecCurrent24StatEntry OBJECT-TYPE
	SYNTAX Pm10010ulhPerfTelecomBerLinePreFecCurrent24StatEntry
	MAX-ACCESS not-accessible
	STATUS current
	DESCRIPTION
        "
        Row definition for the pm10010ulhPerfTelecomBerLinePreFecCurrent24Stat 
        table
        "
	INDEX   { pm10010ulhPerfTelecomBerLinePreFecCurrent24StatIndex }
	::= { pm10010ulhPerfTelecomBerLinePreFecCurrent24StatTable 1 }


Pm10010ulhPerfTelecomBerLinePreFecCurrent24StatEntry ::=
	SEQUENCE {
	pm10010ulhPerfTelecomBerLinePreFecCurrent24StatIndex
		INTEGER,
	pm10010ulhPerfTelecomBerLinePreFecCurrent24StatInvBerPortn
		EkiOnOff,
	pm10010ulhPerfTelecomBerLinePreFecCurrent24StatBerValuePortn
		Unsigned32,
	pm10010ulhPerfTelecomBerLinePreFecCurrent24StatInvMinBerPortn
		EkiOnOff,
	pm10010ulhPerfTelecomBerLinePreFecCurrent24StatMinBerValuePortn
		Unsigned32,
	pm10010ulhPerfTelecomBerLinePreFecCurrent24StatInvMaxBerPortn
		EkiOnOff,
	pm10010ulhPerfTelecomBerLinePreFecCurrent24StatMaxBerValuePortn
		Unsigned32
	}


pm10010ulhPerfTelecomBerLinePreFecCurrent24StatIndex OBJECT-TYPE
	SYNTAX  INTEGER(0..128)
	MAX-ACCESS  read-only
	STATUS current
	DESCRIPTION
        "
        Index definition for the pm10010ulhPerfTelecomBerLinePreFecCurrent24Stat 
        table
        "
	::= { pm10010ulhPerfTelecomBerLinePreFecCurrent24StatEntry 1 }


pm10010ulhPerfTelecomBerLinePreFecCurrent24StatInvBerPortn OBJECT-TYPE
	SYNTAX  EkiOnOff
	MAX-ACCESS read-only
	STATUS current
	DESCRIPTION
        "
        Current 24-hours BER counter inv. 
        :This OID indicates that the current 
        24-hours Coding Violation counter 
        is invalid
        "
	::= { pm10010ulhPerfTelecomBerLinePreFecCurrent24StatEntry 2 }


pm10010ulhPerfTelecomBerLinePreFecCurrent24StatBerValuePortn OBJECT-TYPE
	SYNTAX  Unsigned32
	MAX-ACCESS read-only
	STATUS current
	DESCRIPTION
        "
        Current 24-hours BER counter :This 
        OID gives the current 24-hours
         Coding Violation counter value
        "
	::= { pm10010ulhPerfTelecomBerLinePreFecCurrent24StatEntry 3 }


pm10010ulhPerfTelecomBerLinePreFecCurrent24StatInvMinBerPortn OBJECT-TYPE
	SYNTAX  EkiOnOff
	MAX-ACCESS read-only
	STATUS current
	DESCRIPTION
        "
        Current 24-hoursMinBER counter 
        inv. :This OID indicates that the 
        current 24-hours Errored Second 
        counter is invalid
        "
	::= { pm10010ulhPerfTelecomBerLinePreFecCurrent24StatEntry 4 }


pm10010ulhPerfTelecomBerLinePreFecCurrent24StatMinBerValuePortn OBJECT-TYPE
	SYNTAX  Unsigned32
	MAX-ACCESS read-only
	STATUS current
	DESCRIPTION
        "
        Current 24-hours MinBER counter 
        :This OID gives the current 24-hours 
        Errored Second counter value
        "
	::= { pm10010ulhPerfTelecomBerLinePreFecCurrent24StatEntry 5 }


pm10010ulhPerfTelecomBerLinePreFecCurrent24StatInvMaxBerPortn OBJECT-TYPE
	SYNTAX  EkiOnOff
	MAX-ACCESS read-only
	STATUS current
	DESCRIPTION
        "
        Current 24-hours MaxBER counter 
        inv. :This OID indicates that the 
        current 24-hours severely Errored 
        Second counter is invalid
        "
	::= { pm10010ulhPerfTelecomBerLinePreFecCurrent24StatEntry 6 }


pm10010ulhPerfTelecomBerLinePreFecCurrent24StatMaxBerValuePortn OBJECT-TYPE
	SYNTAX  Unsigned32
	MAX-ACCESS read-only
	STATUS current
	DESCRIPTION
        "
        Current 24-hours MaxBER counter 
        :This OID gives the current 24-hours 
        severely Errored Second counter 
        value
        "
	::= { pm10010ulhPerfTelecomBerLinePreFecCurrent24StatEntry 7 }


--- *****************************************************
---     Leaf of the telecomBerLinePreFecPast24Stat
--- *****************************************************
--- *********************************************************
---     TABLE for the pm10010ulhPerfTelecomBerLinePreFecPast24StatHistory articles
--- *********************************************************

pm10010ulhPerfTelecomBerLinePreFecPast24StatHistoryPort1Table OBJECT-TYPE
	SYNTAX  SEQUENCE OF Pm10010ulhPerfTelecomBerLinePreFecPast24StatHistoryPort1Entry
	MAX-ACCESS not-accessible
	STATUS current
	DESCRIPTION
        "
        List of pm10010ulhPerfTelecomBerLinePreFecPast24StatHistory 
        Article
        "
	::= { pm10010ulhMonPerfLine 355 }


pm10010ulhPerfTelecomBerLinePreFecPast24StatHistoryPort1Entry OBJECT-TYPE
	SYNTAX Pm10010ulhPerfTelecomBerLinePreFecPast24StatHistoryPort1Entry
	MAX-ACCESS not-accessible
	STATUS current
	DESCRIPTION
        "
        Row definition for the pm10010ulhPerfTelecomBerLinePreFecPast24StatHistory 
        table
        "
	INDEX   { pm10010ulhPerfTelecomBerLinePreFecPast24StatHistoryPort1Index }
	::= { pm10010ulhPerfTelecomBerLinePreFecPast24StatHistoryPort1Table 1 }


Pm10010ulhPerfTelecomBerLinePreFecPast24StatHistoryPort1Entry ::=
	SEQUENCE {
	pm10010ulhPerfTelecomBerLinePreFecPast24StatHistoryPort1Index
		INTEGER,
	pm10010ulhPerfTelecomBerLinePreFecPast24StatHistoryInvBerPort1
		EkiOnOff,
	pm10010ulhPerfTelecomBerLinePreFecPast24StatHistoryBerValuePort1
		Unsigned32,
	pm10010ulhPerfTelecomBerLinePreFecPast24StatHistoryInvMinBerPort1
		EkiOnOff,
	pm10010ulhPerfTelecomBerLinePreFecPast24StatHistoryMinBerValuePort1
		Unsigned32,
	pm10010ulhPerfTelecomBerLinePreFecPast24StatHistoryInvMaxBerPort1
		EkiOnOff,
	pm10010ulhPerfTelecomBerLinePreFecPast24StatHistoryMaxBerValuePort1
		Unsigned32
	}


pm10010ulhPerfTelecomBerLinePreFecPast24StatHistoryPort1Index OBJECT-TYPE
	SYNTAX  INTEGER(0..128)
	MAX-ACCESS  read-only
	STATUS current
	DESCRIPTION
        "
        Index definition for the pm10010ulhPerfTelecomBerLinePreFecPast24StatHistory 
        table
        "
	::= { pm10010ulhPerfTelecomBerLinePreFecPast24StatHistoryPort1Entry 1 }


pm10010ulhPerfTelecomBerLinePreFecPast24StatHistoryInvBerPort1 OBJECT-TYPE
	SYNTAX  EkiOnOff
	MAX-ACCESS read-only
	STATUS current
	DESCRIPTION
        "
        Previous 24-hours BER counter
         inv. :This OID indicates that
         the previous 24-hours Coding Violation 
        counter is invalid
        "
	::= { pm10010ulhPerfTelecomBerLinePreFecPast24StatHistoryPort1Entry 2 }


pm10010ulhPerfTelecomBerLinePreFecPast24StatHistoryBerValuePort1 OBJECT-TYPE
	SYNTAX  Unsigned32
	MAX-ACCESS read-only
	STATUS current
	DESCRIPTION
        "
        Previous 24-hours BER counter
         :This OID gives the previous 24-hours 
        Coding Violation counter value
        "
	::= { pm10010ulhPerfTelecomBerLinePreFecPast24StatHistoryPort1Entry 3 }


pm10010ulhPerfTelecomBerLinePreFecPast24StatHistoryInvMinBerPort1 OBJECT-TYPE
	SYNTAX  EkiOnOff
	MAX-ACCESS read-only
	STATUS current
	DESCRIPTION
        "
        Previous 24-hours MinBER counter 
        inv. :This OID indicates that the 
        previous 24-hours Errored Second 
        counter is invalid
        "
	::= { pm10010ulhPerfTelecomBerLinePreFecPast24StatHistoryPort1Entry 4 }


pm10010ulhPerfTelecomBerLinePreFecPast24StatHistoryMinBerValuePort1 OBJECT-TYPE
	SYNTAX  Unsigned32
	MAX-ACCESS read-only
	STATUS current
	DESCRIPTION
        "
        Previous 24-hours MinBER counter 
        :This OID gives the previous 24-hours 
        Errored Second counter value
        "
	::= { pm10010ulhPerfTelecomBerLinePreFecPast24StatHistoryPort1Entry 5 }


pm10010ulhPerfTelecomBerLinePreFecPast24StatHistoryInvMaxBerPort1 OBJECT-TYPE
	SYNTAX  EkiOnOff
	MAX-ACCESS read-only
	STATUS current
	DESCRIPTION
        "
        Previous 24-hours MaxBER counter 
        inv. :This OID indicates that the 
        previous 24-hours severely Errored 
        Second counter is invalid
        "
	::= { pm10010ulhPerfTelecomBerLinePreFecPast24StatHistoryPort1Entry 6 }


pm10010ulhPerfTelecomBerLinePreFecPast24StatHistoryMaxBerValuePort1 OBJECT-TYPE
	SYNTAX  Unsigned32
	MAX-ACCESS read-only
	STATUS current
	DESCRIPTION
        "
        Previous 24-hours MaxBER counter 
        :This OID gives the previous 24-hours 
        severely Errored Second counter 
        value
        "
	::= { pm10010ulhPerfTelecomBerLinePreFecPast24StatHistoryPort1Entry 7 }


--- *****************************************************
---     Leaf of the datacomClientCurrent15Stat
--- *****************************************************
--- *********************************************************
---     TABLE for the pm10010ulhPerfDatacomClientCurrent15Stat articles
--- *********************************************************

pm10010ulhPerfDatacomClientCurrent15StatTable OBJECT-TYPE
	SYNTAX  SEQUENCE OF Pm10010ulhPerfDatacomClientCurrent15StatEntry
	MAX-ACCESS not-accessible
	STATUS current
	DESCRIPTION
        "
        List of pm10010ulhPerfDatacomClientCurrent15Stat 
        Article
        "
	::= { pm10010ulhMonPerfClient 848 }


pm10010ulhPerfDatacomClientCurrent15StatEntry OBJECT-TYPE
	SYNTAX Pm10010ulhPerfDatacomClientCurrent15StatEntry
	MAX-ACCESS not-accessible
	STATUS current
	DESCRIPTION
        "
        Row definition for the pm10010ulhPerfDatacomClientCurrent15Stat 
        table
        "
	INDEX   { pm10010ulhPerfDatacomClientCurrent15StatIndex }
	::= { pm10010ulhPerfDatacomClientCurrent15StatTable 1 }


Pm10010ulhPerfDatacomClientCurrent15StatEntry ::=
	SEQUENCE {
	pm10010ulhPerfDatacomClientCurrent15StatIndex
		INTEGER,
	pm10010ulhperfdatacomclientCurrent15StatOutPacketCountInvPortn
		EkiOnOff,
	pm10010ulhperfdatacomclientCurrent15StatOutPacketCountPortn
		Counter64,
	pm10010ulhperfdatacomclientCurrent15StatOutCrcCountInvPortn
		EkiOnOff,
	pm10010ulhperfdatacomclientCurrent15StatOutCrcCountPortn
		Counter64,
	pm10010ulhperfdatacomclientCurrent15StatInPacketCountInvPortn
		EkiOnOff,
	pm10010ulhperfdatacomclientCurrent15StatInPacketCountPortn
		Counter64,
	pm10010ulhperfdatacomclientCurrent15StatInCrcCountInvPortn
		EkiOnOff,
	pm10010ulhperfdatacomclientCurrent15StatInCrcCountPortn
		Counter64
	}


pm10010ulhPerfDatacomClientCurrent15StatIndex OBJECT-TYPE
	SYNTAX  INTEGER(0..128)
	MAX-ACCESS  read-only
	STATUS current
	DESCRIPTION
        "
        Index definition for the pm10010ulhPerfDatacomClientCurrent15Stat 
        table
        "
	::= { pm10010ulhPerfDatacomClientCurrent15StatEntry 1 }


pm10010ulhperfdatacomclientCurrent15StatOutPacketCountInvPortn OBJECT-TYPE
	SYNTAX  EkiOnOff
	MAX-ACCESS read-only
	STATUS current
	DESCRIPTION
        "
        Client Current 15-min Output Packet 
        counter inv. :This OID indicates 
        that the current 15-min Output
         Packets counter is invalid
        "
	::= { pm10010ulhPerfDatacomClientCurrent15StatEntry 30 }


pm10010ulhperfdatacomclientCurrent15StatOutPacketCountPortn OBJECT-TYPE
	SYNTAX  Counter64
	MAX-ACCESS read-only
	STATUS current
	DESCRIPTION
        "
        Client Current 15-min Output Packet 
        counter :This OID gives the current 
        15-min Output Packets counter value
        "
	::= { pm10010ulhPerfDatacomClientCurrent15StatEntry 31 }


pm10010ulhperfdatacomclientCurrent15StatOutCrcCountInvPortn OBJECT-TYPE
	SYNTAX  EkiOnOff
	MAX-ACCESS read-only
	STATUS current
	DESCRIPTION
        "
        Client Current 15-min Output CRC 
        counter inv. :This OID indicates 
        that the current 15-min Output
         CRC counter is invalid
        "
	::= { pm10010ulhPerfDatacomClientCurrent15StatEntry 28 }


pm10010ulhperfdatacomclientCurrent15StatOutCrcCountPortn OBJECT-TYPE
	SYNTAX  Counter64
	MAX-ACCESS read-only
	STATUS current
	DESCRIPTION
        "
        Client Current 15-min Output CRC 
        counter :This OID gives the current 
        15-min Output CRC counter value
        "
	::= { pm10010ulhPerfDatacomClientCurrent15StatEntry 29 }


pm10010ulhperfdatacomclientCurrent15StatInPacketCountInvPortn OBJECT-TYPE
	SYNTAX  EkiOnOff
	MAX-ACCESS read-only
	STATUS current
	DESCRIPTION
        "
        Client Current 15-min Input Packet 
        counter inv. :This OID indicates 
        that the current 15-min Input Packet 
        counter is invalid
        "
	::= { pm10010ulhPerfDatacomClientCurrent15StatEntry 6 }


pm10010ulhperfdatacomclientCurrent15StatInPacketCountPortn OBJECT-TYPE
	SYNTAX  Counter64
	MAX-ACCESS read-only
	STATUS current
	DESCRIPTION
        "
        Client Current 15-min Input Packet 
        counter :This OID gives the current 
        15-min Input Packet counter value
        "
	::= { pm10010ulhPerfDatacomClientCurrent15StatEntry 7 }


pm10010ulhperfdatacomclientCurrent15StatInCrcCountInvPortn OBJECT-TYPE
	SYNTAX  EkiOnOff
	MAX-ACCESS read-only
	STATUS current
	DESCRIPTION
        "
        Client Current 15-min Input CRC 
        counter inv. :This OID indicates 
        that the current 15-min Input CRC 
        counter is invalid
        "
	::= { pm10010ulhPerfDatacomClientCurrent15StatEntry 4 }


pm10010ulhperfdatacomclientCurrent15StatInCrcCountPortn OBJECT-TYPE
	SYNTAX  Counter64
	MAX-ACCESS read-only
	STATUS current
	DESCRIPTION
        "
        Client Current 15-min Input CRC 
        counter :This OID gives the current 
        15-min Input CRC counter value
        "
	::= { pm10010ulhPerfDatacomClientCurrent15StatEntry 5 }


--- *****************************************************
---     Leaf of the datacomClientPast15Stat
--- *****************************************************
--- *********************************************************
---     TABLE for the pm10010ulhPerfDatacomClientPast15StatHistory articles
--- *********************************************************

pm10010ulhPerfDatacomClientPast15StatHistoryPort1Table OBJECT-TYPE
	SYNTAX  SEQUENCE OF Pm10010ulhPerfDatacomClientPast15StatHistoryPort1Entry
	MAX-ACCESS not-accessible
	STATUS current
	DESCRIPTION
        "
        List of pm10010ulhPerfDatacomClientPast15StatHistory 
        Article
        "
	::= { pm10010ulhMonPerfClient 880 }


pm10010ulhPerfDatacomClientPast15StatHistoryPort1Entry OBJECT-TYPE
	SYNTAX Pm10010ulhPerfDatacomClientPast15StatHistoryPort1Entry
	MAX-ACCESS not-accessible
	STATUS current
	DESCRIPTION
        "
        Row definition for the pm10010ulhPerfDatacomClientPast15StatHistory 
        table
        "
	INDEX   { pm10010ulhPerfDatacomClientPast15StatHistoryPort1Index }
	::= { pm10010ulhPerfDatacomClientPast15StatHistoryPort1Table 1 }


Pm10010ulhPerfDatacomClientPast15StatHistoryPort1Entry ::=
	SEQUENCE {
	pm10010ulhPerfDatacomClientPast15StatHistoryPort1Index
		INTEGER,
	pm10010ulhperfdatacomclientPast15StatOutPacketCountInvPort1
		EkiOnOff,
	pm10010ulhperfdatacomclientPast15StatOutPacketCountPort1
		Counter64,
	pm10010ulhperfdatacomclientPast15StatOutCrcCountInvPort1
		EkiOnOff,
	pm10010ulhperfdatacomclientPast15StatOutCrcCountPort1
		Counter64,
	pm10010ulhperfdatacomclientPast15StatInPacketCountInvPort1
		EkiOnOff,
	pm10010ulhperfdatacomclientPast15StatInPacketCountPort1
		Counter64,
	pm10010ulhperfdatacomclientPast15StatInCrcCountInvPort1
		EkiOnOff,
	pm10010ulhperfdatacomclientPast15StatInCrcCountPort1
		Counter64
	}


pm10010ulhPerfDatacomClientPast15StatHistoryPort1Index OBJECT-TYPE
	SYNTAX  INTEGER(0..128)
	MAX-ACCESS  read-only
	STATUS current
	DESCRIPTION
        "
        Index definition for the pm10010ulhPerfDatacomClientPast15StatHistory 
        table
        "
	::= { pm10010ulhPerfDatacomClientPast15StatHistoryPort1Entry 1 }


pm10010ulhperfdatacomclientPast15StatOutPacketCountInvPort1 OBJECT-TYPE
	SYNTAX  EkiOnOff
	MAX-ACCESS read-only
	STATUS current
	DESCRIPTION
        "
        Client Past 15-min Output Packet 
        counter inv. :This OID indicates 
        that the past 15-min Output Packets 
        counter is invalid
        "
	::= { pm10010ulhPerfDatacomClientPast15StatHistoryPort1Entry 30 }


pm10010ulhperfdatacomclientPast15StatOutPacketCountPort1 OBJECT-TYPE
	SYNTAX  Counter64
	MAX-ACCESS read-only
	STATUS current
	DESCRIPTION
        "
        Client Past 15-min Output Packet 
        counter :This OID gives the past 
        15-min Output Packets counter value
        "
	::= { pm10010ulhPerfDatacomClientPast15StatHistoryPort1Entry 31 }


pm10010ulhperfdatacomclientPast15StatOutCrcCountInvPort1 OBJECT-TYPE
	SYNTAX  EkiOnOff
	MAX-ACCESS read-only
	STATUS current
	DESCRIPTION
        "
        Client Past 15-min Output CRC
         counter inv. :This OID indicates 
        that the past 15-min Output CRC 
        counter is invalid
        "
	::= { pm10010ulhPerfDatacomClientPast15StatHistoryPort1Entry 28 }


pm10010ulhperfdatacomclientPast15StatOutCrcCountPort1 OBJECT-TYPE
	SYNTAX  Counter64
	MAX-ACCESS read-only
	STATUS current
	DESCRIPTION
        "
        Client Past 15-min Output CRC
         counter :This OID gives the past 
        15-min Output CRC counter value
        "
	::= { pm10010ulhPerfDatacomClientPast15StatHistoryPort1Entry 29 }


pm10010ulhperfdatacomclientPast15StatInPacketCountInvPort1 OBJECT-TYPE
	SYNTAX  EkiOnOff
	MAX-ACCESS read-only
	STATUS current
	DESCRIPTION
        "
        Client Past 15-min Input Packet 
        counter inv. :This OID indicates 
        that the past 15-min Input Packet 
        counter is invalid
        "
	::= { pm10010ulhPerfDatacomClientPast15StatHistoryPort1Entry 6 }


pm10010ulhperfdatacomclientPast15StatInPacketCountPort1 OBJECT-TYPE
	SYNTAX  Counter64
	MAX-ACCESS read-only
	STATUS current
	DESCRIPTION
        "
        Client Past 15-min Input Packet 
        counter :This OID gives the past 
        15-min Input Packet counter value
        "
	::= { pm10010ulhPerfDatacomClientPast15StatHistoryPort1Entry 7 }


pm10010ulhperfdatacomclientPast15StatInCrcCountInvPort1 OBJECT-TYPE
	SYNTAX  EkiOnOff
	MAX-ACCESS read-only
	STATUS current
	DESCRIPTION
        "
        Client Past 15-min Input CRC counter 
        inv. :This OID indicates that the 
        past 15-min Input CRC counter is 
        invalid
        "
	::= { pm10010ulhPerfDatacomClientPast15StatHistoryPort1Entry 4 }


pm10010ulhperfdatacomclientPast15StatInCrcCountPort1 OBJECT-TYPE
	SYNTAX  Counter64
	MAX-ACCESS read-only
	STATUS current
	DESCRIPTION
        "
        Client Past 15-min Input CRC counter 
        :This OID gives the past 15-min 
        Input CRC counter value
        "
	::= { pm10010ulhPerfDatacomClientPast15StatHistoryPort1Entry 5 }


--- *****************************************************
---     Leaf of the datacomClientCurrent24Stat
--- *****************************************************
--- *********************************************************
---     TABLE for the pm10010ulhPerfDatacomClientCurrent24Stat articles
--- *********************************************************

pm10010ulhPerfDatacomClientCurrent24StatTable OBJECT-TYPE
	SYNTAX  SEQUENCE OF Pm10010ulhPerfDatacomClientCurrent24StatEntry
	MAX-ACCESS not-accessible
	STATUS current
	DESCRIPTION
        "
        List of pm10010ulhPerfDatacomClientCurrent24Stat 
        Article
        "
	::= { pm10010ulhMonPerfClient 912 }


pm10010ulhPerfDatacomClientCurrent24StatEntry OBJECT-TYPE
	SYNTAX Pm10010ulhPerfDatacomClientCurrent24StatEntry
	MAX-ACCESS not-accessible
	STATUS current
	DESCRIPTION
        "
        Row definition for the pm10010ulhPerfDatacomClientCurrent24Stat 
        table
        "
	INDEX   { pm10010ulhPerfDatacomClientCurrent24StatIndex }
	::= { pm10010ulhPerfDatacomClientCurrent24StatTable 1 }


Pm10010ulhPerfDatacomClientCurrent24StatEntry ::=
	SEQUENCE {
	pm10010ulhPerfDatacomClientCurrent24StatIndex
		INTEGER,
	pm10010ulhperfdatacomclientCurrent24StatOutPacketCountInvPortn
		EkiOnOff,
	pm10010ulhperfdatacomclientCurrent24StatOutPacketCountPortn
		Counter64,
	pm10010ulhperfdatacomclientCurrent24StatOutCrcCountInvPortn
		EkiOnOff,
	pm10010ulhperfdatacomclientCurrent24StatOutCrcCountPortn
		Counter64,
	pm10010ulhperfdatacomclientCurrent24StatInPacketCountInvPortn
		EkiOnOff,
	pm10010ulhperfdatacomclientCurrent24StatInPacketCountPortn
		Counter64,
	pm10010ulhperfdatacomclientCurrent24StatInCrcCountInvPortn
		EkiOnOff,
	pm10010ulhperfdatacomclientCurrent24StatInCrcCountPortn
		Counter64
	}


pm10010ulhPerfDatacomClientCurrent24StatIndex OBJECT-TYPE
	SYNTAX  INTEGER(0..128)
	MAX-ACCESS  read-only
	STATUS current
	DESCRIPTION
        "
        Index definition for the pm10010ulhPerfDatacomClientCurrent24Stat 
        table
        "
	::= { pm10010ulhPerfDatacomClientCurrent24StatEntry 1 }


pm10010ulhperfdatacomclientCurrent24StatOutPacketCountInvPortn OBJECT-TYPE
	SYNTAX  EkiOnOff
	MAX-ACCESS read-only
	STATUS current
	DESCRIPTION
        "
        Client Current 24-hours Output 
        Packet counter inv. :This OID indicates 
        that the current 24-hours Output 
        Packets counter is invalid
        "
	::= { pm10010ulhPerfDatacomClientCurrent24StatEntry 30 }


pm10010ulhperfdatacomclientCurrent24StatOutPacketCountPortn OBJECT-TYPE
	SYNTAX  Counter64
	MAX-ACCESS read-only
	STATUS current
	DESCRIPTION
        "
        Client Current 24-hours Output 
        Packet counter :This OID gives
         the current 24-hours Output Packets 
        counter value
        "
	::= { pm10010ulhPerfDatacomClientCurrent24StatEntry 31 }


pm10010ulhperfdatacomclientCurrent24StatOutCrcCountInvPortn OBJECT-TYPE
	SYNTAX  EkiOnOff
	MAX-ACCESS read-only
	STATUS current
	DESCRIPTION
        "
        Client Current 24-hours Output 
        CRC counter inv. :This OID indicates 
        that the current 24-hours Output 
        CRC counter is invalid
        "
	::= { pm10010ulhPerfDatacomClientCurrent24StatEntry 28 }


pm10010ulhperfdatacomclientCurrent24StatOutCrcCountPortn OBJECT-TYPE
	SYNTAX  Counter64
	MAX-ACCESS read-only
	STATUS current
	DESCRIPTION
        "
        Client Current 24-hours Output 
        CRC counter :This OID gives the 
        current 24-hours Output CRC counter 
        value
        "
	::= { pm10010ulhPerfDatacomClientCurrent24StatEntry 29 }


pm10010ulhperfdatacomclientCurrent24StatInPacketCountInvPortn OBJECT-TYPE
	SYNTAX  EkiOnOff
	MAX-ACCESS read-only
	STATUS current
	DESCRIPTION
        "
        Client Current 24-hours Input
         Packet counter inv. :This OID
         indicates that the current 24-hours 
        Input Packet counter is invalid
        "
	::= { pm10010ulhPerfDatacomClientCurrent24StatEntry 6 }


pm10010ulhperfdatacomclientCurrent24StatInPacketCountPortn OBJECT-TYPE
	SYNTAX  Counter64
	MAX-ACCESS read-only
	STATUS current
	DESCRIPTION
        "
        Client Current 24-hours Input
         Packet counter :This OID gives 
        the current 24-hours Input Packet 
        counter value
        "
	::= { pm10010ulhPerfDatacomClientCurrent24StatEntry 7 }


pm10010ulhperfdatacomclientCurrent24StatInCrcCountInvPortn OBJECT-TYPE
	SYNTAX  EkiOnOff
	MAX-ACCESS read-only
	STATUS current
	DESCRIPTION
        "
        Client Current 24-hours Input
         CRC counter inv. :This OID indicates 
        that the current 24-hours Input 
        CRC counter is invalid
        "
	::= { pm10010ulhPerfDatacomClientCurrent24StatEntry 4 }


pm10010ulhperfdatacomclientCurrent24StatInCrcCountPortn OBJECT-TYPE
	SYNTAX  Counter64
	MAX-ACCESS read-only
	STATUS current
	DESCRIPTION
        "
        Client Current 24-hours Input
         CRC counter :This OID gives the 
        current 24-hours Input CRC counter 
        value
        "
	::= { pm10010ulhPerfDatacomClientCurrent24StatEntry 5 }


--- *****************************************************
---     Leaf of the datacomClientPast24Stat
--- *****************************************************
--- *********************************************************
---     TABLE for the pm10010ulhPerfDatacomClientPast24StatHistory articles
--- *********************************************************

pm10010ulhPerfDatacomClientPast24StatHistoryPort1Table OBJECT-TYPE
	SYNTAX  SEQUENCE OF Pm10010ulhPerfDatacomClientPast24StatHistoryPort1Entry
	MAX-ACCESS not-accessible
	STATUS current
	DESCRIPTION
        "
        List of pm10010ulhPerfDatacomClientPast24StatHistory 
        Article
        "
	::= { pm10010ulhMonPerfClient 944 }


pm10010ulhPerfDatacomClientPast24StatHistoryPort1Entry OBJECT-TYPE
	SYNTAX Pm10010ulhPerfDatacomClientPast24StatHistoryPort1Entry
	MAX-ACCESS not-accessible
	STATUS current
	DESCRIPTION
        "
        Row definition for the pm10010ulhPerfDatacomClientPast24StatHistory 
        table
        "
	INDEX   { pm10010ulhPerfDatacomClientPast24StatHistoryPort1Index }
	::= { pm10010ulhPerfDatacomClientPast24StatHistoryPort1Table 1 }


Pm10010ulhPerfDatacomClientPast24StatHistoryPort1Entry ::=
	SEQUENCE {
	pm10010ulhPerfDatacomClientPast24StatHistoryPort1Index
		INTEGER,
	pm10010ulhperfdatacomclientPast24StatOutPacketCountInvPort1
		EkiOnOff,
	pm10010ulhperfdatacomclientPast24StatOutPacketCountPort1
		Counter64,
	pm10010ulhperfdatacomclientPast24StatOutCrcCountInvPort1
		EkiOnOff,
	pm10010ulhperfdatacomclientPast24StatOutCrcCountPort1
		Counter64,
	pm10010ulhperfdatacomclientPast24StatInPacketCountInvPort1
		EkiOnOff,
	pm10010ulhperfdatacomclientPast24StatInPacketCountPort1
		Counter64,
	pm10010ulhperfdatacomclientPast24StatInCrcCountInvPort1
		EkiOnOff,
	pm10010ulhperfdatacomclientPast24StatInCrcCountPort1
		Counter64
	}


pm10010ulhPerfDatacomClientPast24StatHistoryPort1Index OBJECT-TYPE
	SYNTAX  INTEGER(0..128)
	MAX-ACCESS  read-only
	STATUS current
	DESCRIPTION
        "
        Index definition for the pm10010ulhPerfDatacomClientPast24StatHistory 
        table
        "
	::= { pm10010ulhPerfDatacomClientPast24StatHistoryPort1Entry 1 }


pm10010ulhperfdatacomclientPast24StatOutPacketCountInvPort1 OBJECT-TYPE
	SYNTAX  EkiOnOff
	MAX-ACCESS read-only
	STATUS current
	DESCRIPTION
        "
        Client Past 24-hours Output Packet 
        counter inv. :This OID indicates 
        that the past 24-hours Output Packets 
        counter is invalid
        "
	::= { pm10010ulhPerfDatacomClientPast24StatHistoryPort1Entry 30 }


pm10010ulhperfdatacomclientPast24StatOutPacketCountPort1 OBJECT-TYPE
	SYNTAX  Counter64
	MAX-ACCESS read-only
	STATUS current
	DESCRIPTION
        "
        Client Past 24-hours Output Packet 
        counter :This OID gives the past 
        24-hours Output Packets counter 
        value
        "
	::= { pm10010ulhPerfDatacomClientPast24StatHistoryPort1Entry 31 }


pm10010ulhperfdatacomclientPast24StatOutCrcCountInvPort1 OBJECT-TYPE
	SYNTAX  EkiOnOff
	MAX-ACCESS read-only
	STATUS current
	DESCRIPTION
        "
        Client Past 24-hours Output CRC 
        counter inv. :This OID indicates 
        that the past 24-hours Output CRC 
        counter is invalid
        "
	::= { pm10010ulhPerfDatacomClientPast24StatHistoryPort1Entry 28 }


pm10010ulhperfdatacomclientPast24StatOutCrcCountPort1 OBJECT-TYPE
	SYNTAX  Counter64
	MAX-ACCESS read-only
	STATUS current
	DESCRIPTION
        "
        Client Past 24-hours Output CRC 
        counter :This OID gives the past 
        24-hours Output CRC counter value
        "
	::= { pm10010ulhPerfDatacomClientPast24StatHistoryPort1Entry 29 }


pm10010ulhperfdatacomclientPast24StatInPacketCountInvPort1 OBJECT-TYPE
	SYNTAX  EkiOnOff
	MAX-ACCESS read-only
	STATUS current
	DESCRIPTION
        "
        Client Past 24-hours Input Packet 
        counter inv. :This OID indicates 
        that the past 24-hours Input Packet 
        counter is invalid
        "
	::= { pm10010ulhPerfDatacomClientPast24StatHistoryPort1Entry 6 }


pm10010ulhperfdatacomclientPast24StatInPacketCountPort1 OBJECT-TYPE
	SYNTAX  Counter64
	MAX-ACCESS read-only
	STATUS current
	DESCRIPTION
        "
        Client Past 24-hours Input Packet 
        counter :This OID gives the past 
        24-hours Input Packet counter value
        "
	::= { pm10010ulhPerfDatacomClientPast24StatHistoryPort1Entry 7 }


pm10010ulhperfdatacomclientPast24StatInCrcCountInvPort1 OBJECT-TYPE
	SYNTAX  EkiOnOff
	MAX-ACCESS read-only
	STATUS current
	DESCRIPTION
        "
        Client Past 24-hours Input CRC 
        counter inv. :This OID indicates 
        that the past 24-hours Input CRC 
        counter is invalid
        "
	::= { pm10010ulhPerfDatacomClientPast24StatHistoryPort1Entry 4 }


pm10010ulhperfdatacomclientPast24StatInCrcCountPort1 OBJECT-TYPE
	SYNTAX  Counter64
	MAX-ACCESS read-only
	STATUS current
	DESCRIPTION
        "
        Client Past 24-hours Input CRC 
        counter :This OID gives the past 
        24-hours Input CRC counter value
        "
	::= { pm10010ulhPerfDatacomClientPast24StatHistoryPort1Entry 5 }



pm10010ulhPerfEnable OBJECT-TYPE
	SYNTAX EkiOnOff
	MAX-ACCESS read-write
	STATUS current
	DESCRIPTION
        "
        Perf. Mon. Enable :This OID enables 
        the Performance Monitoring application
        "
	::= { pm10010ulhMonPerfSync 257 }


pm10010ulhPerf15minSync OBJECT-TYPE
	SYNTAX EkiOnOff
	MAX-ACCESS read-write
	STATUS current
	DESCRIPTION
        "
        Perf. Mon. 15-min sync. :This
         OID must be used in external synchronisation 
        mode only to send a 15-min synchronisation 
        command
        "
	::= { pm10010ulhMonPerfSync 259 }


pm10010ulhPerf24hSync OBJECT-TYPE
	SYNTAX EkiOnOff
	MAX-ACCESS read-write
	STATUS current
	DESCRIPTION
        "
        Perf. Mon. 24-hours sync. :This 
        OID must be used in external synchronisation 
        mode only to send a 24-hours synchronisation 
        command
        "
	::= { pm10010ulhMonPerfSync 260 }


pm10010ulhPerf15MinShort OBJECT-TYPE
	SYNTAX EkiOnOff
	MAX-ACCESS read-write
	STATUS current
	DESCRIPTION
        "
        15-min period is short :This OID 
        indicates that the 15-min period 
        lasts less than 890 seconds
        "
	::= { pm10010ulhMonPerfTimeStamp 1 }


pm10010ulhPerf15MinLong OBJECT-TYPE
	SYNTAX EkiOnOff
	MAX-ACCESS read-write
	STATUS current
	DESCRIPTION
        "
        15-min period is long :This OID 
        indicates that the 15-min period 
        lasts more than 910 seconds
        "
	::= { pm10010ulhMonPerfTimeStamp 2 }


pm10010ulhPerf24HoursShort OBJECT-TYPE
	SYNTAX Counter32
	MAX-ACCESS read-write
	STATUS current
	DESCRIPTION
        "
        24-hours period is short :This 
        OID indicates that 24-hours period 
        lasts less than 86390 seconds
        "
	::= { pm10010ulhMonPerfTimeStamp 5 }


pm10010ulhPerf24HoursLong OBJECT-TYPE
	SYNTAX Counter32
	MAX-ACCESS read-write
	STATUS current
	DESCRIPTION
        "
        24-hours period is long :This
         OID indicates that 24-hours period 
        lasts more than 86410 seconds
        "
	::= { pm10010ulhMonPerfTimeStamp 6 }


pm10010ulhPerfCurrent15MinElapsedTime OBJECT-TYPE
	SYNTAX Counter32
	MAX-ACCESS read-write
	STATUS current
	DESCRIPTION
        "
        Current 15min period Elapsed Time 
         :This OID gives the number of
         seconds elapsed in the current 
        15-minutes period
        "
	::= { pm10010ulhMonPerfTimeStamp 7 }


pm10010ulhPerfCurrent24HoursElapsedTime OBJECT-TYPE
	SYNTAX Counter32
	MAX-ACCESS read-write
	STATUS current
	DESCRIPTION
        "
        Current 24hours period Elapsed 
        Time :This OID gives the number 
        of seconds elapsed in the current 
        24-hours period
        "
	::= { pm10010ulhMonPerfTimeStamp 8 }






--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm10010ulhDwlrestartProcess OBJECT IDENTIFIER ::= { pm10010ulhDwlOther 0 }




pm10010ulhDwlColdRestartProcessed OBJECT-TYPE
	  SYNTAX EkiOnOff
	  MAX-ACCESS read-only
	  STATUS current
	  DESCRIPTION
        "
        Cold Restart :This OID indicates 
        that the module last restart was 
        a Cold RESTART
        "
	  ::= { pm10010ulhDwlrestartProcess 2 }



pm10010ulhDwlWarmRestartProcessed OBJECT-TYPE
	  SYNTAX EkiOnOff
	  MAX-ACCESS read-only
	  STATUS current
	  DESCRIPTION
        "
        Warm Restart :This OID indicates 
        that the module last restart was 
        a Warm RESTART
        "
	  ::= { pm10010ulhDwlrestartProcess 1 }



--- *****************************************************
---     LEAF for the swBanksUsed article
--- *****************************************************
pm10010ulhDwlswBanksUsed OBJECT IDENTIFIER ::= { pm10010ulhDwlOther 1 }




pm10010ulhDwlSwBank2Notempty OBJECT-TYPE
	  SYNTAX EkiOnOff
	  MAX-ACCESS read-only
	  STATUS current
	  DESCRIPTION
        "
        SW bank 2 loaded :This OID indicates 
        a software is loaded in SW bank 
        2  <Help>  This status indicates 
        if the SW bank 2 contains SW package
        "
	  ::= { pm10010ulhDwlswBanksUsed 6 }



pm10010ulhDwlSwBank1Notempty OBJECT-TYPE
	  SYNTAX EkiOnOff
	  MAX-ACCESS read-only
	  STATUS current
	  DESCRIPTION
        "
        SW bank 1 loaded :This OID indicates 
        a software is loaded in SW bank 
        1  <Help>  This status indicates 
        if the SW bank 1 contains SW package
        "
	  ::= { pm10010ulhDwlswBanksUsed 5 }



pm10010ulhDwlSwBank2Used OBJECT-TYPE
	  SYNTAX EkiOnOff
	  MAX-ACCESS read-only
	  STATUS current
	  DESCRIPTION
        "
        SW bank 2 active :This OID indicates 
        the module is working on SW bank 
        2  <Help>  This status indicates 
        if the SW bank 2 is active or standby
        "
	  ::= { pm10010ulhDwlswBanksUsed 2 }



pm10010ulhDwlSwBank1Used OBJECT-TYPE
	  SYNTAX EkiOnOff
	  MAX-ACCESS read-only
	  STATUS current
	  DESCRIPTION
        "
        SW bank 1 active :This OID indicates 
        the module is working on SW bank 
        1  <Help>  This status indicates 
        if the SW bank 1 is active or standby
        "
	  ::= { pm10010ulhDwlswBanksUsed 1 }



--- *****************************************************
---     LEAF for the gwBanksUsed article
--- *****************************************************
pm10010ulhDwlgwBanksUsed OBJECT IDENTIFIER ::= { pm10010ulhDwlOther 2 }




pm10010ulhDwlGwBank4Notempty OBJECT-TYPE
	  SYNTAX EkiOnOff
	  MAX-ACCESS read-only
	  STATUS current
	  DESCRIPTION
        "
        GW bank 4 loaded :This OID indicates 
        a gateware is loaded in GW bank 
        4
        "
	  ::= { pm10010ulhDwlgwBanksUsed 8 }



pm10010ulhDwlGwBank3Notempty OBJECT-TYPE
	  SYNTAX EkiOnOff
	  MAX-ACCESS read-only
	  STATUS current
	  DESCRIPTION
        "
        GW bank 3 loaded :This OID indicates 
        a gateware is loaded in GW bank 
        3  <Help>  This status indicates 
        if the GW bank 3 contains GW package
        "
	  ::= { pm10010ulhDwlgwBanksUsed 7 }



pm10010ulhDwlGwBank2Notempty OBJECT-TYPE
	  SYNTAX EkiOnOff
	  MAX-ACCESS read-only
	  STATUS current
	  DESCRIPTION
        "
        GW bank 2 loaded :This OID indicates 
        a gateware is loaded in GW bank 
        2
        "
	  ::= { pm10010ulhDwlgwBanksUsed 6 }



pm10010ulhDwlGwBank1Notempty OBJECT-TYPE
	  SYNTAX EkiOnOff
	  MAX-ACCESS read-only
	  STATUS current
	  DESCRIPTION
        "
        GW bank 1 loaded :This OID indicates 
        a gateware is loaded in GW bank 
        1  <Help>  This status indicates 
        if the GW bank 1 contains GW package
        "
	  ::= { pm10010ulhDwlgwBanksUsed 5 }



pm10010ulhDwlGwBank4Used OBJECT-TYPE
	  SYNTAX EkiOnOff
	  MAX-ACCESS read-only
	  STATUS current
	  DESCRIPTION
        "
        GW bank 4 active :This OID indicates 
        the module is working on GW bank 
        4
        "
	  ::= { pm10010ulhDwlgwBanksUsed 4 }



pm10010ulhDwlGwBank3Used OBJECT-TYPE
	  SYNTAX EkiOnOff
	  MAX-ACCESS read-only
	  STATUS current
	  DESCRIPTION
        "
        GW bank 3 active :This OID indicates 
        the module is working on GW bank 
        3  <Help>  This status indicates 
        if the GW bank 3 is active or standby
        "
	  ::= { pm10010ulhDwlgwBanksUsed 3 }



pm10010ulhDwlGwBank2Used OBJECT-TYPE
	  SYNTAX EkiOnOff
	  MAX-ACCESS read-only
	  STATUS current
	  DESCRIPTION
        "
        GW bank 2 active :This OID indicates 
        the module is working on GW bank 
        2
        "
	  ::= { pm10010ulhDwlgwBanksUsed 2 }



pm10010ulhDwlGwBank1Used OBJECT-TYPE
	  SYNTAX EkiOnOff
	  MAX-ACCESS read-only
	  STATUS current
	  DESCRIPTION
        "
        GW bank 1 active :This OID indicates 
        the module is working on GW bank 
        1  <Help>  This status indicates 
        if the GW bank 1 is active or standby
        "
	  ::= { pm10010ulhDwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm10010ulhCfgAccessCAisCsf OBJECT IDENTIFIER ::= { pm10010ulhConfig 1 }



--- *****************************************************
---     LEAF for the table 0012
--- *****************************************************

pm10010ulhCfgClientcaiscsfTable OBJECT-TYPE
	SYNTAX  SEQUENCE OF Pm10010ulhCfgClientcaiscsfEntry
	MAX-ACCESS not-accessible
	STATUS current
	DESCRIPTION
        "
        List of  Article
        "
	::= { pm10010ulhCfgAccessCAisCsf 1 }


pm10010ulhCfgClientcaiscsfEntry OBJECT-TYPE
	SYNTAX Pm10010ulhCfgClientcaiscsfEntry
	MAX-ACCESS not-accessible
	STATUS current
	DESCRIPTION
        "
        Row definition for the accessCAisCsf 
        table
        "
	INDEX   { pm10010ulhCfgClientcaiscsfIndex }
	::= { pm10010ulhCfgClientcaiscsfTable 1 }


Pm10010ulhCfgClientcaiscsfEntry ::=
	SEQUENCE {
	pm10010ulhCfgClientcaiscsfIndex
		INTEGER,
	pm10010ulhCfgReservePortn
		Unsigned32
	}


pm10010ulhCfgClientcaiscsfIndex OBJECT-TYPE
	SYNTAX  INTEGER(0..128)
	MAX-ACCESS  read-only
	STATUS current
	DESCRIPTION
        "
        Index definition for the clientcaiscsf 
        table
        "
	::= { pm10010ulhCfgClientcaiscsfEntry 1 }


pm10010ulhCfgReservePortn OBJECT-TYPE
	SYNTAX  Unsigned32 (0..65536)
	MAX-ACCESS read-write
	STATUS current
	DESCRIPTION
        "
        CAIS mode  on Client Port :This 
        register enables/disables port
          laser shutdown on CAIS insertion 
        condition
        "
	::= { pm10010ulhCfgClientcaiscsfEntry 3 }


--- *****************************************************
---     LEAF for the table Group startup
--- *****************************************************

pm10010ulhCfgStartup OBJECT IDENTIFIER ::= { pm10010ulhConfig 2 }



--- *****************************************************
---     LEAF for the table 2110
--- *****************************************************

pm10010ulhCfgClientStartupTable OBJECT-TYPE
	SYNTAX  SEQUENCE OF Pm10010ulhCfgClientStartupEntry
	MAX-ACCESS not-accessible
	STATUS current
	DESCRIPTION
        "
        List of  Article
        "
	::= { pm10010ulhCfgStartup 1 }


pm10010ulhCfgClientStartupEntry OBJECT-TYPE
	SYNTAX Pm10010ulhCfgClientStartupEntry
	MAX-ACCESS not-accessible
	STATUS current
	DESCRIPTION
        "
        Row definition for the startup 
        table
        "
	INDEX   { pm10010ulhCfgClientStartupIndex }
	::= { pm10010ulhCfgClientStartupTable 1 }


Pm10010ulhCfgClientStartupEntry ::=
	SEQUENCE {
	pm10010ulhCfgClientStartupIndex
		INTEGER,
	pm10010ulhCfgSystConfPortPortn
		Unsigned32,
	pm10010ulhCfgNetConfPortPortn
		Unsigned32,
	pm10010ulhCfgOptionsPortPortn
		Unsigned32
	}


pm10010ulhCfgClientStartupIndex OBJECT-TYPE
	SYNTAX  INTEGER(0..128)
	MAX-ACCESS  read-only
	STATUS current
	DESCRIPTION
        "
        Index definition for the clientStartup 
        table
        "
	::= { pm10010ulhCfgClientStartupEntry 1 }


pm10010ulhCfgSystConfPortPortn OBJECT-TYPE
	SYNTAX  Unsigned32 (0..65536)
	MAX-ACCESS read-write
	STATUS current
	DESCRIPTION
        "
        Default Settings on Client Port 
        :This  register configures the
         default initialisation settings 
        on the port.
        "
	::= { pm10010ulhCfgClientStartupEntry 3 }


pm10010ulhCfgNetConfPortPortn OBJECT-TYPE
	SYNTAX  Unsigned32 (0..65536)
	MAX-ACCESS read-write
	STATUS current
	DESCRIPTION
        "
        Default Settings on Client Port 
        :This  register configures the
         default initialisation settings 
        on the port.
        "
	::= { pm10010ulhCfgClientStartupEntry 4 }


pm10010ulhCfgOptionsPortPortn OBJECT-TYPE
	SYNTAX  Unsigned32 (0..65536)
	MAX-ACCESS read-write
	STATUS current
	DESCRIPTION
        "
        Default Options on Client Port 
        :This register configures the default 
        options on the port.
        "
	::= { pm10010ulhCfgClientStartupEntry 14 }


--- *****************************************************
---     LEAF for the table 2190
--- *****************************************************

pm10010ulhCfgLineStartupTable OBJECT-TYPE
	SYNTAX  SEQUENCE OF Pm10010ulhCfgLineStartupEntry
	MAX-ACCESS not-accessible
	STATUS current
	DESCRIPTION
        "
        List of  Article
        "
	::= { pm10010ulhCfgStartup 2 }


pm10010ulhCfgLineStartupEntry OBJECT-TYPE
	SYNTAX Pm10010ulhCfgLineStartupEntry
	MAX-ACCESS not-accessible
	STATUS current
	DESCRIPTION
        "
        Row definition for the startup 
        table
        "
	INDEX   { pm10010ulhCfgLineStartupIndex }
	::= { pm10010ulhCfgLineStartupTable 1 }


Pm10010ulhCfgLineStartupEntry ::=
	SEQUENCE {
	pm10010ulhCfgLineStartupIndex
		INTEGER,
	pm10010ulhCfgSystConfLinePortn
		Unsigned32,
	pm10010ulhCfgOptionsLinePortn
		Unsigned32
	}


pm10010ulhCfgLineStartupIndex OBJECT-TYPE
	SYNTAX  INTEGER(0..128)
	MAX-ACCESS  read-only
	STATUS current
	DESCRIPTION
        "
        Index definition for the lineStartup 
        table
        "
	::= { pm10010ulhCfgLineStartupEntry 1 }


pm10010ulhCfgSystConfLinePortn OBJECT-TYPE
	SYNTAX  Unsigned32 (0..65536)
	MAX-ACCESS read-write
	STATUS current
	DESCRIPTION
        "
        Default Settings on Line :This 
        register configures the default 
        initialisation settings on Line
        "
	::= { pm10010ulhCfgLineStartupEntry 3 }


pm10010ulhCfgOptionsLinePortn OBJECT-TYPE
	SYNTAX  Unsigned32 (0..65536)
	MAX-ACCESS read-write
	STATUS current
	DESCRIPTION
        "
        Default Options on Line :This
         register configures the default 
        options on the line
        "
	::= { pm10010ulhCfgLineStartupEntry 14 }


--- *****************************************************
---     LEAF for the table 21AB
--- *****************************************************

pm10010ulhCfgXfpTable OBJECT-TYPE
	SYNTAX  SEQUENCE OF Pm10010ulhCfgXfpEntry
	MAX-ACCESS not-accessible
	STATUS current
	DESCRIPTION
        "
        List of  Article
        "
	::= { pm10010ulhCfgStartup 3 }


pm10010ulhCfgXfpEntry OBJECT-TYPE
	SYNTAX Pm10010ulhCfgXfpEntry
	MAX-ACCESS not-accessible
	STATUS current
	DESCRIPTION
        "
        Row definition for the startup 
        table
        "
	INDEX   { pm10010ulhCfgXfpIndex }
	::= { pm10010ulhCfgXfpTable 1 }


Pm10010ulhCfgXfpEntry ::=
	SEQUENCE {
	pm10010ulhCfgXfpIndex
		INTEGER,
	pm10010ulhCfgSystConfMsaLinePortn
		Unsigned32
	}


pm10010ulhCfgXfpIndex OBJECT-TYPE
	SYNTAX  INTEGER(0..128)
	MAX-ACCESS  read-only
	STATUS current
	DESCRIPTION
        "
        Index definition for the xfp table
        "
	::= { pm10010ulhCfgXfpEntry 1 }


pm10010ulhCfgSystConfMsaLinePortn OBJECT-TYPE
	SYNTAX  Unsigned32 (0..65536)
	MAX-ACCESS read-write
	STATUS current
	DESCRIPTION
        "
        Default settings on MSA :This
         register configures the default 
        initialisation settings on MSA
        "
	::= { pm10010ulhCfgXfpEntry 3 }


--- *****************************************************
---     LEAF for the table Group labels
--- *****************************************************

pm10010ulhCfgLabels OBJECT IDENTIFIER ::= { pm10010ulhConfig 3 }



--- *****************************************************
---     LEAF for the table 0003
--- *****************************************************

pm10010ulhCfgLabelclientTable OBJECT-TYPE
	SYNTAX  SEQUENCE OF Pm10010ulhCfgLabelclientEntry
	MAX-ACCESS not-accessible
	STATUS current
	DESCRIPTION
        "
        List of  Article
        "
	::= { pm10010ulhCfgLabels 1 }


pm10010ulhCfgLabelclientEntry OBJECT-TYPE
	SYNTAX Pm10010ulhCfgLabelclientEntry
	MAX-ACCESS not-accessible
	STATUS current
	DESCRIPTION
        "
        Row definition for the labels
         table
        "
	INDEX   { pm10010ulhCfgLabelclientIndex }
	::= { pm10010ulhCfgLabelclientTable 1 }


Pm10010ulhCfgLabelclientEntry ::=
	SEQUENCE {
	pm10010ulhCfgLabelclientIndex
		INTEGER,
	pm10010ulhCfgLabelclientPortn
		DisplayString
	}


pm10010ulhCfgLabelclientIndex OBJECT-TYPE
	SYNTAX  INTEGER(0..128)
	MAX-ACCESS  read-only
	STATUS current
	DESCRIPTION
        "
        Index definition for the labelclient 
        table
        "
	::= { pm10010ulhCfgLabelclientEntry 1 }


pm10010ulhCfgLabelclientPortn OBJECT-TYPE
	SYNTAX  DisplayString( SIZE(1..16))
	MAX-ACCESS read-write
	STATUS current
	DESCRIPTION
        "
        Default settings on the label
         of the Ports :These registers
         configures the default initialisation 
        settings of the labels of the ports.
        "
	::= { pm10010ulhCfgLabelclientEntry 3 }


--- *****************************************************
---     LEAF for the table 0004
--- *****************************************************

pm10010ulhCfgLabellineTable OBJECT-TYPE
	SYNTAX  SEQUENCE OF Pm10010ulhCfgLabellineEntry
	MAX-ACCESS not-accessible
	STATUS current
	DESCRIPTION
        "
        List of  Article
        "
	::= { pm10010ulhCfgLabels 2 }


pm10010ulhCfgLabellineEntry OBJECT-TYPE
	SYNTAX Pm10010ulhCfgLabellineEntry
	MAX-ACCESS not-accessible
	STATUS current
	DESCRIPTION
        "
        Row definition for the labels
         table
        "
	INDEX   { pm10010ulhCfgLabellineIndex }
	::= { pm10010ulhCfgLabellineTable 1 }


Pm10010ulhCfgLabellineEntry ::=
	SEQUENCE {
	pm10010ulhCfgLabellineIndex
		INTEGER,
	pm10010ulhCfgLabellinePortn
		DisplayString
	}


pm10010ulhCfgLabellineIndex OBJECT-TYPE
	SYNTAX  INTEGER(0..128)
	MAX-ACCESS  read-only
	STATUS current
	DESCRIPTION
        "
        Index definition for the labelline 
        table
        "
	::= { pm10010ulhCfgLabellineEntry 1 }


pm10010ulhCfgLabellinePortn OBJECT-TYPE
	SYNTAX  DisplayString( SIZE(1..16))
	MAX-ACCESS read-write
	STATUS current
	DESCRIPTION
        "
        Default settings on the label
         of the lines :These registers
         configures the default initialisation 
        settings of the labels of the lines.
        "
	::= { pm10010ulhCfgLabellineEntry 3 }


--- *****************************************************
---     LEAF for the table Group startuptlh
--- *****************************************************

pm10010ulhCfgStartuptlh OBJECT IDENTIFIER ::= { pm10010ulhConfig 4 }



--- *****************************************************
---     LEAF for the table 25AB
--- *****************************************************

pm10010ulhCfgOtxtlhTable OBJECT-TYPE
	SYNTAX  SEQUENCE OF Pm10010ulhCfgOtxtlhEntry
	MAX-ACCESS not-accessible
	STATUS current
	DESCRIPTION
        "
        List of  Article
        "
	::= { pm10010ulhCfgStartuptlh 1 }


pm10010ulhCfgOtxtlhEntry OBJECT-TYPE
	SYNTAX Pm10010ulhCfgOtxtlhEntry
	MAX-ACCESS not-accessible
	STATUS current
	DESCRIPTION
        "
        Row definition for the startuptlh 
        table
        "
	INDEX   { pm10010ulhCfgOtxtlhIndex }
	::= { pm10010ulhCfgOtxtlhTable 1 }


Pm10010ulhCfgOtxtlhEntry ::=
	SEQUENCE {
	pm10010ulhCfgOtxtlhIndex
		INTEGER,
	pm10010ulhCfgLinePwrLaserPortn
		Unsigned32,
	pm10010ulhCfgLineFCurrentPortn
		Unsigned32,
	pm10010ulhCfgLineGridCurrentPortn
		Unsigned32,
	pm10010ulhCfgFPortn
		Unsigned32,
	pm10010ulhCfgRxLineFCurrentPortn
		Unsigned32
	}


pm10010ulhCfgOtxtlhIndex OBJECT-TYPE
	SYNTAX  INTEGER(0..128)
	MAX-ACCESS  read-only
	STATUS current
	DESCRIPTION
        "
        Index definition for the otxtlh 
        table
        "
	::= { pm10010ulhCfgOtxtlhEntry 1 }


pm10010ulhCfgLinePwrLaserPortn OBJECT-TYPE
	SYNTAX  Unsigned32 (0..65536)
	MAX-ACCESS read-write
	STATUS current
	DESCRIPTION
        "
        Defaut Line output Power :This 
        register configures the start-up 
        output power of the Line tranceiver 
         (Unit = dBm)
        "
	::= { pm10010ulhCfgOtxtlhEntry 6 }


pm10010ulhCfgLineFCurrentPortn OBJECT-TYPE
	SYNTAX  Unsigned32 (0..65536)
	MAX-ACCESS read-write
	STATUS current
	DESCRIPTION
        "
        Default Line transceiver Tx Channel 
        :This register configures the start-up 
        laser channel of the Line Tx transceiver
        "
	::= { pm10010ulhCfgOtxtlhEntry 7 }


pm10010ulhCfgLineGridCurrentPortn OBJECT-TYPE
	SYNTAX  Unsigned32 (0..65536)
	MAX-ACCESS read-write
	STATUS current
	DESCRIPTION
        "
        Default Line transceiver Grid
         :This register configures the
         start-up laser grid of the Line 
        transceiver
        "
	::= { pm10010ulhCfgOtxtlhEntry 8 }


pm10010ulhCfgFPortn OBJECT-TYPE
	SYNTAX  Unsigned32 (0..65536)
	MAX-ACCESS read-write
	STATUS current
	DESCRIPTION
        "
        Default Line TRX lowest Freq :This 
        register configures the start-up 
        lowest frequency of the Line transceiver
        "
	::= { pm10010ulhCfgOtxtlhEntry 9 }


pm10010ulhCfgRxLineFCurrentPortn OBJECT-TYPE
	SYNTAX  Unsigned32 (0..65536)
	MAX-ACCESS read-write
	STATUS current
	DESCRIPTION
        "
        Default Line transceiver Rx Channel 
        :This register configures the start-up 
        laser channel of the Line Rx transceiver
        "
	::= { pm10010ulhCfgOtxtlhEntry 10 }


--- *****************************************************
---     LEAF for the table Group other
--- *****************************************************

pm10010ulhCfgOther OBJECT IDENTIFIER ::= { pm10010ulhConfig 5 }



--- *****************************************************
---     LEAF for the table 2300
--- *****************************************************

pm10010ulhtablemoduleOther OBJECT IDENTIFIER ::= { pm10010ulhCfgOther 1 }



pm10010ulhCfgmode OBJECT-TYPE
	  SYNTAX Unsigned32 (0..65536)
	  MAX-ACCESS read-write
	  STATUS current
	  DESCRIPTION
        "
        Default settings on Module :This 
        register selects the configuration 
        mode of the module
        "
	  ::= { pm10010ulhtablemoduleOther 2 }



pm10010ulhCfgfanLowSpeedThreshold OBJECT-TYPE
	  SYNTAX Unsigned32 (0..65536)
	  MAX-ACCESS read-write
	  STATUS current
	  DESCRIPTION
        "
        Default settings on Module :This 
        register selects the speed threshold 
        of the fan's
        "
	  ::= { pm10010ulhtablemoduleOther 3 }



pm10010ulhCfgfanHighSpeedThreshold OBJECT-TYPE
	  SYNTAX Unsigned32 (0..65536)
	  MAX-ACCESS read-write
	  STATUS current
	  DESCRIPTION
        "
        Default settings on Module :This 
        register selects the speed threshold 
        of the fan's
        "
	  ::= { pm10010ulhtablemoduleOther 4 }



--- *****************************************************
---     LEAF for the table Group startuptablefive
--- *****************************************************

pm10010ulhCfgStartuptablefive OBJECT IDENTIFIER ::= { pm10010ulhConfig 6 }



--- *****************************************************
---     LEAF for the table 0005
--- *****************************************************

pm10010ulhCfgOtxtlhcapabilitiesTable OBJECT-TYPE
	SYNTAX  SEQUENCE OF Pm10010ulhCfgOtxtlhcapabilitiesEntry
	MAX-ACCESS not-accessible
	STATUS current
	DESCRIPTION
        "
        List of  Article
        "
	::= { pm10010ulhCfgStartuptablefive 1 }


pm10010ulhCfgOtxtlhcapabilitiesEntry OBJECT-TYPE
	SYNTAX Pm10010ulhCfgOtxtlhcapabilitiesEntry
	MAX-ACCESS not-accessible
	STATUS current
	DESCRIPTION
        "
        Row definition for the startuptablefive 
        table
        "
	INDEX   { pm10010ulhCfgOtxtlhcapabilitiesIndex }
	::= { pm10010ulhCfgOtxtlhcapabilitiesTable 1 }


Pm10010ulhCfgOtxtlhcapabilitiesEntry ::=
	SEQUENCE {
	pm10010ulhCfgOtxtlhcapabilitiesIndex
		INTEGER,
	pm10010ulhCfgComponentTypePortn
		Unsigned32,
	pm10010ulhCfgMiscellaneousPortn
		Unsigned32,
	pm10010ulhCfgFirstChannelPortn
		Unsigned32,
	pm10010ulhCfgLastChannelPortn
		Unsigned32,
	pm10010ulhCfgGridPortn
		Unsigned32
	}


pm10010ulhCfgOtxtlhcapabilitiesIndex OBJECT-TYPE
	SYNTAX  INTEGER(0..128)
	MAX-ACCESS  read-only
	STATUS current
	DESCRIPTION
        "
        Index definition for the otxtlhcapabilities 
        table
        "
	::= { pm10010ulhCfgOtxtlhcapabilitiesEntry 1 }


pm10010ulhCfgComponentTypePortn OBJECT-TYPE
	SYNTAX  Unsigned32 (0..65536)
	MAX-ACCESS read-only
	STATUS current
	DESCRIPTION
        "
        Component parameters :This OID 
        defines the component parameters
        "
	::= { pm10010ulhCfgOtxtlhcapabilitiesEntry 3 }


pm10010ulhCfgMiscellaneousPortn OBJECT-TYPE
	SYNTAX  Unsigned32 (0..65536)
	MAX-ACCESS read-only
	STATUS current
	DESCRIPTION
        "
        Miscellaneous default settings 
        :This OID defines the miscellaneous 
        parameters
        "
	::= { pm10010ulhCfgOtxtlhcapabilitiesEntry 4 }


pm10010ulhCfgFirstChannelPortn OBJECT-TYPE
	SYNTAX  Unsigned32 (0..65536)
	MAX-ACCESS read-only
	STATUS current
	DESCRIPTION
        "
        Number of the first channel of 
        the component :This OID defines 
        the first channel number of the 
        PM
        "
	::= { pm10010ulhCfgOtxtlhcapabilitiesEntry 5 }


pm10010ulhCfgLastChannelPortn OBJECT-TYPE
	SYNTAX  Unsigned32 (0..65536)
	MAX-ACCESS read-only
	STATUS current
	DESCRIPTION
        "
        Number of the last channel of
         the component :This OID defines 
        the last channel number of the
         PM
        "
	::= { pm10010ulhCfgOtxtlhcapabilitiesEntry 6 }


pm10010ulhCfgGridPortn OBJECT-TYPE
	SYNTAX  Unsigned32 (0..65536)
	MAX-ACCESS read-only
	STATUS current
	DESCRIPTION
        "
        Grid value of the component :This 
        OID defines the grid of the PM
        "
	::= { pm10010ulhCfgOtxtlhcapabilitiesEntry 7 }



pm10010ulhCfgWriteConfiguration  OBJECT-TYPE
	SYNTAX EkiOnOff
	MAX-ACCESS read-write
	STATUS current
	DESCRIPTION
	"Write configuration to module:This OID 
	 writes the complete configuration to the module"
	::= { pm10010ulhConfig 257 }






--- *****************************************************
---     TRAP OBJECTS
--- *****************************************************

pm10010ulhtrapPortNumber OBJECT-TYPE
	SYNTAX INTEGER(1..64)
	MAX-ACCESS read-only
	STATUS current
	DESCRIPTION
	"Last port which generates a trap"
	::= { pm10010ulhtraps 2 }

pm10010ulhtrapLineNumber OBJECT-TYPE
	SYNTAX INTEGER(1..64)
	MAX-ACCESS read-only
	STATUS current
	DESCRIPTION
	"Last Line which generates a trap"
	::= { pm10010ulhtraps 3 }

pm10010ulhtrapBoardNumber OBJECT-TYPE
	SYNTAX INTEGER(1..64)
	MAX-ACCESS read-only
	STATUS current
	DESCRIPTION
	"Last module which generates a trap"
	::= { pm10010ulhtraps 4 }







--- *****************************************************
---     LINE TRAPS
--- *****************************************************

pm10010ulhLineTrapNotUrgentGoesOn NOTIFICATION-TYPE
	OBJECTS {pm10010ulhAlmLineDdmWarningPortn, pm10010ulhtrapLineNumber, pm10010ulhtrapBoardNumber}
	STATUS current
	--&FILTNAME    "PM10010ULH Line Not Urgent ON"
	--&ACTIONS     { log, minor }
	--&MATCH       { pm10010ulhAlmLineDdmWarningPortn "on", pm10010ulhtrapLineNumber "$2", pm10010ulhtrapBoardNumber "$3"}
	--&MESG        "DDM Warning appears on Line Port $2 of PM10010ULH in Slot $3 ($A)"
	DESCRIPTION "Not urgent Line default is activated"
	::= { pm10010ulhtraps 30 }

pm10010ulhLineTrapNotUrgentGoesOff NOTIFICATION-TYPE
	OBJECTS {pm10010ulhAlmLineDdmWarningPortn, pm10010ulhtrapLineNumber, pm10010ulhtrapBoardNumber}
	STATUS current
	--&FILTNAME    "PM10010ULH Line Not Urgent OFF"
	--&ACTIONS     { log, normal }
	--&CLEARS      { "PM10010ULH Line Not Urgent ON" }
	--&MATCH       { pm10010ulhAlmLineDdmWarningPortn "on", pm10010ulhtrapLineNumber "$2", pm10010ulhtrapBoardNumber "$3"}
	--&MESG        "DDM Warning disappears on Line Port $2 of PM10010ULH in Slot $3 ($A)"
	DESCRIPTION "Not urgent Line default disappeared"
	::= { pm10010ulhtraps 31 }

pm10010ulhLineTrapUrgentGoesOn NOTIFICATION-TYPE
	OBJECTS {pm10010ulhAlmLineDdmAlmPortn, pm10010ulhtrapLineNumber, pm10010ulhtrapBoardNumber}
	STATUS current
	--&FILTNAME    "PM10010ULH Line Urgent ON"
	--&ACTIONS     { log, major }
	--&MATCH       { pm10010ulhAlmLineDdmAlmPortn "on", pm10010ulhtrapLineNumber "$2", pm10010ulhtrapBoardNumber "$3"}
	--&MESG        "DDM Alarm appears on Line Port $2 of PM10010ULH in Slot $3 ($A)"
	DESCRIPTION "Urgent Line default is activated"
	::= { pm10010ulhtraps 32 }

pm10010ulhLineTrapUrgentGoesOff NOTIFICATION-TYPE
	OBJECTS {pm10010ulhAlmLineDdmAlmPortn, pm10010ulhtrapLineNumber, pm10010ulhtrapBoardNumber}
	STATUS current
	--&FILTNAME    "PM10010ULH Line Urgent OFF"
	--&ACTIONS     { log, normal }
	--&CLEARS      { "PM10010ULH Line Urgent ON" }
	--&MATCH       { pm10010ulhAlmLineDdmAlmPortn "on", pm10010ulhtrapLineNumber "$2", pm10010ulhtrapBoardNumber "$3"}
	--&MESG        "DDM Alarm disappears on Line Port $2 of PM10010ULH in Slot $3 ($A)"
	DESCRIPTION "Urgent Line default disappeared"
	::= { pm10010ulhtraps 33 }

pm10010ulhLineTrapCritGoesOn NOTIFICATION-TYPE
	OBJECTS {pm10010ulhAlmLineFailPortn , pm10010ulhAlmLineHwFailPortn , pm10010ulhtrapLineNumber, pm10010ulhtrapBoardNumber}
	STATUS current
	--&FILTNAME    "PM10010ULH Line Fail ON"
	--&ACTIONS     { log, critical }
	--&MATCH       { pm10010ulhAlmLineFailPortn "on", pm10010ulhAlmLineHwFailPortn "*", pm10010ulhtrapLineNumber "$3", pm10010ulhtrapBoardNumber "$4"}
	--&MESG        "Line Port $3 Down on PM10010ULH in Slot $4 ($A)"
	
	--&FILTNAME    "PM10010ULH Line HW Fail ON (Hidden)"
	--&ACTIONS     { info }
	--&MATCH       { pm10010ulhAlmLineFailPortn "*", pm10010ulhAlmLineHwFailPortn "on", pm10010ulhtrapLineNumber "$3", pm10010ulhtrapBoardNumber "$4"}
	--&MESG        "Line Port $3 Down on PM10010ULH in Slot $4 ($A)"
	DESCRIPTION "Critical Line default is activated"
	::= { pm10010ulhtraps 34 }

pm10010ulhLineTrapCritGoesOff NOTIFICATION-TYPE
	OBJECTS {pm10010ulhAlmLineFailPortn , pm10010ulhAlmLineHwFailPortn , pm10010ulhtrapLineNumber, pm10010ulhtrapBoardNumber}
	STATUS current
	--&FILTNAME    "PM10010ULH Line Fail OFF"
	--&ACTIONS     { log,  normal }
	--&CLEARS      { "PM10010ULH Line Fail ON" }
	--&MATCH       { pm10010ulhAlmLineFailPortn "on", pm10010ulhAlmLineHwFailPortn "*", pm10010ulhtrapLineNumber "$3", pm10010ulhtrapBoardNumber "$4"}
	--&MESG        "Line Port $3 Up on PM10010ULH in Slot $4 ($A)"

	--&FILTNAME    "PM10010ULH Line HW Fail OFF (Hidden)"
	--&ACTIONS     { info }
	--&MATCH       { pm10010ulhAlmLineFailPortn "*", pm10010ulhAlmLineHwFailPortn "on", pm10010ulhtrapLineNumber "$3", pm10010ulhtrapBoardNumber "$4"}
	--&MESG        "Line Port $3 Up on PM10010ULH in Slot $4 ($A)"
	DESCRIPTION "Critical Line default disappeared"
	::= { pm10010ulhtraps 35 }






--- *****************************************************
---     CLIENT TRAPS
--- *****************************************************

pm10010ulhClientTrapNotUrgentGoesOn NOTIFICATION-TYPE
	OBJECTS {pm10010ulhAlmSfpDdmWarningPortn, pm10010ulhtrapPortNumber, pm10010ulhtrapBoardNumber}
	STATUS current
		--&FILTNAME    "PM10010ULH Client Not Urgent ON"
		--&ACTIONS     { log, minor }
		--&MATCH       { pm10010ulhAlmSfpDdmWarningPortn "on", pm10010ulhtrapPortNumber "$2", pm10010ulhtrapBoardNumber "$3"}
		--&MESG        "DDM Warning appears on Client Port $2 of PM10010ULH in Slot $3 ($A)"
	DESCRIPTION "Not urgent client default is activated"
	::= { pm10010ulhtraps 40 }

pm10010ulhClientTrapNotUrgentGoesOff NOTIFICATION-TYPE
	OBJECTS {pm10010ulhAlmSfpDdmWarningPortn, pm10010ulhtrapPortNumber, pm10010ulhtrapBoardNumber}
	STATUS current
		--&FILTNAME    "PM10010ULH Client Not Urgent OFF"
		--&ACTIONS     { log, normal }
		--&CLEARS      { "PM10010ULH Client Not Urgent ON" }
		--&MATCH       { pm10010ulhAlmSfpDdmWarningPortn "on", pm10010ulhtrapPortNumber "$2", pm10010ulhtrapBoardNumber "$3"}
		--&MESG        "DDM Warning appears on Client Port $2 of PM10010ULH in Slot $3 ($A)"
	DESCRIPTION "Not urgent client default disappeared"
	::= { pm10010ulhtraps 41 }

pm10010ulhClientTrapUrgentGoesOn NOTIFICATION-TYPE
	OBJECTS {pm10010ulhAlmSfpDdmAlmPortn, pm10010ulhtrapPortNumber, pm10010ulhtrapBoardNumber}
	STATUS current
		--&FILTNAME    "PM10010ULH Client Urgent ON"
		--&ACTIONS     { log, major }
		--&MATCH       { pm10010ulhAlmSfpDdmAlmPortn "on", pm10010ulhtrapPortNumber "$2", pm10010ulhtrapBoardNumber "$3"}
		--&MESG        "DDM Alarm appears on Client Port $2 of PM10010ULH in Slot $3 ($A)"
	DESCRIPTION "Urgent client default is activated"
	::= { pm10010ulhtraps 42 }

pm10010ulhClientTrapUrgentGoesOff NOTIFICATION-TYPE
	OBJECTS {pm10010ulhAlmSfpDdmAlmPortn, pm10010ulhtrapPortNumber, pm10010ulhtrapBoardNumber}
	STATUS current
		--&FILTNAME    "PM10010ULH Client Urgent OFF"
		--&ACTIONS     { log, normal }
		--&CLEARS      { "PM10010ULH Client Urgent ON" }
		--&MATCH       { pm10010ulhAlmSfpDdmAlmPortn "on", pm10010ulhtrapPortNumber "$2", pm10010ulhtrapBoardNumber "$3"}
		--&MESG        "DDM Alarm disappears on Client Port $2 of PM10010ULH in Slot $3 ($A)"
	DESCRIPTION "Urgent client default disappeared"
	::= { pm10010ulhtraps 43 }

pm10010ulhClientTrapCritGoesOn NOTIFICATION-TYPE
	OBJECTS {pm10010ulhAlmFailAccPortn, pm10010ulhAlmHwFailAccPortn, pm10010ulhtrapPortNumber, pm10010ulhtrapBoardNumber}
	STATUS current
		--&FILTNAME    "PM10010ULH Client Fail ON"
		--&ACTIONS     { log, critical }
		--&MATCH       { pm10010ulhAlmFailAccPortn "on", pm10010ulhAlmHwFailAccPortn "*", pm10010ulhtrapPortNumber "$3", pm10010ulhtrapBoardNumber "$4"}
		--&MESG        "Client Port $3 Down on PM10010ULH in Slot $4 ($A)"
		
		--&FILTNAME    "PM10010ULH Client HW Fail ON (Hidden)"
		--&ACTIONS     { info }
		--&MATCH       { pm10010ulhAlmFailAccPortn "*", pm10010ulhAlmHwFailAccPortn "on", pm10010ulhtrapPortNumber "$3", pm10010ulhtrapBoardNumber "$4"}
		--&MESG        "Client Port $3 Down on PM10010ULH in Slot $4 ($A)"
	DESCRIPTION "Critical client default is activated"
	::= { pm10010ulhtraps 44 }

pm10010ulhClientTrapCritGoesOff NOTIFICATION-TYPE
	OBJECTS {pm10010ulhAlmFailAccPortn, pm10010ulhAlmHwFailAccPortn, pm10010ulhtrapPortNumber, pm10010ulhtrapBoardNumber}
	STATUS current
		--&FILTNAME    "PM10010ULH Client Fail OFF"
		--&ACTIONS     { log, normal }
		--&CLEARS      { "PM10010ULH Client Fail ON" }
		--&MATCH       { pm10010ulhAlmFailAccPortn "on", pm10010ulhAlmHwFailAccPortn "*", pm10010ulhtrapPortNumber "$3", pm10010ulhtrapBoardNumber "$4"}
		--&MESG        "Client Port $3 Up on PM10010ULH in Slot $4 ($A)"
		
		--&FILTNAME    "PM10010ULH Client HW Fail OFF (Hidden)"
		--&ACTIONS     { info }
		--&MATCH       { pm10010ulhAlmFailAccPortn "*", pm10010ulhAlmHwFailAccPortn "on", pm10010ulhtrapPortNumber "$3", pm10010ulhtrapBoardNumber "$4"}
		--&MESG        "Client Port $3 Up on PM10010ULH in Slot $4 ($A)"
	DESCRIPTION "Critical client default disappeared"
	::= { pm10010ulhtraps 45 }






--- *****************************************************
---     HW TRAPS
--- *****************************************************

pm10010ulhPowerTrapUrgentGoesOn NOTIFICATION-TYPE
	OBJECTS {pm10010ulhAlmDefFuseB, pm10010ulhAlmDefFuseA , pm10010ulhtrapBoardNumber}
	STATUS current
		--&FILTNAME    "PM10010ULH Fuse A Fail ON"
		--&ACTIONS     { log, major }
		--&MATCH       { pm10010ulhAlmDefFuseB "*", pm10010ulhAlmDefFuseA "on", pm10010ulhtrapBoardNumber "$3"}
		--&MESG        "Power Input A Fail on PM10010ULH in Slot $3 ($A)"
	
		--&FILTNAME    "PM10010ULH Fuse B Fail ON"
		--&ACTIONS     { log, major }
		--&MATCH       { pm10010ulhAlmDefFuseB "on", pm10010ulhAlmDefFuseA "*", pm10010ulhtrapBoardNumber "$3"}
		--&MESG        "Power Input B Fail on PM10010ULH in Slot $3 ($A)"
	DESCRIPTION "Urgent power supply default is activated"
	::= { pm10010ulhtraps 50 }

pm10010ulhPowerTrapUrgentGoesOff NOTIFICATION-TYPE
	OBJECTS {pm10010ulhAlmDefFuseB, pm10010ulhAlmDefFuseA , pm10010ulhtrapBoardNumber}
	STATUS current
		--&FILTNAME    "PM10010ULH Fuse A&B Fail OFF"
		--&ACTIONS     { log, normal}
		--&CLEARS      { "PM10010ULH Fuse A Fail ON", "PM10010ULH Fuse B Fail ON" }
		--&MATCH       { pm10010ulhAlmDefFuseB "on", pm10010ulhAlmDefFuseA "on", pm10010ulhtrapBoardNumber "$3"}
		--&MESG        "Power Inputs A and B Present on PM10010ULH in Slot $3 ($A)"
	DESCRIPTION "Urgent power supply default disappeared"
	::= { pm10010ulhtraps 51 }






END
