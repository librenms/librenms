TREDESS-FS-MIB DEFINITIONS ::= BEGIN

IMPORTS
	NOTIFICATION-TYPE, OBJECT-TYPE, MODULE-IDENTITY,
	Unsigned32, enterprises, IpAddress, Integer32
		FROM SNMPv2-SMI
	MODULE-COMPLIANCE, NOTIFICATION-GROUP, OBJECT-GROUP
		FROM SNMPv2-CONF
	TEXTUAL-CONVENTION, TruthValue, MacAddress,
	DisplayString
		FROM SNMPv2-TC;

fsTredessMIB MODULE-IDENTITY
	LAST-UPDATED "202311301335Z"
	ORGANIZATION
		"TRedess 2010 S.L."
	CONTACT-INFO
		"support@tredess.com"
	DESCRIPTION
		"Root OID of Fourth Series TRedess MIB"

  REVISION "202311301335Z"
    DESCRIPTION
		"
			OID dabTimestampType renamed to dabAvailableTimestampType:
				and changed value: relativeAndAbsolute (1)

			Modified dabTistFct OID description

			New OID: dabFct0AsReference
		"

  REVISION "202306121416Z"
    DESCRIPTION
		"
			New OIDs:
				dstR1TsEtiOutputStreamTo
		"
		
  REVISION "202306061522Z"
    DESCRIPTION
		"
			New OIDs:
				dstR1TsEtiOutputWithouService
				socket1TimeWithoutService
				socket2TimeWithoutService  
				eti1TimeWithoutService  
				eti2TimeWithoutService  
		"

  REVISION "202304261408Z"
    DESCRIPTION
		"
			New OIDs:
				eti2ErrorStatus
				dabEti2
				serviceRackCooling7Board

			New branch for ETI2. New OIDs:
				eti2Enable, eti2DetectedLayer, eti2InputBitrate, eti2CorrectedRSCodewords, eti2NotCorrectedRSCodewords, eti2RxStatisticsReset
			
			New traps:
				automaticPowerCompensationTrap, eti2ErrorTrap
			
			New value for amplifierStageType OID: pw4F (6)

			Changed value name (rNp1Mode):
				swUpgrade now is maintenance
			
			Removed OIDs:
				serviceIdentifyAsiMatrix,serviceIdentifyRfMatrix, serviceIdentifyEtiMatrix
				isdbtPidFilteringLA, isdbtPidFilteringLB, isdbtPidFilteringLC
				serviceEtiInputsEnabled
		"

  REVISION "202302271417Z"
    DESCRIPTION
		"
			New OIDs
				automaticPowerCompensationEnable, compensationPerStage

			New value for dateTimeStatus: input(3)
		"
	
  REVISION "202302071539Z"
    DESCRIPTION
		"
			New OIDs
				socket1RxOutOfRangePackets, socket1RxFixedPackets
				socket2RxOutOfRangePackets, socket2RxFixedPackets
				serviceInput2
				r1p1AutoVDailyWindow
				r1p1AutoVAlarmEnable  
				rNp1AutoVDailyWindow  

			Fixed connectedWebUsers OID

			Modified OID r1p1InputValidation description
		"

  REVISION "202301111727Z"
    DESCRIPTION
		"
			New OID connectedWebUsers 
			New value for deviceBConfigurationA synchronizedModified(3)
		"

  REVISION "202212161310Z"
    DESCRIPTION
		"
			New OIDs
			dstReceiver1TsBissEnable, dstReceiver1TsBissMode, dstReceiver1TsBissPass, dstReceiver1TsBissInjectId
		"

  REVISION "202209021427Z"
    DESCRIPTION
		"
			Modified description OID configuredPower
			Use efficiencyShoulderTarget instead of efficiencyShoulderCalibration. Delete unused efficiencyShoulderCalibration. 
			New OID dttReceiver1CellId
			New OID r1p1RfSwitchStatus
		"

  REVISION "202205200906Z"
    DESCRIPTION
		"
			New value (null) in serviceInstallSyncBoard
			New value (atsc3) in ecBandwidthAdaptation  
		"

  REVISION "202203171559Z"
    DESCRIPTION
		"
			New OIDs:
				dttReceiver1BerMuteTrap, dttReceiver2BerMuteTrap,
				dttReceiver1BerMute  
				dttRx1IsdbtLACber, dttRx1IsdbtLBCber, dttRx1IsdbtLCCber  

				dabGfBoard  
				dstReceiver1TsEtiOutput: dstR1TsEtiOutputPid, dstR1TsEtiOutputType, dstR1TsEtiOutputLayer, dstR1TsEtiOutputInputBitrate
				dstR1TsEtiOutputStatistics: dstR1TsEOCorrectedRsCodewords, dstR1TsEONotCorrectedRsCodewords, dstR1TsEOResetCounters

				input1Pat, input2Pat, input3Pat, input4Pat

				inputChannelChannel  

				socket1DabFec, socket2DabFec  

			New value (null) in serviceInstallSyncBoard
		"

  REVISION "202202100728Z"
    DESCRIPTION
		"
			New OIDs:
				unlimitedPowerSw, monitoringSw
				dttRx1Level
		"

  REVISION "202112011027Z"
    DESCRIPTION
		"
			New OIDs:
				localNetmask, localMacAddr
				socket1UnicastNetmask, socket1MacAddr  
				socket2UnicastNetmask, socket2MacAddr  
				gbe1LinkConfiguration, gbe2LinkConfiguration, gbe3LinkConfiguration, gbe3LinkConfiguration,

			Removed OIDs:
				ifaceGbe1, ifaceGbe2, ifaceGbe3, ifaceGbe4
		"

  REVISION "202111251104Z"
    DESCRIPTION
		"
			New event traps:
				shortTermMonitoringEventTrap, autoconfFromInputEventTrap, channelAdaptationEventTrap
		"

  REVISION "202109271141Z"
    DESCRIPTION
		"
 			OID ecNonLinearPrecorrection and modNonLinearPrecorrectionEnable now can be set to:
			 	0: DAP off
			 	1: DAP adaptative
			 	2: DAP static

			New OIDs 
				ecNonLinearStoredPrecorrection ecNonLinearPrecorrectorFeedback
				modNonLinearStoredPrecorrection modNonLinearPrecorrectorFeedback
		"

  REVISION "202106140852Z"
    DESCRIPTION
		"
			Changed minimum value for inputLevelThreshold and inputLevelMeasureCalibration

			New OIDs:
				dttRx1Mer, dttRx1Snr
		"

  REVISION "202105051130Z"
    DESCRIPTION
		"
			New value (minimumPower) for OIDs input01Mode, input02Mode

			New value for RedundancyDeviceStatus: loadNotReadyMaxRestorations 

			New OIDs:
				bissDecription, btsDecompressionRma  

			Changed values for serviceNumberOfAmplifierStages OID

		"
  REVISION "202103231203Z"
    DESCRIPTION
		"
			New OIDs: rfPowerSample, rfBooster
		"

  REVISION "202103011335Z"
    DESCRIPTION
		"
			New OID: amplifierHwRevision
		"

  REVISION "202102251309Z"
    DESCRIPTION
		"
			New amplifierHw options: PW_1F, PW_1G, PW_1H
		"

  REVISION "202101261116Z"
    DESCRIPTION
		"
			r1p1Mode new maintenance mode

			New Oids: 
				dabTistFct

			New Oids for ISDB-T Receiver
				dttRx1IsdbtSystem,dttRx1IsdbtMode,dttRx1IsdbtGuard,dttRx1IsdbtEws,dttRx1IsdbtPartialRx
				dttRx1IsdbtLASegments,dttRx1IsdbtLAInterleaveLength,dttRx1IsdbtLAConstellation,dttRx1IsdbtLACodeRate,dttRx1IsdbtLABERbeforeRS
				dttRx1IsdbtLBSegments,dttRx1IsdbtLBInterleaveLength,dttRx1IsdbtLBConstellation,dttRx1IsdbtLBCodeRate,dttRx1IsdbtLBBERbeforeRS
				dttRx1IsdbtLCSegments,dttRx1IsdbtLCInterleaveLength,dttRx1IsdbtLCConstellation,dttRx1IsdbtLCCodeRate,dttRx1IsdbtLCBERbeforeRS
				dstReceiver1Band
				isdbtCasBiss, isdbtCasMode,isdbtCasPass,isdbtCasInjectId
				isdbtBtsDecompression,isdbtBtsIipPid,isdbtBtsAuxPid,isdbtBtsPidRemapping,isdbtBtsRestorePcr,isdbtBtsBypass,
				isdbtBtsVirtualChannel,isdbtBtsChannel,isdbtBtsAreaCode,isdbtBts188BInputLocked,isdbtBts204BOutputLocked,
				isdbtDeletePids,isdbtPidListTable
				isdbtBufferDuration

			Changed limits values for OIDs: 
				isdbtRemoteControlIdKey, isdbtOverwriteRemoteControlIdKey

			Changed OID Name:
				isdbtBypassRemoteControlIdKey now is isdbtVirtualChannelBypass

			Changed value name:
				swUpgradeMode now is maintenanceMode

			New table dstServicesTable

			Removed OIDs:
				dstReceiver1TsCamProgramId, dstReceiver1TsProgramIdStatus

			Fixed inputFrequencyFlt OID

			New value for
				dstReceiver1Status
		"

  REVISION "202011191431Z"
    DESCRIPTION
		"
			Now it's possible to configure all parameters from An multiplex in a N+1 redundant system.
			Deleted the OIDs from branch redundancyNp1An:
				rNp1AnControlStatus,rNp1AnRfSwitchStatus,rNp1AnStatus,rNp1AnSwitchingCauses,rNp1AnManualSwitching,
				rNp1AnSyncWeb,rNp1AnSyncDate,rNp1AnSyncSnmp,rNp1AnSyncIO,rNp1AnSyncEvents,rNp1AnSyncInput,rNp1AnSyncRfInput,
				rNp1AnSyncCanceller,rNp1AnSyncModulator,rNp1AnSyncRfConfiguration,rNp1AnSyncMutes,rNp1AnSyncExternalAmplifier,
				rNp1AnSyncAmplifier,rNp1AnSyncReference
		"

  REVISION "202010021903Z"
	DESCRIPTION
		"
			New value loadReadyVerifing for RedundancyDeviceStatus Syntax
			New value reset (3) for input01Mode and input02Mode
			New values pw4D and pw4E for amplifierStageType
		"

  REVISION "202010011621Z"
    DESCRIPTION
		"
		New OID:
			dabMargin
		"

  REVISION "202009140830Z"
    DESCRIPTION
		"
			Removed OIDs: 
				dabCompensationDelayCfg, dabTotalDelay, dabAdditionalProcessingDelay  

			New OIDs:
				dabSynchronizationType, dabRelativeSfnReference, dabAbsoluteSfnReference, dabTimestampType

			Renamed OID:
			dabCompensationDelayCfg now is dabBufferingTime

			Modified OID:
				dabNetworkType is read-write
		"

  REVISION "202009081046Z"
    DESCRIPTION
		"
			New values systemReset for intput01Mode and input02Mode OIDs

			New OID: redundancyHwRfMatrixStatus

			ETI Matrix for redundancey systems. New OIDs:
				serviceDetectedEtiMatrix, serviceEtiInputsEnabled, serviceAssingAddressEtiMatrix, serviceDeleteAddressEtiMatrix
				serviceInstalledEtiMatrix1, serviceInstalledEtiMatrix2, serviceIdentifyEtiMatrix
				eti1Matrix1Hw,eti1Matrix2Hw,eti2Matrix1Hw,eti2Matrix2Hw,
				redundancyInputEtiMatrixStatus, redundancyHwEtiMatrixStatus
				New branch redundancyEti for ETI Redundancy Matrix with:
					etiMatrixControlStatus, etiMatrixHwStatus,etiMatrixSelected,eti1InputLoopStatus,eti2InputLoopStatus,
					etiMatrixInputStatusTable,etiMatrixInputStatusEntry,etiMatrixInputStatusIndex,eti1InputStatus,eti2InputStatus

			New traps:
				redundancyHwRfMatrixStatus, redundancyInputEtiMatrixStatus,	redundancyHwEtiMatrixStatus,
		"

  REVISION "202003230855Z"
	DESCRIPTION
		"
			New OIDs:
				ecUnmuteRetriesInterval
				dabCompensationDelayCfg, dabProcessingDelayCfg
				dabMinimumProcessingDelay, dabAdditionalProcessingDelay

				TrapHysteresis:
					geralTrapHysteresis, amplifierTrapHysteresis, amplifierStage1TrapHysteresis, amplifierStage2TrapHysteresis,	amplifierStage3TrapHysteresis, amplifierStage4TrapHysteresis, 
					amplifierStagesTrapHysteresis, asiTrapHysteresis, etiTrapHysteresis, ipInputTrapHysteresis, rxSat1TrapHysteresis, rxSat2TrapHysteresis, rxDtt1TrapHysteresis, rxDtt2TrapHysteresis,
					rfInTrapHysteresis, rackCoolingTrapHysteresis, cancellerTrapHysteresis, modulatorTrapHysteresis, rfOutTrapHysteresis, synchronizationTrapHysteresis, errorHwTrapHysteresis,
					fanTrapHysteresis, externalTrapHysteresis, powerSupplyTrapHysteresis, dcInputTrapHysteresis, redundancySysTrapHysteresis

			Renamed OID:
				dabNetworkDelay to dabTotalDelay

			Up to 7 cooling rack:
				new OID: rackCooling7Hw
				rackCoolingTable rcIndex up to 7
				new range to serviceAssignAddressCoolingBoard and serviceDeleteAddressCoolingBoard

			Fixed dvbt2GuardInterval values.

			New Sw Option for DAB Transmitter: dabSw
		"

  REVISION "202002131430Z"
    DESCRIPTION
        "
			New OIDs:
				dvbtRetransmissionDelay,

			New range for dvbtLocalDelay  
		"

  REVISION "202002121051Z"
    DESCRIPTION
		"
			Compibility with more than 4 external amplifiers.
				serviceNumberOfAmplifierStages up to eigth amplifiers
				New OIDs for it:
					amplifierStagesStatus,aSsInputLevelStatus,aSsExceededPowerStatus,aSsDecreasedPowerStatus,aSsReflectedPowerStatus,aSsTemperatureStatus,aSsHwErrorStatus,aSsPsusErrorStatus
				New table
					amplifierStagesTable
				New Traps:
					amplifierStagesSumTrap,aSsInputLevelTrap,aSsExceededPowerTrap,aSsDecreasedPowerTrap,aSsReflectedPowerTrap,aSsTemperatureTrap,aSsHwErrorTrap,aSsPsusErrorTrap
		"

  REVISION "202001221021Z"
    DESCRIPTION
		"
			Renamed OIDs: 
				asiMatrix1Hw to asi1Matrix1Hw
				asiMatrix2Hw to asi1Matrix2Hw
				asiMatrix3Hw to asi2Matrix1Hw
				asiMatrix4Hw to asi2Matrix2Hw
			Renamed option values of:
				serviceAssingAddressAsiMatrix serviceDeleteAddressAsiMatrix

			New OIDs:
				serviceDetectedAsiMatrix
				rfMatrix1Hw, rfMatrix2Hw  
				serviceInstalledAsiMatrix1, serviceInstalledAsiMatrix2
				serviceDetectedRfMatrix, serviceAssingAddressRfMatrix, serviceDeleteAddressRfMatrix, serviceInstalledRfMatrix, serviceIdentifyRfMatrix

			Removed OIDs:
				serviceAsiInputsEnabled

			New branch serviceRfMatrix

		"

  REVISION "201912230923Z"
    DESCRIPTION
		"
			New OIDs:
				ecSlopeCorrection
				dvbtBufferDuration
				dvbt2BufferDuration
				modulatorStandardAutoConfig  

			Fixed rNp1RfAControlEntry index value
		"

  REVISION "201911200831Z"
    DESCRIPTION
		"
			Removed table: 
				rNp1DeviceAConfigurationTable

			Add new tables:
				rNp1RfAControlTable  
				rNp1DeviceAPriorityTable  
		"
  REVISION "201910180810Z"
    DESCRIPTION
		"
			New OIDs:
				rNp1AutoVDailyMode  
				r1p1AutoVDailyMode  
		"

  REVISION "201909131231Z"
    DESCRIPTION
        "
			New value priorityDisabled for RedundancyDeviceStatus Syntax
		"

  REVISION "201907290901Z"
    DESCRIPTION
        "
			New value dummyAntenna for RedundancyDeviceStatus Syntax

			New OID:
				rNp1AnRfSwitchStatus

			New OID in rNp1DeviceAStatusTable: 
				deviceARfSwitchStatus
        "

  REVISION "201907080837Z"
    DESCRIPTION
		"
		New values for serviceAssignAddressCoolingBoard, serviceDeleteAddressCoolingBoard

		New OIDs:
			serviceRackCooling5Board, serviceRackCooling6Board, rackCooling5Hw, rackCooling6Hw

		New Range:
			rcIndex (up to 6)
		"

	REVISION "201906281423Z"
    DESCRIPTION
		"
			Deleted OIDs:
				synchronizationEnable
		
			Modified wrong syntax for socket1Protocol and socket2Protocol: rtp instead of tcp
		"

	REVISION "201904241012Z"
    DESCRIPTION
		"
			Deleted eti1Layer OID

			Satellite receiver (new OIDs)
				dstReceiver1Enable, dstReceiver1Status, dstReceiver1Temperature, dstReceiver1Frequency, dstReceiver1Polarization, dstReceiver1Satellite,
				dstReceiver1DvbMode, dstReceiver1SymbolRateMode, dstReceiver1ConfiguredSymbolRate, dstReceiver1MeasuredSymbolRate, dstReceiver1Rolloff,
				dstReceiver1Pilots, dstReceiver1FrameLength, dstReceiver1Modulation, dstReceiver1Fec, dstReceiver1PlsMode, dstReceiver1Pls, dstReceiver1Cber,
				dstReceiver1Vber, dstReceiver1Ldpc, dstReceiver1Per, dstReceiver1CN, dstReceiver1LinkMarginThreshold, dstReceiver1LinkMargin,
				dstReceiver1Level, dstReceiver1Mode, dstReceiver1LnbStatus, dstReceiver1LnbOlLow, dstReceiver1LnbBandSwitchingFreq, dstReceiver1LnbOlHigh,
				dstReceiver1Voltage, dstReceiver1Tone22kHz, dstReceiver1OlManual, dstReceiver1TsAvailableIsis, dstReceiver1TsIsi,	dstReceiver1TsRate, 
				dstReceiver1TsMode, dstReceiver1TsCamEnable, dstReceiver1TsCamProgramId, dstReceiver1TsCamStatus, dstReceiver1TsProgramIdStatus, dstReceiver1TsCamReset
				camSatReceiver1Status, smartCardSatReceiver1Status, smartCardRightsSatReceiver1Stat, asiOutputSatReceiver1Status 
				camSatReceiver1Trap, smartCardSatReceiver1Trap, smartCardRightsSatReceiver1Trap, asiOutputSatReceiver1Trap

			New OID:
				reverseRetriesInterval
				antennaStatus, ppsStatus
				r1p1SyncIO, rNp1AnSyncIO  
				r1p1SyncMutes, rNp1AnSyncMutes
		
			Renamed syntax:
				selected10Mhz, selected1Pps

			Modified Description:
				r1p1SyncEvents, rNp1AnSyncEvents

			Renamed OID:
				rNp1AnSyncRfOutput to rNp1AnSyncRfConfiguration  
				r1p1SyncRfOutput to r1p1SyncRfConfiguration
		"

	REVISION "201904080831Z"
    DESCRIPTION
		"
			localIp read-write
		"

  REVISION "201903281315Z"
    DESCRIPTION
		"
			Modified ASI Matrix information
				Deleted OIDs:
					asi1MatrixCtrl1Status, asi1MatrixCtrl2Status, asi1MatrixHwStatus, asi1MatrixSelected, asi1InputLoopStatus, asi1InputStatus
					asi2MatrixCtrl1Status, asi2MatrixCtrl2Status, asi2MatrixHwStatus, asi2MatrixSelected, asi2InputLoopStatus, asi2InputStatus
				New OIDs:
					asiMatrixControlStatus, asiMatrixHwStatus, asiMatrixSelected, asi1InputLoopStatus, asi2InputLoopStatus, asiMatrixInputStatusTable
		"

  REVISION "201903250830Z"
	  DESCRIPTION
		"
			rNp1Mode new value swUpgrade
			RedundancyDeviceStatus new option swUpgradeMode 
			New low limit for outputCentralFrequency outputCentralFrequencyMHz for DAB

			New OIDs: 
					rNp1SyncAllConfigurations
					dabBoard  
		"

  REVISION "201902111733Z"
    DESCRIPTION
		"
			Included modulatorDAB option:
				New OIDs:
					edi1:
						socket1and1Content,socket1Jitter,socket1RxPackets,socket1RxDisorderedPkts,socket1RxDuplicatedPkts,socket1RxReorderedPkts,socket1RxLostPkts,socket1RxStatisticsReset,
						socket1CorrectedRSCodewords, socket1NotCorrectedRSCodewords
					edi2:
						socket1and2Content,socket2Jitter,socket2RxPackets,socket2RxDisorderedPkts,socket2RxDuplicatedPkts,socket2RxReorderedPkts,socket2RxLostPkts,socket2RxStatisticsReset,
						socket2CorrectedRSCodewords, socket2NotCorrectedRSCodewords
					eti1:
						eti1Enable, eti1Layer, eti1DetectedLayer, eti1InputBitrate, eti1CorrectedRSCodewords, eti1NotCorrectedRSCodewords, eti1RxStatisticsReset
					dabSystem: 
						dabTransmitterId, dabMode,
					dabNetwork: 
						dabNetworkType,	dabDynamicCompensationDelay, dabMaximumBirate, dabBitrateOffset, dabTimestampLevel, dabLocalDelay, dabOffsetDelayAutoconfigure,
						dabTiiCode:
							dabTiiCodeConfiguration, dabMainId, dabSubId,
						dabTimeInformationGroup:
							dabReceivedInformationTime, dabDateAndTime, dabTimeAccurary, dabSynchronizationToFrame,
						dabTsc:
							dabReceivedTSC, dabSavedTSC, dabOffsetDelayTSC, dabMainIdTSC, dabSubIdTSC, dabControlFlagsTSC,
						dabTimmingInformation:
							dabProcessingDelay, dabCompensationDelay, dabNetworkDelay,
					dabOutputChannel  
					etiTable  
					statusModulator:
						inputDabErrorStatus, 
					statusEtiInput:
						etiInputStatus, eti1ErrorStatus
					traps:
						inputDabErrorStatusEventTrap, etiInputTrap, eti1ErrorTrap

				New values:
					New modulatorStandard value
		"

  REVISION "201902111020Z"
    DESCRIPTION
		"
			New OIDs:
				monitorOutput
				asi1MatrixCtrl1Status, asi1MatrixCtrl2Status, asi1MatrixHwStatus, asi1MatrixSelected, asi1InputLoopStatus, asi1InputStatus
				asi2MatrixCtrl1Status, asi2MatrixCtrl2Status, asi2MatrixHwStatus, asi2MatrixSelected, asi2InputLoopStatus, asi2InputStatus
				redundancyInputAsiMatrixStatus, redundancyHwMatrixStatus, redundancyInputAsiMatrixTrap, redundancyHwMatrixEventTrap
		"

  REVISION "201902031553Z"
    DESCRIPTION
		"
			New OID:
				serviceCanBusIdentifier
		"

  REVISION "201901091211Z"
    DESCRIPTION
		"
			New OIDs:
				modulatorBerStatus,modBerStatusTrap
				modBerFlt,isdbtBerLA,isdbtBerLB,isdbtBerLC,plpBer,
				input10Mhz  
		"

  REVISION "201812141011Z"
    DESCRIPTION
		"
			Modified rackCoolingTable: 
				Deleted rcPressureDifference
			New configuration alarm table redundancySysTable and redundancy alarms OIDs:
				redundancySysStatus, redundancySysCommunicationStatus, redundancySysSwitchStatus, redundancySysReserveStatus,
				redundancySysEventTrap, redundancySysComEventTrap, redundancySysSwitchEventTrap, redundancySysReserveEventTrap,
		"

  REVISION "201811270849Z"
    DESCRIPTION
		"
			New OIDs:
				serviceDualDriveRelay
		"

  REVISION "201809261300Z"
    DESCRIPTION
		"
			Modified Textual-convention for AlarmStatus(6) 'initAlarm' to 'uninitiatedAlarm'

			New OIDs:
				In the RackCoolingTable: rcPressureSensor
				Device Info: referenceHwSerialNumber

			New table for Device Info: amplifierStageInfoTable  

			New columns in externalAmplifierCoolingTable:
				amStFan1rpm  amStFan2rpm  

			ISDB-T issues:
				isdbtRegionId is Unsigned32 instead of DisplayString
				isdbtBtsRateLock now is visible (read-only)
			
			rNp1ConfigurationDeviceB must be read-write

			Modified RackCoolingEntry:
				Deleted rcPressureSensor,rcTemperatureThreshold
				Added rcExternalSensor1,rcExternalSensor2
				Rearrange OIDs

			New values for serviceTypeOfRedundancy:	nPlusOneB (5), nPlusOneA1 (6), nPlusOneA2 (7), ... nPlusOneA11 (16)
			
			serviceInstallUnitType on demand

			Deleted OIDs (never used):
				nPlusOneNvalue, nPlusOneIdentifier

		"

  REVISION "201808281101Z"
    DESCRIPTION
		"
			New OIDs:
				ntpServerAlternative: Alternative NTP server (for specific hardware)
				cancellerMerStatus
				rackCooling1Hw,rackCooling2Hw,rackCooling3Hw,rackCooling4Hw,
				asiMatrix1Hw,asiMatrix2Hw,asiMatrix3Hw,asiMatrix4Hw,
				serviceDetectedCoolingBoard,serviceAssignAddressCoolingBoard,serviceDeleteAddressCoolingBoard,serviceRackCooling1Board,serviceRackCooling2Board,serviceRackCooling3Board,serviceRackCooling4Board
				serviceAsiInputsEnabled,serviceAssingAddressAsiMatrix,serviceDeleteAddressAsiMatrix,serviceIdentifyAsiMatrix
				rackCoolingStatus,rackCoolingTemperatureStatus,pressureDifferenceStatus,rackCoolingHwErrorStatus,
				dcInputStatus

			New option value for ntpStatus: synchronizedAlternative 

			New table
				rackCoolingTable  
				rackCoolingAlarmConfTable  

			New traps:
				cancellerMerStatusTrap
				standardAutoConfigurationTrap  
				rackCoolingEventTrap,rackCoolingTemperatureEventTrap,rackCPressureDifferenceTrap,rackCoolingHwErrorEventTrap
				externalDcPowerSupplyEventTrap
				ioInterfaceInputEventTrap,ioInterfaceOutputEventTrap
				dcInputEventTrap
		"

  REVISION "201807110811Z"
    DESCRIPTION
		"
			Improved descriptions 

			New softwareOptions:
				np1Sw

			New option for serviceTypeOfRedundancy:
				nPlusOne
			
			New options
				loadNotReadyMaxVerifications (23), value 20 was previous version loadNotReadyMaxSwitchings
				antennaNokMaxRestorations (21) and antennaOkMaxRestorations (22) (just for N+1 redundancy)
				Defined textual convention for these values
			
			New OIDs:
				dcInVoltage
				outputFrequencyFlt (Value for Output Frequency in FloatingPoint format)
				inputFrequencyFlt (Value for Input Frequency in FloatingPoint format)
				outputCentralFrequencyMHz (outputCentralFrequency in MHz units)
				inputCentralFrequencyMHz (inputCentralFrequency in MHz units)
				modMerFlt (MER value in FloatingPoint format)
				reversePowerFlt (Reverse Power in FloatingPoint format)
				amStReversePowerFlt (Reverse Power in FloatingPoint format)
				New HardwareBase options: i2o8Interface, externalInterlock, i4o10Interface
				New serviceInstallHwSw options: nPlusOneNvalue, nPlusOneIdentifier
			
			New branchs: 
				redundancyNp1BConfiguration, redundancyNp1BSynchronization, redundancyNp1AnStatus, redundancyNp1AnSynchronization

			Deleted OIDs (never used): nPlusOneRedundancy, dualDriveRedundancy

			New options for redundancyId  OBJECT-TYPE:
				deviceNp1B (3), deviceNp1A1 (4), ... deviceNp1A11 (14)
			
			New HW Option dcConnector
		"

  REVISION "201807031146Z"
    DESCRIPTION
	    "
			New OID:
				trapsInitialStatus  
				sendAllTraps
		"

  REVISION "201806181005Z"
    DESCRIPTION
	    "
			DTT Receiver input:
				Read-only the OIDs: dttReceiver1Fec,dttReceiver1GuardInterval,dttReceiver1Fft,dttReceiver1T2Version,dttRx1T2PilotPattern	

			New softwareOptions: 
				atsc1Sw

			Obsoleted OIDs: 
				dvbtRateAdaptation, cancelInputCalibration
			
			New OIDs:
				efficiencyShoulderCalibration  
				serviceSwVersionFile
			
			New branch:
				serviceInstallHwSw with OIDs:
					serviceInstallSyncBoard, serviceRedundantPsu, serviceTypeOfRedundancy, serviceInstallUnitType, serviceNumberOfAmplifierStages, serviceInstallSwActivationCode
			
			Renamed OID: 
				serviceSwFile to serviceSwUpgradingFile
			
			In serviceSwStatus branch (ftp upgrading process):
				renamed processNeverExecuted to processNoExecuted 
				new value downloadProcessFailed
				new OID serviceSwDownload  
				deleted serviceSwPeriodic
		"

  REVISION "201802260801Z"
    DESCRIPTION
	    "
		ISDB-T Modulation changes:
			Obsoleted OIDs:
				isdbtPidFilteringLA, isdbtPidFilteringLB, isdbtPidFilteringLC
			New OID for ISDBT modulation:
				isdbtPidFiltering
				isdbtServicesA, isdbtServicesB, isdbtServicesC
				isdbtCountry, isdbtRegionId
				isdbtRfDelay
		"
  REVISION "201801251001Z"
  	DESCRIPTION
		"
		New OIDs:
	  		operationMode
			isdbtBypassRemoteControlIdKey
			tsErrorMuteHysteresis

		Modified:
			isdbtTSName,isdbtNetworkName max length
			dttReceiver1Frequency low frequency limit
			muteCausesBinary add new values Interlock 1, 2
		"

  REVISION "201712190813Z"
  	DESCRIPTION
		"
		New OIDs:
	  		dvbtRateAdaptation
		"

  REVISION "201711030901Z"
  	DESCRIPTION
		"
		New OIDs:
			decreasedOutputPowerNonCritical
			decreasedPowerThresholdNonCrit
			autoreturnToRemote
			dvbtAutoconfigurationFromDttRcv

		New TRAPs:
			decreasedOuputPowerNonCritTrap
			lockingStart1ppsEventTrap

		Modified values:
			rPrDdControlBusStatus new possible value: collisionError (4)
			amStControlStatus new possible values: errorNoSwVersion (3), errorNoAddress (4), errorCollision (5)
		"

  REVISION "201709210752Z"
    DESCRIPTION
		"
		DVB-T and DVB-T2 input receiver compatibility

		New branchs:
			dttReceiver1 and dttReceiver2
		"

  REVISION "201709200830Z"
    DESCRIPTION
		"
		New OIDs:
			endlessHoldoverThresholdEnable
			r1p1StatusA and r1p1StatusB news values

		New OID:
			ocxoReferenceHw
		"

  REVISION "201709070946Z"
    DESCRIPTION
		"
		New OIDs:
			automaticRfPhaseAdjustment
			muteCausesBinary

		Deleted OIDs:
  			efficiencyShoulderCalibration OID. Setting efficiencyShoulderTarget OID starts calibration
  			efficiencyMerCalibration OID. Setting efficiencyMerTarget OID starts calibration

		Modified values:
			rPrDdControlBusStatus new possible value: redundancyTypeError
			muteOutputStatus new possible value: stageMuted

		Syntax OIDs changed:
			rfReset and systemReset are now NullApply (Typed Integer) instead of Integer32

		Modified description:
			The values for 'muteCauses' and 'amStMuteSelfProtection' variables are specified in description.
		"

  REVISION "201709061131Z"
    DESCRIPTION
		"
		Modified values:
			higherPriorityHysteresis maximum is now 600 (seconds) instead of 120s
		"

  REVISION "201706260913Z"
    DESCRIPTION
		"
		New row synchronizationDD in alarmsConfiguration tables
		New branch r1p1Synchronization with OIDs:
			r1p1SyncWeb, r1p1SyncDate, r1p1SyncSnmp, r1p1SyncEvents, r1p1SyncInput, r1p1SyncRfInput, r1p1SyncCanceller,
			r1p1SyncModulator, r1p1SyncRfOutput, r1p1SyncAmplifier, r1p1SyncExternalAmplifier, r1p1SyncReference,
		Renamed OIDs:
			gmt to utcOffset
		New OIDs:
			timezone
			aS1PsusErrorStatus, aS2PsusErrorStatus, aS3PsusErrorStatus, aS4PsusErrorStatus
			aS1PsusErrorTrap, aS2PsusErrorTrap, aS3PsusErrorTrap, aS4PsusErrorTrap
			r1p1PriorityInversionEnable, r1p1PriorityInversionPeriod, r1p1PriorityInversionTime
		New Table:
			externalAmplifierCooling with: amStFanSpeed, amStFan1OperatingTime, amStFan2OperatingTime
		Moved OID:
			amStFanSpeed from amplifierStageTable to externalAmplifierCooling
		"

  REVISION "201706210821Z"
    DESCRIPTION
        "
		New trap binding: redundancyId
		Renamed OID:
			startLinearPrecorrection now is startLinearPrecorrectionBBPF
			eventTrapLogIndex (accesible-for-notify) now is eventTrapLogId
		New OID:
			startLinearPrecorrectionABPF
		New value:
			linearStatusPrecorrection now is: noCalibrated (0), calibratedBeforeBPF (1), calibratedAfterBPF (2)
		"

  REVISION "201706191340Z"
    DESCRIPTION
		"
		News OIDs:
			ISDBT Program Association
				isdbtAvailablePrograms
			ISDBT Broadcast Information:
				isdbtAffiliationId
			ISDBT Network Information:
				isdbtNetworkId, isdbtNetworkName, isdbtTransportStreamId, isdbtNetworkId, isdbtAreaCode, isdbtOverwriteAreaCode, isdbtFrequency, isdbtOverwriteFrequency, isdbtRemoteControlIdKey, isdbtOverwriteRemoteControlIdKey, isdbtTSName

		muteBtsError syntax is DisabledEnabled
		"

  REVISION "201706071910Z"
  	DESCRIPTION
		"
		New OIDs:
			redundantPsuHw
			trapsLocalMode

		Modified:
			fanSpeed and amStFanSpeed units
		"

  REVISION "201705120843Z"
    DESCRIPTION
	    "
		OID syntax amStMuteSelfProtection Integer to DisplayString

		Modified table amplifierStageTable: new OID amStRfPhase

		New OIDs:
			satellitesConstellationTable
			dualDriveSw

		Renamed OIDs:
			r1p1Enable - r1p1EnableNCB
			r1p1DeviceIdentifier - rPrDdDeviceIdentifier
			r1p1SystemIp - rPrDdSystemIp
			r1p1ControlBusStatus - rPrDdControlBusStatus
			r1p1SwitchToAntenna - rPrDdSwitchToAntenna

		Obsoleted:
			satellite01, satellite02, satellite03, satellite04, satellite05,
				satellite06, satellite07, satellite08 - satellitesConstellationTable instead of these
		"

  REVISION "201704261117Z"
    DESCRIPTION
	    "
		Changed UNITS Celsius for avoiding some compilation problems
		Renamed OIDs:
			psuAStatus to acPsuAStatus (some compilation warnings due to psuAstatus coincidence)
			psuBStatus to acPsuBStatus
			amplifierStagesTable to amplifierStageTable
		New OIDs:
			location
			r1p1InputValidation, r1p1PowerValidation, r1p1SwitchingHysteresis,
		"

  REVISION "201704190930Z"
    DESCRIPTION
	    "
		Added OIDs:
		    asiBypassEqualizers
			r1p1AutoVerificationsStatus
		Syntax OIDs changed:
			dvbtLocalDelay,dvbtMaximumNetworkDelay,dvbtTimeOffset
			isdbtLocalDelay,isdbtTimeOffset
		Moved OIDs:
			r1p1AutoVDuration,r1p1AutoVPerformedVerifications,r1p1AutoVMaxVerifications,r1p1AutoVNexVerification
		"

  REVISION "201703091236Z"
    DESCRIPTION
	    "
		Deleted OIDs:
			cancellerMerStatus, cancellerMerStatusTrap
			trapCommunity
		Added OIDs:
			cancelInputCalibration
			serviceSwUpgradeMode, serviceSwUpgradeServer, serviceSwUpgradeUser, serviceSwUpgradePassword, serviceSwDaily,
			serviceSwPeriodic, serviceSwFile, serviceSwStatus, serviceSwCheckNow, serviceSwDownloadNow, serviceSwUpgradeNow
			readCommunity2, writeCommunity2
			new row for trapSinkTable (trapSinkCommunity)
		Modified OIDs:
			readCommunity/writeCommunity is now called readCommunity1,writeCommunity1.

		Comments:
			ReadOnly/ReadWrite/Traps communities are now limited to 16 characters
	    "

  REVISION "201702220934Z"
    DESCRIPTION
		"
		Changed OIDs:
			r1p1StatusA and r1p1StatusB are read-only
			r1p1SwitchToAntenna is read-write
			New node (efficiencyImprovement) for efficiencyCalibration OIDs


		Relocated OIDs:
			muteGainMarginThreshold,ecGainMargin, muteErrorMip


		Added OIDs:
			acApparentPower,acEfficiency

		Renamed OIDs:
			serviceDCPowerSupply to servicePowerSupply

		New OIDs:
			psuAstatus,psuAacInputVoltage,psuAdcOutputVoltage,psuAtemperature,
			psuBstatus,psuBacInputVoltage,psuBdcOutputVoltage,psuBtemperature
			modThresholdMer,modMer
			cancellerMerStatus,gainMarginStatus,cancExternalFeedbackStatus,
			cancellerMerStatusTrap,gainMarginStatusTrap,cancExternalFeedbackStatusTrap,
			modulatorMerStatusTrap,modExternalFeedbackStatusTrap,
			modulatorMerStatus,modulatorExternalFeedbackStatus,
			amplifierStage1Table,amplifierStage1AlarmName,amplifierStage1AlarmStatus,amplifierStage1On,amplifierStage1Log,amplifierStage1Fault,
			amplifierStage1Warning,amplifierStage1Led,amplifierStage11p1,amplifierStage1Ext1,amplifierStage1Ext2,amplifierStage1Trap,
			amplifierStage2Table,amplifierStage2AlarmName,amplifierStage2AlarmStatus,amplifierStage2On,amplifierStage2Log,amplifierStage2Fault,
			amplifierStage2Warning,amplifierStage2Led,amplifierStage21p1,amplifierStage2Ext1,amplifierStage2Ext2,amplifierStage2Trap,
			amplifierStage3Table,amplifierStage3AlarmName,amplifierStage3AlarmStatus,amplifierStage3On,amplifierStage3Log,amplifierStage3Fault,
			amplifierStage3Warning,amplifierStage3Led,amplifierStage31p1,amplifierStage3Ext1,amplifierStage3Ext2,amplifierStage3Trap,
			amplifierStage4Table,amplifierStage4AlarmName,amplifierStage4AlarmStatus,amplifierStage4On,amplifierStage4Log,amplifierStage4Fault,
			amplifierStage4Warning,amplifierStage4Led,amplifierStage41p1,amplifierStage4Ext1,amplifierStage4Ext2,amplifierStage4Trap,
			amplifierStage1Status,aS1InputLevelStatus,aS1ExceededPowerStatus,aS1DecreasedPowerStatus,aS1ReflectedPowerStatus,aS1TemperatureStatus,aS1HwErrorStatus,
			amplifierStage2Status,aS2InputLevelStatus,aS2ExceededPowerStatus,aS2DecreasedPowerStatus,aS2ReflectedPowerStatus,aS2TemperatureStatus,aS2HwErrorStatus,
			amplifierStage3Status,aS3InputLevelStatus,aS3ExceededPowerStatus,aS3DecreasedPowerStatus,aS3ReflectedPowerStatus,aS3TemperatureStatus,aS3HwErrorStatus,
			amplifierStage4Status,aS4InputLevelStatus,aS4ExceededPowerStatus,aS4DecreasedPowerStatus,aS4ReflectedPowerStatus,aS4TemperatureStatus,aS4HwErrorStatus,
			amplifierStage1SumTrap,aS1InputLevelTrap,aS1ExceededPowerTrap,aS1DecreasedPowerTrap,aS1ReflectedPowerTrap,aS1TemperatureTrap,aS1HwErrorTrap,
			amplifierStage2SumTrap,aS2InputLevelTrap,aS2ExceededPowerTrap,aS2DecreasedPowerTrap,aS2ReflectedPowerTrap,aS2TemperatureTrap,aS2HwErrorTrap,
			amplifierStage3SumTrap,aS3InputLevelTrap,aS3ExceededPowerTrap,aS3DecreasedPowerTrap,aS3ReflectedPowerTrap,aS3TemperatureTrap,aS3HwErrorTrap,
			amplifierStage4SumTrap,aS4InputLevelTrap,aS4ExceededPowerTrap,aS4DecreasedPowerTrap,aS4ReflectedPowerTrap,aS4TemperatureTrap,aS4HwErrorTrap
 		"

  REVISION "201611110931Z"
	DESCRIPTION
		"writeCommunity wrong type, must be DisplayString
			softwareId wrong type, must be Gauge32,

		Added OIDs:
		efficiencyShoulderTarget,efficiencyMerMeasure,efficiencyMerTarget, efficiencyMerCalibration
		efficiencyShoulderMeasure, efficiencyShoulderCalibration
		"

  REVISION "201609271032Z"
	DESCRIPTION
		"Changed some OID types to Unsigned32 instead of Integer32
		New OIDs:
		ethernetMode
		ifaceGbe1, ifaceGbe2, ifaceGbe3, ifaceGbe4
		networkGbe1, networkGbe2, networkGbe3, networkGbe4
		muteErrorMip
		startNonLinearPrecorrection,linearStatusPrecorrection, startLinearPrecorrection
		partNumber, softwareId
		ctrlBoard,ctrlCBoard,ctrlMBoard,signalBoardGf,signalBoardTx,extraDigitalDacModulator,satelliteBoard,
		terrestialReceiver1Board,terrestialReceiver2Board,satelliteReceiver1Board,satelliteReceiver2Board,
		onePlusOneRedundancy,nPlusOneRedundancy,dualDriveRedundancy,amplifierHw
		gnssReceiverHw,externalReferenceHw
		snmpSw,dvbtSw,dvbt2Sw,isdbtSw,deecSw,isdbtRemuxSw,onePlusOneSw
		asi1Enable,asi2Enable
		modulatorPrbsType,modulatorPrbsPid,modulatorPrbsIn,
		amplifierOutputSampleTrap
		externalFeedback, relay1p1Interface, ctrlBusInterface
		r1p1StatusA, switchingCausesA, r1p1StatusB, switchingCausesB,
		r1p1SystemIp, r1p1DeviceIdentifier, r1p1SwitchToAntenna, r1p1PriorityAB, r1p1ControlBusStatus, r1p1AutoReturn

		Renamed OIDs:
		isdbtLatency to isdbtDelay
		dvbtLatency to dvbtDelay
		dvbt2Latency to dvbt2Delay
		startNonLinearPowerCalibration to startNonLinearPrecorrection
		cancelNonLinearPowerCalibration to cancelNonLinearPrecorrection
		nonLinearCalibration to nonLinearPrecorrection
		nonLinearStatusCalibration to nonLinearStatusPrecorrection
		modIn-bandLevelVariation to modInBandLevelVariation
		ecIn-bandLevelVariation to ecInBandLevelVariation
		in-bandSignalling to inBandSignalling
		efficiencyLevelMeasureCalibration to efficiencyLevelMeasureCalibrat
		r1p1Status to r1p1StatusNCB
		r1p1priority to r1p1priorityNCB
		r1p1SwitchingCauses to r1p1SwitchingCausesNCB

		Rearranged OIDs:

		Removed OIDs:
		portGbe1, portGbe2, portGbe3, portGbe4
		refExternalTable
		testbranch
		cancelPowerCalibration,cancelInputCalibration
		socket1MaximumBuffer,socket2MaximumBuffer,maximumLatency
		modClipping branch
		modNonLinearPrecorrectionAdaptative, modLinearPrecorrectionAdaptative
		dvbt1ppsActiveEdge,dvbt21ppsActiveEdge,isdbt1ppsActiveEdge,isdbtBtsRateLock,isdbtFftWindowing,isdbtFftWindowRate
		modMer,ecMode

		Modified:
		fan01Reset, fan02Reset, fan03Reset Sysntax to NullApply value

		"

  REVISION "201605180958Z"
	DESCRIPTION
		"New OIDs:
			nonSeamlessHysteresis, higherPriorityHysteresis,
			cancellerShouldersStatus, cancellerShouldersTrap
			modulatorShouldersTrap, modulatorShouldersStatus
			input10MhzStatus,input1ppsStatus,input10MhzTrap,input1ppsTrap
			powerSupplyTable
			acPowerSupplyStatus,psuAStatus,psuBStatus
			acPowerSupplyTrap,psuATrap,psuBTrap
			ecMode, ecEnable
			ecShoulderAlarm
			inputStatusCalibration, cancelInputCalibration, inputLevelMeasureCalibration, powerStatusCalibration, cancelPowerCalibration,	powerLevelMeasureCalibration,
			nonLinearStatusCalibration, cancelNonLinearPowerCalibration, efficiencyStatusCalibration, cancelEfficiencyCalibration, efficiencyLevelMeasureCalibration
			externalReferenceOutputs
			dvbtProcessingDelay
			r1p1InputTest
			r1p1SwitchingCauses
			powerDisplaOffset
			dvbt2TimingInformation (branch)
			dvbt2ProcessingDelay
			dvbtTimingInformation (branch)
			dvbtLatency dvbtCurrentNetworkDelay
			isdbtLatency
			inputLevelThreshold
			inputFrequencyMode
			inputCentralFrequency
	 	modMer
			modShoulderAlarm
			dvbt2NetworkIdOverwrite

		Relocated OIDs:
			ecGainMargin,
			ecLowerShoulder, ecUpperShoulder, ecIn-bandLevelVariation
			selected10Mhz, selected1Pps
			forwardPower, reversePower, exceededPowerThreshold, decreasedPowerThreshold, reverserPowerThreshold, amplifierStageTemperature, ldmosTransistor1Current,
			ldmosTransistor2Current, ldmosTransistor3Current, ldmosTransistor4Current
			dvbt2SuperFrameDuration
			dvbt2InputBufferDelay dvbt2NetworkDelayMargin dvbt2Latency
			modEfficiencyImprovement will be in service menu

		Deleted OIDs:
			externalReference status and traps
			serviceInputCalibration, servicePowerCalibration
			dvbt2TimeToTx
			mer
			dvbt2NetworkIdManual
			modPrecorrectorSelected

		Unified Traps:
				startOfVerificationTrap, endOfVerificationTrap and verificationTrap to redundancyTrap

				configurationFromBackupTrap, restoreFromBackupTrap,	errorConfigurationFromBackupTrap
				and errorRestoringFromBackupTrap to configurationFromBackupTrap

		Renamed OIDs:
			dvbt2IndividualAddresssingDelay to dvbt2TimeOffset
			elevatedPowerThreshold to exceededPowerThreshold
			reducedPowerThreshold to decreasedPowerThreshold
			dvbt2SystemIdManual to dvbt2SystemIdOverwrite
			dvbtUserDelay to dvbtLocalDelay
			isdbtUserDelay to isdbtLocalDelay
			isdbtDelayFromIip to isdbtTimeOffset
			elevatedOutputPower to exceededOutputPower
		"

	REVISION "201605121005Z"
	DESCRIPTION
		"Added portsConfiguration"

	REVISION "201604061801Z"
	DESCRIPTION
		"Contents of rfOutputTrap, externalAlarm1Trap, externalAlarm2Trap, external10Mhz corrected"

	REVISION "201603161214Z"
	DESCRIPTION
		"Added dvbt2SfnRelativeReference, dvbt2SfnAbsoluteReference, ntpClient, ntpServerStatus, input1pps"

	REVISION "201601151804Z"
	DESCRIPTION
		"Added redundancy system"

	REVISION "201510091047Z"
	DESCRIPTION
		"Initial Version"
::= { tredessProducts 2 }

RedundancyDeviceStatus ::= TEXTUAL-CONVENTION
	STATUS		current
	DESCRIPTION
		"Redundancy Status"
	SYNTAX  INTEGER {
		null (0),
		notReadyInitializing (1),
		loadNotReadyNotVerified (2),
		loadNotReadyVerifing (3),
		loadNotReadyLastVerificationNok (4),
		loadNotReadyLastVerification (5),
		loadTestingInput (6),
		loadReady (7),
		antennaNok (8),
		antennaOk (9),
		disabled (10),
		loadManual (11),
		antennaManual (12),
		unknownManual (13),
		commError (14),
		powerOff (15),
		commInitError (16),
		unknownAuto (17),
		swVersionError (18),
		loadNotReady (19),
		loadNotReadyMaxSwitchings (20),
		antennaNokMaxRestorations (21),
		antennaOkMaxRestorations (22),
		loadNotReadyMaxVerifications (23),
		maintenanceMode (24),
		dummyAntenna (25),
		priorityDisabled (26),
		loadReadyVerifing (27),
		loadNotReadyMaxRestorations (28)
	}

RedundancyRfSwitchStatus ::= TEXTUAL-CONVENTION
	STATUS		current
	DESCRIPTION
		"Relay Redundancy Status"
	SYNTAX  INTEGER {
		null (0),
		ok (1),
		errorNoPosition (2),
		errorBlocked (3)
	}

FloatingPoint ::= TEXTUAL-CONVENTION
    DISPLAY-HINT     "255a"
    STATUS     current
    DESCRIPTION
        "FloatingPoint provides a way of representing non-integer
        numbers in SNMP. Numbers are represented as a string of
        ASCII characters in the natural way. So for example, '3',
        '3.142' and '0.3142E1' are all valid numbers.
                
        The syntax for the string is as follows.  [] enclose an
        optional element, | is the separator for a set of
        alternatives.  () enclose syntax which is to be viewed
        as a unit.
                
        FloatingPoint ::= [Sign]  (Float1 | Float2 | DigitSequence) [ExponentPart]
                Float1        ::= DigitSequence '.' [DigitSequence]
                Float2        ::= '.' DigitSequence
                DigitSequence ::= Digit [DigitSequence]
                
                ExponentPart  ::= ('e' | 'E') [Sign] DigitSequence
                
                Digit         ::= '0'..'9'
                Sign          ::= '+' | '-'
        "
    SYNTAX  OCTET STRING (SIZE(1..63))

AlarmStatus ::= TEXTUAL-CONVENTION
	STATUS     current
	DESCRIPTION
		"Possible Alarm Status"
	SYNTAX  INTEGER {
		desactivedAlarm (0),
		activedAlarm (1),
		disabledAlarm (2),
		noApplyAlarm (3),
		uninitiatedAlarm (6)
	}

EventStatus ::= TEXTUAL-CONVENTION
	STATUS     current
	DESCRIPTION
		"Event status content "
	SYNTAX  INTEGER {
		unknown (0),
		noAlarm (1),
		alarmTriggered (2),
		notApplyAlarm (3),
		disabledAlarm (4),
		information (5)
	}


DisabledEnabled ::= TEXTUAL-CONVENTION
	STATUS		current
	DESCRIPTION
		"Disabled (0) / Enabled (1)"
	SYNTAX     INTEGER {
		disabled (0),
		enabled (1)
	}

NoYes ::= TEXTUAL-CONVENTION
	STATUS		current
	DESCRIPTION
		"No (0) / Yes (1)"
	SYNTAX     INTEGER {
		no (0),
		yes (1)
	}

SyncNotSync ::= TEXTUAL-CONVENTION
	STATUS		current
	DESCRIPTION
		"Getting value implies status. Commit only sync value"
	SYNTAX     INTEGER {
		notSync (0),
		sync (1)
	}

NullApply ::= TEXTUAL-CONVENTION
	STATUS		current
	DESCRIPTION
		"Null (nothing) (0) / Apply the request (1)"
	SYNTAX     INTEGER {
		null (0),
		apply (1)
	}

OptionHw ::= TEXTUAL-CONVENTION
	STATUS		current
	DESCRIPTION
		"Not Installed (0) / Installed (1) / Version Error (2) / Hardware Error (3)"
	SYNTAX     INTEGER {
		notInstalled (0),
		installed (1),
		versionError (2),
		hardwareError (3)
	}

OptionSw ::= TEXTUAL-CONVENTION
	STATUS		current
	DESCRIPTION
		"Not Installed (0) / Installed (1)"
	SYNTAX     INTEGER {
		notInstalled (0),
		installed (1)
	}

-- Trigger ::= TEXTUAL-CONVENTION
--	STATUS     current
--	DESCRIPTION
--		" "
--	SYNTAX  INTEGER {
--		iddle (1),
--		trigger (2)
--	}

OpenClose ::= TEXTUAL-CONVENTION
	STATUS		current
	DESCRIPTION
		"Open (0) / Close (1)"
	SYNTAX     INTEGER {
		open (0),
		close (1)
	}

IsdbtLayerConstellation ::= TEXTUAL-CONVENTION
	STATUS     current
	DESCRIPTION
		"ISDB-T Layer Constellation"
	SYNTAX     INTEGER {
		null(0),
		dqpsk(1),
		qam16(2),
		qam64(3),
		reserved4(4),
		reserved5(5),
		reserved6(6),
		reserved7(7)
	}

IsdbtLayerCodeRate ::= TEXTUAL-CONVENTION
	STATUS     current
	DESCRIPTION
		"ISDB-T Layer Code Rate"
	SYNTAX     INTEGER {
		null(0),
		codeRate1div2(1),
		codeRate2div3(2),
		codeRate3div4(3),
		codeRate5div6(4),
		codeRate7div8(5),
		reserved5(6),
		reserved6(7),
		reserved7(8)
	}

NokOk ::= TEXTUAL-CONVENTION
	STATUS		current
	DESCRIPTION
		"NOK (0) / OK (1)"
	SYNTAX     INTEGER {
		nok (0),
		ok (1)
	}

LinkStatusValue ::= TEXTUAL-CONVENTION
	STATUS		current
	DESCRIPTION
		"Link speed configuration"
	SYNTAX     INTEGER {
		eth10MFullDuplex (0),
		eth100MFullDuplex (1),
		eth1000MFullDuplex (2),
		ethDown (3),
		disabled (4),
		eth10MHalfDuplex (5),
		eth100MHalfDuplex (6),
		eth1000MHalfDuplex (7)
	}

LinkConfigurationValue ::= TEXTUAL-CONVENTION
	STATUS		current
	DESCRIPTION
		"Link speed configuration"
	SYNTAX     INTEGER {
		auto (0),
		eth10MFullDuplex (1),
		eth10MHalfDuplex (2),
		eth100MFullDuplex (3),
		eth100MHalfDuplex (4),
		eth1000MFullDuplex (5)
	}


DabOutputChannelType ::= TEXTUAL-CONVENTION
	STATUS		current
	DESCRIPTION
		"DAB Output Channel" 
	SYNTAX     INTEGER {
		ch5A (0),
		ch5B (1),
		ch5C (2),
		ch5D (3),
		ch6A (4),
		ch6B (5),
		ch6C (6),
		ch6D (7),
		ch7A (8),
		ch7B (9),
		ch7C (10),
		ch7D (11),
		ch8A (12),
		ch8B (13),
		ch8C (14),
		ch8D (15),
		ch9A (16),
		ch9B (17),
		ch9C (18),
		ch9D (19),
		ch10A (20),
		ch10B (21),
		ch10C (22),
		ch10D (23),
		ch11A (24),
		ch11B (25),
		ch11C (26),
		ch11D (27),
		ch12A (28),
		ch12B (29),
		ch12C (30),
		ch12D (31),
		ch13A (32),
		ch13B (33),
		ch13C (34),
		ch13D (35),
		ch13E (36),
		ch13F (37)
	}


televes              OBJECT IDENTIFIER ::= { enterprises 23180 }
televesGroup         OBJECT IDENTIFIER ::= { televes 2 }
tredess              OBJECT IDENTIFIER ::= { televesGroup 1 }
tredessProducts      OBJECT IDENTIFIER ::= { tredess 1 }
system               OBJECT IDENTIFIER ::= { fsTredessMIB 1 }
general              OBJECT IDENTIFIER ::= { system 1 }
dateTime             OBJECT IDENTIFIER ::= { general 10 }
networkInterfaces    OBJECT IDENTIFIER ::= { system 2 }
remoteInterfaz       OBJECT IDENTIFIER ::= { networkInterfaces 1 }
localInterfaz        OBJECT IDENTIFIER ::= { networkInterfaces 2 }
linkStatus           OBJECT IDENTIFIER ::= { networkInterfaces 3 }
--portsConfiguration   OBJECT IDENTIFIER ::= { networkInterfaces 4 }
linkConfiguration    OBJECT IDENTIFIER ::= { networkInterfaces 5 }
-- networkModeConfiguration   OBJECT IDENTIFIER ::= { portsConfiguration 2 }
-- ifaceModeConfiguration  	 OBJECT IDENTIFIER ::= { portsConfiguration 3 }
webInterface         OBJECT IDENTIFIER ::= { system 3 }

-- Modify autorefresh options

autorefreshWeb       OBJECT IDENTIFIER ::= { webInterface 1 }

-- Change actual user password

usersControl         OBJECT IDENTIFIER ::= { webInterface 2 }

-- Set default user passwords

setDefaultPasswords  OBJECT IDENTIFIER ::= { webInterface 3 }
eventConfiguration   OBJECT IDENTIFIER ::= { system 4 }
alarmsConfiguration  OBJECT IDENTIFIER ::= { eventConfiguration 1 }
eventsConfiguration  OBJECT IDENTIFIER ::= { eventConfiguration 2 }
ioInterface          OBJECT IDENTIFIER ::= { eventConfiguration 3 }
input01              OBJECT IDENTIFIER ::= { ioInterface 1 }
input02              OBJECT IDENTIFIER ::= { ioInterface 2 }
output01             OBJECT IDENTIFIER ::= { ioInterface 11 }
output02             OBJECT IDENTIFIER ::= { ioInterface 12 }
snmp                 OBJECT IDENTIFIER ::= { system 5 }
deviceInfo           OBJECT IDENTIFIER ::= { system 6 }
hardwareBasis      OBJECT IDENTIFIER ::= { deviceInfo 20 }
hardwareOptions      OBJECT IDENTIFIER ::= { deviceInfo 25 }
softwareOptions      OBJECT IDENTIFIER ::= { deviceInfo 30 }
service              OBJECT IDENTIFIER ::= { system 7 }
serviceReset         OBJECT IDENTIFIER ::= { service 1 }
serviceSystemCalibration  OBJECT IDENTIFIER ::= { service 5 }
inputCalibration     OBJECT IDENTIFIER ::= { serviceSystemCalibration 1 }
powerCalibration     OBJECT IDENTIFIER ::= { serviceSystemCalibration 5 }
phaseRf     		 OBJECT IDENTIFIER ::= { serviceSystemCalibration 7 }
linearPrecorrection      OBJECT IDENTIFIER ::= { serviceSystemCalibration 9 }
nonLinearPrecorrection      OBJECT IDENTIFIER ::= { serviceSystemCalibration 10 }
efficiencyCalibration     OBJECT IDENTIFIER ::= { serviceSystemCalibration 15 }
efficiencyImprovement	OBJECT IDENTIFIER ::= { efficiencyCalibration 20 }
serviceCooling       OBJECT IDENTIFIER ::= { service 10 }

-- Fan 01 values

fan01                OBJECT IDENTIFIER ::= { serviceCooling 1 }

-- Fan 01 values

fan02                OBJECT IDENTIFIER ::= { serviceCooling 2 }

-- Fan 01 values

fan03                OBJECT IDENTIFIER ::= { serviceCooling 3 }

-- Cooling for External Amplifier

externalAmplifierCooling                OBJECT IDENTIFIER ::= { serviceCooling 20 }

-- Rack Cooling
rackCooling                OBJECT IDENTIFIER ::= { serviceCooling 30 }

servicePowerSupply  OBJECT IDENTIFIER ::= { service 15 }
externalAmplifierPS  OBJECT IDENTIFIER ::= { servicePowerSupply 20 }
serviceSwUpgrade    OBJECT IDENTIFIER ::= { service 20 }
serviceInstallHwSw  OBJECT IDENTIFIER ::= { service 30 }
serviceRackCooling  OBJECT IDENTIFIER ::= { serviceInstallHwSw 32 }
serviceAsiMatrix  OBJECT IDENTIFIER ::= { serviceInstallHwSw 34 }
serviceRfMatrix  OBJECT IDENTIFIER ::= { serviceInstallHwSw 35 }
serviceEtiMatrix  OBJECT IDENTIFIER ::= { serviceInstallHwSw 36 }
psuA				OBJECT IDENTIFIER ::= { servicePowerSupply 10 }
psuB				OBJECT IDENTIFIER ::= { servicePowerSupply 11 }
setup                OBJECT IDENTIFIER ::= { fsTredessMIB 2 }
input                OBJECT IDENTIFIER ::= { setup 1 }
socket1              OBJECT IDENTIFIER ::= { input 1 }
socket1Statistics      OBJECT IDENTIFIER ::= { socket1 20 }
socket2              OBJECT IDENTIFIER ::= { input 2 }
socket2Statistics      OBJECT IDENTIFIER ::= { socket2 20 }
inputSwitching       OBJECT IDENTIFIER ::= { input 3 }
asi1                 OBJECT IDENTIFIER ::= { input 4 }
asi2                 OBJECT IDENTIFIER ::= { input 5 }
eti1                 OBJECT IDENTIFIER ::= { input 6 }
eti1Statistics         OBJECT IDENTIFIER ::= { eti1 20 }
eti2                 OBJECT IDENTIFIER ::= { input 7 }
eti2Statistics         OBJECT IDENTIFIER ::= { eti2 20 }

dttReceiver1         OBJECT IDENTIFIER ::= { input 10 }
dttReceiver1ChannelMode              OBJECT IDENTIFIER ::= { dttReceiver1 50 }
dttReceiver1CentralFrequencyMode     OBJECT IDENTIFIER ::= { dttReceiver1 55 }
dttReceiver1Status                   OBJECT IDENTIFIER ::= { dttReceiver1 60 }

dttReceiver1DvbT                     OBJECT IDENTIFIER ::= { dttReceiver1 65 }
dttReceiver1TModulation              OBJECT IDENTIFIER ::= { dttReceiver1DvbT 5 }
dttReceiver1TMeasures                OBJECT IDENTIFIER ::= { dttReceiver1DvbT 10 }

dttReceiver1DvbT2                    OBJECT IDENTIFIER ::= { dttReceiver1 70 }
dttReceiver1T2System                 OBJECT IDENTIFIER ::= { dttReceiver1DvbT2 5 }
dttReceiver1T2Frame                  OBJECT IDENTIFIER ::= { dttReceiver1DvbT2 15 }
dttReceiver1T2PLP                    OBJECT IDENTIFIER ::= { dttReceiver1DvbT2 20 }
dttReceiver1T2Measures               OBJECT IDENTIFIER ::= { dttReceiver1DvbT2 25 }

dttReceiver1Isdbt                    OBJECT IDENTIFIER ::= { dttReceiver1 75 }
dttReceiver1IsdbtSystem              OBJECT IDENTIFIER ::= { dttReceiver1Isdbt 5 }
dttReceiver1IsdbtLayerA              OBJECT IDENTIFIER ::= { dttReceiver1Isdbt 15 }
dttReceiver1IsdbtLayerB              OBJECT IDENTIFIER ::= { dttReceiver1Isdbt 20 }
dttReceiver1IsdbtLayerC              OBJECT IDENTIFIER ::= { dttReceiver1Isdbt 25 }

dttReceiver1CommonMeasures                    OBJECT IDENTIFIER ::= { dttReceiver1 80 }

dstReceiver1												OBJECT IDENTIFIER ::= { input 15 }
dstReceiver1Demodulator							OBJECT IDENTIFIER ::= { dstReceiver1 5 }
dstReceiver1DemFrequency						OBJECT IDENTIFIER ::= { dstReceiver1Demodulator 20 }
dstReceiver1DemModulation						OBJECT IDENTIFIER ::= { dstReceiver1Demodulator 25 }
dstReceiver1DemScrambling						OBJECT IDENTIFIER ::= { dstReceiver1Demodulator 30 }
dstReceiver1DemQuality							OBJECT IDENTIFIER ::= { dstReceiver1Demodulator 35 }

dstReceiver1Lnb											OBJECT IDENTIFIER ::= { dstReceiver1 10 }
dstReceiver1LnbSingleDualMode				OBJECT IDENTIFIER ::= { dstReceiver1Lnb 15 }
dstReceiver1LnbManualMode						OBJECT IDENTIFIER ::= { dstReceiver1Lnb 20 }

dstReceiver1Ts											OBJECT IDENTIFIER ::= { dstReceiver1 15 }
dstReceiver1TsAsiOutput							OBJECT IDENTIFIER ::= { dstReceiver1Ts 15 }
dstReceiver1TsBiss							OBJECT IDENTIFIER ::= { dstReceiver1Ts 17 }
dstReceiver1TsCam										OBJECT IDENTIFIER ::= { dstReceiver1Ts 20 }
dstReceiver1TsEtiOutput									OBJECT IDENTIFIER ::= { dstReceiver1Ts 30 }
dstR1TsEtiOutputStatistics									OBJECT IDENTIFIER ::= { dstReceiver1TsEtiOutput	25 }

---dttReceiver2         OBJECT IDENTIFIER ::= { input 15 }

-- inputSwitchingHystersis

inputSwitchingHysteresis	OBJECT IDENTIFIER ::= { inputSwitching 4 }

-- Input 1

input1               OBJECT IDENTIFIER ::= { inputSwitching 10 }

-- Input 2

input2               OBJECT IDENTIFIER ::= { inputSwitching 11 }

-- Input 3

input3               OBJECT IDENTIFIER ::= { inputSwitching 12 }

-- Input 4

input4               OBJECT IDENTIFIER ::= { inputSwitching 13 }
exciter              OBJECT IDENTIFIER ::= { setup 2 }
rfInput              OBJECT IDENTIFIER ::= { exciter 1 }
rfInputConfiguration  OBJECT IDENTIFIER ::= { rfInput 1 }
inputChannelMode     OBJECT IDENTIFIER ::= { rfInputConfiguration 10 }
inputCentralFrequencyMode     OBJECT IDENTIFIER ::= { rfInputConfiguration 15 }
echoCanceller        OBJECT IDENTIFIER ::= { exciter 5 }
ecGeneral            OBJECT IDENTIFIER ::= { echoCanceller 1 }
ecSystem             OBJECT IDENTIFIER ::= { echoCanceller 2 }
ecLevels             OBJECT IDENTIFIER ::= { ecSystem 10 }
ecWindows            OBJECT IDENTIFIER ::= { echoCanceller 3 }
ecWindowSpeed        OBJECT IDENTIFIER ::= { ecWindows 5 }
ecPrecorrector       OBJECT IDENTIFIER ::= { echoCanceller 10 }
ecPrecorrectorLevels  OBJECT IDENTIFIER ::= { ecPrecorrector 5 }
ecSpectrumMeasures   OBJECT IDENTIFIER ::= { ecPrecorrector 6 }
modulator            OBJECT IDENTIFIER ::= { exciter 10 }
modulatorGeneral     OBJECT IDENTIFIER ::= { modulator 1 }
modulatorGeneralPrbs     OBJECT IDENTIFIER ::= { modulatorGeneral 10 }
modulatorDVBT        OBJECT IDENTIFIER ::= { modulator 5 }
dvbtSystem           OBJECT IDENTIFIER ::= { modulatorDVBT 1 }
dvbtNetwork          OBJECT IDENTIFIER ::= { modulatorDVBT 2 }
dvbtMip                  OBJECT IDENTIFIER ::= { dvbtNetwork 20 }
dvbtTimingInformation OBJECT IDENTIFIER ::= { dvbtNetwork 25 }
dvbtModulation       OBJECT IDENTIFIER ::= { modulatorDVBT 3 }
modulatorDVBT2       OBJECT IDENTIFIER ::= { modulator 10 }
dvbt2System          OBJECT IDENTIFIER ::= { modulatorDVBT2 1 }
dvbt2CellId          OBJECT IDENTIFIER ::= { dvbt2System 6 }
dvbt2NetworkId       OBJECT IDENTIFIER ::= { dvbt2System 7 }
dvbt2SystemId        OBJECT IDENTIFIER ::= { dvbt2System 8 }
dvbt2Frequency       OBJECT IDENTIFIER ::= { dvbt2System 9 }
dvbt2Network         OBJECT IDENTIFIER ::= { modulatorDVBT2 2 }
dvbt2IndividualAddresssing  OBJECT IDENTIFIER ::= { dvbt2Network 20 }
dvbt2TimingInformation OBJECT IDENTIFIER ::= { dvbt2Network 25 }
dvbt2Frame           OBJECT IDENTIFIER ::= { modulatorDVBT2 3 }
dvbt2Plp             OBJECT IDENTIFIER ::= { modulatorDVBT2 4 }
modulatorISDBT       OBJECT IDENTIFIER ::= { modulator 15 }
isdbtSystem          OBJECT IDENTIFIER ::= { modulatorISDBT 1 }
isdbtConditionaAccessSystem          OBJECT IDENTIFIER ::= { isdbtSystem 10 }
isdbtBroadcastTransportStream          OBJECT IDENTIFIER ::= { isdbtSystem 15 }
isdbtPidList          OBJECT IDENTIFIER ::= { isdbtSystem 20 }
isdbtNetwork         OBJECT IDENTIFIER ::= { modulatorISDBT 2 }
iip                  OBJECT IDENTIFIER ::= { isdbtNetwork 4 }
isdbtTimingInformation  OBJECT IDENTIFIER ::= { isdbtNetwork 5 }
isdbtModulation      OBJECT IDENTIFIER ::= { modulatorISDBT 3 }
isdbtLayerA          OBJECT IDENTIFIER ::= { isdbtModulation 6 }
isdbtLayerB          OBJECT IDENTIFIER ::= { isdbtModulation 7 }
isdbtLayerC          OBJECT IDENTIFIER ::= { isdbtModulation 8 }
isdbtPSI             OBJECT IDENTIFIER ::= { modulatorISDBT 4 }
isdbtPAT             OBJECT IDENTIFIER ::= { isdbtPSI 5 }
isdbtBIT             OBJECT IDENTIFIER ::= { isdbtPSI 10 }
isdbtNIT             OBJECT IDENTIFIER ::= { isdbtPSI 15 }
isdbtTOT             OBJECT IDENTIFIER ::= { isdbtPSI 20 }
modulatorDAB         OBJECT IDENTIFIER ::= { modulator 17 }
dabSystem            OBJECT IDENTIFIER ::= { modulatorDAB 1 }
dabNetwork           OBJECT IDENTIFIER ::= { modulatorDAB 3 }
dabTiiCode           OBJECT IDENTIFIER ::= { dabNetwork 30 }
dabMnsc              OBJECT IDENTIFIER ::= { dabNetwork 35 }
dabTimeInformationGroup    OBJECT IDENTIFIER ::= { dabMnsc 1 }
dabTsc               OBJECT IDENTIFIER ::= { dabMnsc 5 }
dabTimmingInformation    OBJECT IDENTIFIER ::= { dabNetwork 45 }
dabStc            OBJECT IDENTIFIER ::= { modulatorDAB 6 }

modPrecorrector      OBJECT IDENTIFIER ::= { modulator 20 }
modLinearPrecorrection  OBJECT IDENTIFIER ::= { modPrecorrector 1 }
modNonLinearPrecorrection  OBJECT IDENTIFIER ::= { modPrecorrector 2 }
-- modClipping          OBJECT IDENTIFIER ::= { modPrecorrector 4 }
modPrecorrectorLevels  OBJECT IDENTIFIER ::= { modPrecorrector 5 }
modSpectrumMeasures  OBJECT IDENTIFIER ::= { modPrecorrector 6 }
rfOutput             OBJECT IDENTIFIER ::= { exciter 15 }
outputChannelMode    OBJECT IDENTIFIER ::= { rfOutput 10 }
outputCentralFrequencyMode  OBJECT IDENTIFIER ::= { rfOutput 15 }
mutes                OBJECT IDENTIFIER ::= { rfOutput 20 }
reference            OBJECT IDENTIFIER ::= { setup 3 }
referenceSource      OBJECT IDENTIFIER ::= { reference 1 }
synchronization      OBJECT IDENTIFIER ::= { reference 2 }
amplifier            OBJECT IDENTIFIER ::= { setup 4 }
automaticPowerCompensation            OBJECT IDENTIFIER ::= { amplifier 19 }
redundancy           OBJECT IDENTIFIER ::= { setup 5 }

-- 1+1 System

redundancy1p1        OBJECT IDENTIFIER ::= { redundancy 1 }

r1p1DeviceA         OBJECT IDENTIFIER ::= { redundancy1p1 25 }
r1p1DeviceB         OBJECT IDENTIFIER ::= { redundancy1p1 26 }

-- Redundancy 1+1: RF output status

r1p1RfStatus         OBJECT IDENTIFIER ::= { redundancy1p1 30 }

-- Redundancy 1+1: Automatic verifications

r1p1AutoVerifications  OBJECT IDENTIFIER ::= { redundancy1p1 35 }

-- Redundancy 1+1: automatic verification: reiterated with cadence

r1p1AutoVReiterated  OBJECT IDENTIFIER ::= { redundancy1p1 40 }

-- Redundancy 1+1: automatic verification daily

r1p1AutoVDaily       OBJECT IDENTIFIER ::= { redundancy1p1 50 }

-- Redundancy 1+1: automatic verification alarm

r1p1AutoVAlarm       OBJECT IDENTIFIER ::= { redundancy1p1 52 }

-- Redundancy 1+1: automatic priority inversion

r1p1AutoPriorityInversion OBJECT IDENTIFIER ::= { redundancy1p1 55 }

r1p1Synchronization       OBJECT IDENTIFIER ::= { redundancy1p1 70 }

-- Reundancy n+1

redundancyNp1        OBJECT IDENTIFIER ::= { redundancy 5 }

-- Reundancy n+1 B

redundancyNp1B        OBJECT IDENTIFIER ::= { redundancyNp1 5 }

redundancyNp1BConfiguration        OBJECT IDENTIFIER ::= { redundancyNp1B 5 }

rNp1RfControl         OBJECT IDENTIFIER ::= { redundancyNp1BConfiguration 57 }
rNp1DeviceAPriorites		OBJECT IDENTIFIER ::= { redundancyNp1BConfiguration 58 }
rNp1DeviceBStatus    OBJECT IDENTIFIER ::= { redundancyNp1BConfiguration 60 }
rNp1DeviceBConfiguration         OBJECT IDENTIFIER ::= { redundancyNp1BConfiguration 70 }
rNp1AutoVerifications            OBJECT IDENTIFIER ::= { redundancyNp1BConfiguration 80 }
rNp1AutoVReiterated              OBJECT IDENTIFIER ::= { redundancyNp1BConfiguration 85 }
rNp1AutoVDaily                   OBJECT IDENTIFIER ::= { redundancyNp1BConfiguration 90 }
rNp1AutomaticVerificationAlarm   OBJECT IDENTIFIER ::= { redundancyNp1BConfiguration 95 }

redundancyNp1BSynchronization        OBJECT IDENTIFIER ::= { redundancyNp1B 10 }

-- ASI Matrix
redundancyAsi                OBJECT IDENTIFIER ::= { redundancy 10 }

-- ETI Matrix
redundancyEti                OBJECT IDENTIFIER ::= { redundancy 12 }

-- status main branch

status               OBJECT IDENTIFIER ::= { fsTredessMIB 3 }
statusAmplifier      OBJECT IDENTIFIER ::= { status 3 }
statusAsiInput       OBJECT IDENTIFIER ::= { status 4 }
statusIpInput        OBJECT IDENTIFIER ::= { status 5 }
statusSatelliteReceiver1  OBJECT IDENTIFIER ::= { status 6 }
statusSatelliteReceiver2  OBJECT IDENTIFIER ::= { status 7 }
statusTerrestialReceiver1  OBJECT IDENTIFIER ::= { status 8 }
statusTerrestialReceiver2  OBJECT IDENTIFIER ::= { status 9 }
statusModulator      OBJECT IDENTIFIER ::= { status 10 }
statusRfInput        OBJECT IDENTIFIER ::= { status 11 }
statusEchoCanceller  OBJECT IDENTIFIER ::= { status 12 }
statusEtiInput       OBJECT IDENTIFIER ::= { status 14 }
statusRfOutput       OBJECT IDENTIFIER ::= { status 15 }

synchronizationModule  OBJECT IDENTIFIER ::= { status 17 }
rackCoolingBoards    OBJECT IDENTIFIER ::= { status 18 }
statusHwError        OBJECT IDENTIFIER ::= { status 19 }
statusFan            OBJECT IDENTIFIER ::= { status 20 }
statusExternal       OBJECT IDENTIFIER ::= { status 21 }
statusPowerSupply    OBJECT IDENTIFIER ::= { status 22 }
statusAmplifierStage1	OBJECT IDENTIFIER ::= { status 23 }
statusAmplifierStage2	OBJECT IDENTIFIER ::= { status 24 }
statusAmplifierStage3	OBJECT IDENTIFIER ::= { status 25 }
statusAmplifierStage4	OBJECT IDENTIFIER ::= { status 26 }
statusAmplifierStages	OBJECT IDENTIFIER ::= { status 27 }
-- statusSystem         OBJECT IDENTIFIER ::= { status 30 }
-- statusUnknown        OBJECT IDENTIFIER ::= { status 35 }
statusDcInput        OBJECT IDENTIFIER ::= { status 40 }
redundancySys        OBJECT IDENTIFIER ::= { status 45 }
eventTx              OBJECT IDENTIFIER ::= { fsTredessMIB 10 }
eventsTx             OBJECT IDENTIFIER ::= { eventTx 0 }
eventContent         OBJECT IDENTIFIER ::= { eventTx 1 }
-- testBranch           OBJECT IDENTIFIER ::= { fsTredessMIB 100 }
conformance          OBJECT IDENTIFIER ::= { fsTredessMIB 102 }
objectGroups         OBJECT IDENTIFIER ::= { conformance 1 }
groupCompilance      OBJECT IDENTIFIER ::= { conformance 2 }

language  OBJECT-TYPE
	SYNTAX     INTEGER {
		spanish (0),
		english (1),
		french (2)
	}
	MAX-ACCESS read-write
	STATUS     current
	DESCRIPTION
		"System language"
	::= { general 1 }

name  OBJECT-TYPE
	SYNTAX     DisplayString (SIZE(1..16))
	MAX-ACCESS read-write
	STATUS     current
	DESCRIPTION
		"System name"
	::= { general 2 }

temperature  OBJECT-TYPE
	SYNTAX     DisplayString (SIZE(1..16))
	MAX-ACCESS read-only
	STATUS     current
	DESCRIPTION
		"Control board temperature"
	::= { general 3 }

location  OBJECT-TYPE
	SYNTAX     DisplayString (SIZE(1..16))
	MAX-ACCESS read-write
	STATUS     current
	DESCRIPTION
		"System location"
	::= { general 4 }

operationMode OBJECT-TYPE
	SYNTAX     INTEGER {
	 	local (0),
		remote (1)
	}
	MAX-ACCESS read-only
	STATUS     current
	DESCRIPTION
		"Operation mode"
	::= { general 5 }

autoreturnToRemote  OBJECT-TYPE
	SYNTAX     INTEGER {
	 	auto30minutes (0),
		auto2minutes (2),
		auto12hours (6),
		autoDisabled (15)
	}
	MAX-ACCESS read-write
	STATUS     current
	DESCRIPTION
		"Auto return to remote mode"
	::= { general 6 }

dateTimeSource  OBJECT-TYPE
	SYNTAX     INTEGER {
		manual (0),
		ntp (1),
		gnss (2),
		input (3)
	}
	MAX-ACCESS read-only
	STATUS     current
	DESCRIPTION
		"Date and time selected source"
	::= { dateTime 1 }

dateTimeStatus  OBJECT-TYPE
	SYNTAX     INTEGER {
		desynchronized (0),
		synchronized (1)
	}
	MAX-ACCESS read-only
	STATUS     current
	DESCRIPTION
		"Date and Time status (synchronized/desynchronized)"
	::= { dateTime 2 }

dateTime1  OBJECT-TYPE
	SYNTAX     INTEGER {
		manual (0),
		ntp (1),
		gnss (2),
		input (3)
	}
	MAX-ACCESS read-write
	STATUS     current
	DESCRIPTION
		"Date and time source 1"
	::= { dateTime 3 }

dateTime2  OBJECT-TYPE
	SYNTAX     INTEGER {
		null (0),
		ntp (1),
		gnss (2),
		input (3)
	}
	MAX-ACCESS read-write
	STATUS     current
	DESCRIPTION
		"Date and time source 2"
	::= { dateTime 4 }

localTime  OBJECT-TYPE
	SYNTAX     DisplayString
	MAX-ACCESS read-write
	STATUS     current
	DESCRIPTION
		"System time"
	::= { dateTime 5 }

utcOffset  OBJECT-TYPE
	SYNTAX     Integer32 (-11..12)
	MAX-ACCESS read-write
	STATUS     current
	DESCRIPTION
		"Coordinated Universal Time offset"
	::= { dateTime 6 }

ntpServer  OBJECT-TYPE
	SYNTAX     DisplayString
	MAX-ACCESS read-write
	STATUS     current
	DESCRIPTION
		"Network Time Protocol Server"
	::= { dateTime 7 }

ntpRefresh  OBJECT-TYPE
	SYNTAX     Unsigned32 (1..180)
	MAX-ACCESS read-write
	STATUS     current
	DESCRIPTION
		"Network Time Protocol Refresh"
	::= { dateTime 8 }

ntpClient  OBJECT-TYPE
	SYNTAX     INTEGER {
		synchronized (0),
		syntaxisError (1),
		serverConnectionError (2),
		serverDroppedLeapNotInSync (3),
		serverDroppedLeapNotInSyncNoData (4),
		serverDroppedStrataTooHigh (5),
		serverDroppedStepTimeServer (6),
		notServerSuitableForSync (7),
		unknownError (8),
		notSynchronized (9),
		notConfigured (10),
		synchronizedAlternative (11)
	}
	MAX-ACCESS read-only
	STATUS     current
	DESCRIPTION
		"NTP client status"
	::= { dateTime 9 }

ntpServerStatus  OBJECT-TYPE
	SYNTAX     INTEGER {
		notRunning (0),
		running (1)
	}
	MAX-ACCESS read-only
	STATUS     current
	DESCRIPTION
		"NTP Server status [Local]"
	::= { dateTime 10 }

ntpServerAlternative  OBJECT-TYPE
	SYNTAX     DisplayString
	MAX-ACCESS read-write
	STATUS     current
	DESCRIPTION
		"Network Time Protocol Server [alternative]"
	::= { dateTime 11 }

timezone  OBJECT-TYPE
	SYNTAX     INTEGER {
		deshabilitado (0),
        pacificNiueNUT (4),
        pacificHonoluluUSHawaii (8),
        americaAnchorageUSAlask (12),
        americaLosAngelesUSPacific (16),
        americaTijuana (20),
        americaPhoenixUSArizona (24),
        americaDenverUSMountain (28),
        americaMazatlan (32),
        americaChicagoUSCentral (36),
        americaReginaCanadaSaskatchewan (40),
        americaMexicoCity (44),
        americaBogota (48),
        americaNewYorkUSEastern (52),
        americaCaracas (56),
        americaHalifaxCanadaAtlantic (60),
        americaSantiago (64),
        americaLaPaz (68),
        americaStJohnsCandaNewfoundland (72),
        americaSaoPauloBrazilEast (76),
        americaBuenosAires (80),
        americaMontevideo (84),
        atlanticSouthGeorgiaKingEdward (88),
        atlanticAzores (92),
        atlanticCapeVerdePraia (96),
        africaCasablanca (100),
		europeLisbonAtalancticCanaryFaro (102),
        europeLondon (104),
        europeAmsterdamBerlinRomeStockho (106),
        europeBelgradeBratislavaBudapest (107),
        europeBrusselsCopenhagenMadridPa (108),
        europeSarajevoSkopjeWarsawZagreb (109),
        africaKinshasa (112),
        europeAthensBucharestHelsinki (114),
        africaCairo (116),
        asiaJerusalem (120),
        africaJohannesburg (124),
        europeIstanbul (128),
        europeMoscow (132),
        africaNairobi (136),
        asiaBaghdad (140),
        asiaTehran (144),
        asiaMuscat (148),
        asiaBaku (152),
        asiaKabul (156),
        asiaKarachi (160),
        asiaKolkata (164),
        asiaKatmandu (168),
        asiaAlmaty (172),
        asiaDhaka (176),
        asiaRangoonAsiaNaypyidaw (180),
        asiaBangkok (184),
        asiaHongKong (188),
        asiaSingapore (192),
        australiaPerth (196),
        asiaTaipei (200),
        asiaTokyo (204),
        asiaSeoul (208),
        australiaAdelaide (212),
        australiaDarwin (216),
        australiaSydney (220),
        australiaBrisbane (224),
        pacificNoumea (228),
        pacificAuckland (232),
        pacificKwajalein (236),
        pacificApiaSamoa (240),
        pacificLineIslands (244)
	}
	MAX-ACCESS read-write
	STATUS     current
	DESCRIPTION
		"Timezone"
	::= { dateTime 15 }

dhcp  OBJECT-TYPE
	SYNTAX     DisabledEnabled
	MAX-ACCESS read-write
	STATUS     current
	DESCRIPTION
		"Enable/Disable DHCP"
	::= { remoteInterfaz 1 }

remoteIp  OBJECT-TYPE
	SYNTAX     IpAddress
	MAX-ACCESS read-write
	STATUS     current
	DESCRIPTION
		"Remote IP"
	::= { remoteInterfaz 2 }

remoteNetmask  OBJECT-TYPE
	SYNTAX     IpAddress
	MAX-ACCESS read-write
	STATUS     current
	DESCRIPTION
		"Remote netmask"
	::= { remoteInterfaz 3 }

remoteGateway  OBJECT-TYPE
	SYNTAX     IpAddress
	MAX-ACCESS read-write
	STATUS     current
	DESCRIPTION
		"Remote gateway"
	::= { remoteInterfaz 4 }

dnsServer  OBJECT-TYPE
	SYNTAX     IpAddress
	MAX-ACCESS read-write
	STATUS     current
	DESCRIPTION
		"Domain Name System server"
	::= { remoteInterfaz 5 }

macAddr  OBJECT-TYPE
	SYNTAX     MacAddress
	MAX-ACCESS read-only
	STATUS     current
	DESCRIPTION
		"MAC interfaz address"
	::= { remoteInterfaz 6 }

localIp  OBJECT-TYPE
	SYNTAX     IpAddress
	MAX-ACCESS read-write
	STATUS     current
	DESCRIPTION
		"Local IP"
	::= { localInterfaz 1 }

localNetmask  OBJECT-TYPE
	SYNTAX     IpAddress
	MAX-ACCESS read-write
	STATUS     current
	DESCRIPTION
		"Local netmask"
	::= { localInterfaz 2 }

localMacAddr  OBJECT-TYPE
	SYNTAX     MacAddress
	MAX-ACCESS read-only
	STATUS     current
	DESCRIPTION
		"Local MAC interfaz address"
	::= { localInterfaz 5 }

gbe1  OBJECT-TYPE
	SYNTAX     LinkStatusValue
	MAX-ACCESS read-only
	STATUS     current
	DESCRIPTION
		"GbE1 status"
	::= { linkStatus 1 }

gbe2  OBJECT-TYPE
	SYNTAX     LinkStatusValue
	MAX-ACCESS read-only
	STATUS     current
	DESCRIPTION
		"GbE2 status"
	::= { linkStatus 2 }

gbe3  OBJECT-TYPE
	SYNTAX     LinkStatusValue
	MAX-ACCESS read-only
	STATUS     current
	DESCRIPTION
		"GbE3 status"
	::= { linkStatus 3 }

gbe4  OBJECT-TYPE
	SYNTAX     LinkStatusValue
	MAX-ACCESS read-only
	STATUS     current
	DESCRIPTION
		"GbE4 status"
	::= { linkStatus 4 }

--ethernetMode  OBJECT-TYPE
--	SYNTAX     INTEGER {
--		networkMode (0),
--		interfaceMode (1)
--	}
--	MAX-ACCESS read-write
--	STATUS     current
--	DESCRIPTION
--		"Configuration for Ethernet ports"
--	::= { portsConfiguration 1 }
--
--networkGbe1  OBJECT-TYPE
--	SYNTAX     INTEGER {
--		networkA (0),
--		networkB (1),
--		networkC (2),
--		networkD (3),
--		disabled (4)
--	}
--	MAX-ACCESS read-write
--	STATUS     current
--	DESCRIPTION
--		"GbE1 port configuration mode network"
--	::= { networkModeConfiguration 1 }
--
--networkGbe2  OBJECT-TYPE
--	SYNTAX     INTEGER {
--		networkA (0),
--		networkB (1),
--		networkC (2),
--		networkD (3),
--		disabled (4)
--	}
--	MAX-ACCESS read-write
--	STATUS     current
--	DESCRIPTION
--		"GbE2 port configuration mode network"
--	::= { networkModeConfiguration 2 }
--
--networkGbe3  OBJECT-TYPE
--	SYNTAX     INTEGER {
--		networkA (0),
--		networkB (1),
--		networkC (2),
--		networkD (3),
--		disabled (4)
--	}
--	MAX-ACCESS read-write
--	STATUS     current
--	DESCRIPTION
--		"GbE3 port configuration mode network"
--	::= { networkModeConfiguration 3 }
--
--networkGbe4  OBJECT-TYPE
--	SYNTAX     INTEGER {
--		networkA (0),
--		networkB (1),
--		networkC (2),
--		networkD (3),
--		disabled (4)
--	}
--	MAX-ACCESS read-write
--	STATUS     current
--	DESCRIPTION
--		"GbE4 port configuration mode network"
--	::= { networkModeConfiguration 4 }

--ifaceGbe1  OBJECT-TYPE
--	SYNTAX     INTEGER {
--		ifaceRemote (0),
--		ifaceLocal (1),
--		ifaceSocket1 (2),
--		ifaceSocket2 (3),
--		ifaceSockets (4),
--		ifacedisabled (5)
--	}
--	MAX-ACCESS read-write
--	STATUS     current
--	DESCRIPTION
--		"GbE1 port configuration mode interface"
--	::= { ifaceModeConfiguration 1 }
--
--ifaceGbe2  OBJECT-TYPE
--	SYNTAX     INTEGER {
--		ifaceRemote (0),
--		ifaceLocal (1),
--		ifaceSocket1 (2),
--		ifaceSocket2 (3),
--		ifaceSockets (4),
--		ifacedisabled (5)
--	}
--	MAX-ACCESS read-write
--	STATUS     current
--	DESCRIPTION
--		"GbE2 port configuration mode interface"
--	::= { ifaceModeConfiguration 2 }
--
--ifaceGbe3  OBJECT-TYPE
--	SYNTAX     INTEGER {
--		ifaceRemote (0),
--		ifaceLocal (1),
--		ifaceSocket1 (2),
--		ifaceSocket2 (3),
--		ifaceSockets (4),
--		ifacedisabled (5)
--	}
--	MAX-ACCESS read-write
--	STATUS     current
--	DESCRIPTION
--		"GbE3 port configuration mode interface"
--	::= { ifaceModeConfiguration 3 }
--
--ifaceGbe4  OBJECT-TYPE
--	SYNTAX     INTEGER {
--		ifaceRemote (0),
--		ifaceLocal (1),
--		ifaceSocket1 (2),
--		ifaceSocket2 (3),
--		ifaceSockets (4),
--		ifacedisabled (5)
--	}
--	MAX-ACCESS read-write
--	STATUS     current
--	DESCRIPTION
--		"GbE4 port configuration mode interface"
--	::= { ifaceModeConfiguration 4 }

gbe1LinkConfiguration  OBJECT-TYPE
	SYNTAX     LinkConfigurationValue
	MAX-ACCESS read-write
	STATUS     current
	DESCRIPTION
		"GbE1 link configuration"
	::= { linkConfiguration 1 }

gbe2LinkConfiguration  OBJECT-TYPE
	SYNTAX     LinkConfigurationValue
	MAX-ACCESS read-write
	STATUS     current
	DESCRIPTION
		"GbE2 link configuration"
	::= { linkConfiguration 2 }

gbe3LinkConfiguration  OBJECT-TYPE
	SYNTAX     LinkConfigurationValue
	MAX-ACCESS read-write
	STATUS     current
	DESCRIPTION
		"GbE3 link configuration"
	::= { linkConfiguration 3 }

gbe4LinkConfiguration  OBJECT-TYPE
	SYNTAX     LinkConfigurationValue
	MAX-ACCESS read-write
	STATUS     current
	DESCRIPTION
		"GbE4 link configuration"
	::= { linkConfiguration 4 }

autorefreshWebConfig  OBJECT-TYPE
	SYNTAX     DisabledEnabled
	MAX-ACCESS read-write
	STATUS     current
	DESCRIPTION
		"Enable/Disable autorefresh web"
	::= { autorefreshWeb 1 }

autorefreshWebTime  OBJECT-TYPE
	SYNTAX     Unsigned32 (1..100)
	UNITS 	"seconds"
	MAX-ACCESS read-write
	STATUS     current
	DESCRIPTION
		"Time in seconds for auto-refresh web"
	::= { autorefreshWeb 2 }

connectedWebUsers OBJECT-TYPE
	SYNTAX     Unsigned32
	MAX-ACCESS read-only
	STATUS     current
	DESCRIPTION
		"Connected web users"
	::= { autorefreshWeb 10 }

user  OBJECT-TYPE
	SYNTAX     INTEGER {
		admin (0),
		public (1)
	}
	MAX-ACCESS read-write
	STATUS     current
	DESCRIPTION
		"User to change password"
	::= { usersControl 1 }

actualPassword  OBJECT-TYPE
	SYNTAX     DisplayString (SIZE(1..8))
	MAX-ACCESS read-write
	STATUS     current
	DESCRIPTION
		"It is necessary before change the user password,
		set this OID one time with the actual password"
	::= { usersControl 2 }

newPassword  OBJECT-TYPE
	SYNTAX     DisplayString (SIZE(1..8))
	MAX-ACCESS read-write
	STATUS     current
	DESCRIPTION
		"New password for selected user"
	::= { usersControl 3 }

confirmNewPassword  OBJECT-TYPE
	SYNTAX     DisplayString (SIZE(1..8))
	MAX-ACCESS read-write
	STATUS     current
	DESCRIPTION
		"Confirm the previous password"
	::= { usersControl 4 }

adminUserPassword  OBJECT-TYPE
	SYNTAX     INTEGER {
		null (0),
		reset (1)
	}
	MAX-ACCESS read-write
	STATUS     current
	DESCRIPTION
		"Set default password for user 'admin'"
	::= { setDefaultPasswords 1 }

publicUserPassword  OBJECT-TYPE
	SYNTAX     INTEGER {
		null (0),
		reset (1)
	}
	MAX-ACCESS read-write
	STATUS     current
	DESCRIPTION
		"Set default password for user 'public'"
	::= { setDefaultPasswords 2 }

geralTable  OBJECT-TYPE
	SYNTAX SEQUENCE OF GeralEntry
	MAX-ACCESS not-accessible
	STATUS     current
	DESCRIPTION
		"Geral alarms configuration"
	::= { alarmsConfiguration 1 }

geralEntry  OBJECT-TYPE
	SYNTAX 	GeralEntry
	MAX-ACCESS not-accessible
	STATUS     current
	DESCRIPTION
		"Geral Alarms configuration Entry "
	INDEX { geralIndex }
	::= { geralTable 1 }

GeralEntry ::= SEQUENCE {
	geralIndex
		Unsigned32,
	geralAlarmName
		DisplayString,
	geralAlarmStatus
		AlarmStatus,
	geralOn
		TruthValue,
	geralLog
		TruthValue,
	geralFault
		TruthValue,
	geralWarning
		TruthValue,
	geralLed
		TruthValue,
	geral1p1
		TruthValue,
	geralExt1
		TruthValue,
	geralExt2
		TruthValue,
	geralTrap
		TruthValue,
	geralDD
		TruthValue,
	geralTrapHysteresis
		Unsigned32
}

geralIndex  OBJECT-TYPE
	SYNTAX     Unsigned32 (1..2)
	MAX-ACCESS not-accessible
	STATUS     current
	DESCRIPTION
		"General Alarm Index"
	::= { geralEntry 1 }

geralAlarmName  OBJECT-TYPE
	SYNTAX     DisplayString
	MAX-ACCESS read-only
	STATUS     current
	DESCRIPTION
		"General Alarm Name"
	::= { geralEntry 2 }

geralAlarmStatus  OBJECT-TYPE
	SYNTAX     AlarmStatus
	MAX-ACCESS read-only
	STATUS     current
	DESCRIPTION
		"General Alarm Status"
	::= { geralEntry 3 }

geralOn  OBJECT-TYPE
	SYNTAX     TruthValue
	MAX-ACCESS read-write
	STATUS     current
	DESCRIPTION
		"On/Off alarm viwer.

		When you set off this amlarm, it will be on 3th status, so alarm will be on unknown status."
	::= { geralEntry 4 }

geralLog  OBJECT-TYPE
	SYNTAX     TruthValue
	MAX-ACCESS read-write
	STATUS     current
	DESCRIPTION
		"On/Off log this alarm"
	::= { geralEntry 5 }

geralFault  OBJECT-TYPE
	SYNTAX     TruthValue
	MAX-ACCESS read-write
	STATUS     current
	DESCRIPTION
		"Sum this alarm to Fault status "
	::= { geralEntry 6 }

geralWarning  OBJECT-TYPE
	SYNTAX     TruthValue
	MAX-ACCESS read-write
	STATUS     current
	DESCRIPTION
		"Sum this alarm to Warning status "
	::= { geralEntry 7 }

geralLed  OBJECT-TYPE
	SYNTAX     TruthValue
	MAX-ACCESS read-write
	STATUS     current
	DESCRIPTION
		"This alarm sum to LED status "
	::= { geralEntry 8 }

geral1p1  OBJECT-TYPE
	SYNTAX     TruthValue
	MAX-ACCESS read-write
	STATUS     current
	DESCRIPTION
		"This alarm implies changes in 1+1 system "
	::= { geralEntry 9 }

geralExt1  OBJECT-TYPE
	SYNTAX     TruthValue
	MAX-ACCESS read-write
	STATUS     current
	DESCRIPTION
		"This alarm modify external relay 1"
	::= { geralEntry 10 }

geralExt2  OBJECT-TYPE
	SYNTAX     TruthValue
	MAX-ACCESS read-write
	STATUS     current
	DESCRIPTION
		"This alarm modify external relay 2"
	::= { geralEntry 11 }

geralTrap  OBJECT-TYPE
	SYNTAX     TruthValue
	MAX-ACCESS read-write
	STATUS     current
	DESCRIPTION
		"This alarm generate SNMP trap "
	::= { geralEntry 12 }

geralDD  OBJECT-TYPE
	SYNTAX     TruthValue
	MAX-ACCESS read-write
	STATUS     current
	DESCRIPTION
		"This alarm is a switching cause"
	::= { geralEntry 13 }

geralTrapHysteresis  OBJECT-TYPE
	SYNTAX     Unsigned32(0..255)
	MAX-ACCESS read-write
	STATUS     current
	DESCRIPTION
		"Hysteresis trap"
	::= { geralEntry 14 }

amplifierTable  OBJECT-TYPE
	SYNTAX SEQUENCE OF AmplifierEntry
	MAX-ACCESS not-accessible
	STATUS     current
	DESCRIPTION
		"Amplifier alarms table "
	::= { alarmsConfiguration 5 }

amplifierEntry  OBJECT-TYPE
	SYNTAX 	AmplifierEntry
	MAX-ACCESS not-accessible
	STATUS     current
	DESCRIPTION
		"Amplifier alarms table entry "
	INDEX { amplifierIndex }
	::= { amplifierTable 1 }

AmplifierEntry ::= SEQUENCE {
	amplifierIndex
		Unsigned32,
	amplifierAlarmName
		DisplayString,
	amplifierAlarmStatus
		AlarmStatus,
	amplifierOn
		TruthValue,
	amplifierLog
		TruthValue,
	amplifierFault
		TruthValue,
	amplifierWarning
		TruthValue,
	amplifierLed
		TruthValue,
	amplifier1p1
		TruthValue,
	amplifierExt1
		TruthValue,
	amplifierExt2
		TruthValue,
	amplifierTrap
		TruthValue,
	amplifierDD
		TruthValue,
	amplifierTrapHysteresis
		Unsigned32
}

amplifierIndex  OBJECT-TYPE
	SYNTAX     Unsigned32 (1..5)
	MAX-ACCESS not-accessible
	STATUS     current
	DESCRIPTION
		"Amplifier Alarm Index"
	::= { amplifierEntry 1 }

amplifierAlarmName  OBJECT-TYPE
	SYNTAX     DisplayString
	MAX-ACCESS read-only
	STATUS     current
	DESCRIPTION
		"Amplifier Alarm Name"
	::= { amplifierEntry 2 }

amplifierAlarmStatus  OBJECT-TYPE
	SYNTAX     AlarmStatus
	MAX-ACCESS read-only
	STATUS     current
	DESCRIPTION
		"Amplifier"
	::= { amplifierEntry 3 }

amplifierOn  OBJECT-TYPE
	SYNTAX     TruthValue
	MAX-ACCESS read-write
	STATUS     current
	DESCRIPTION
		"On/Off alarm viwer.

		When you set off this amlarm, it will be on 3th status, so alarm will be on unknown status."
	::= { amplifierEntry 4 }

amplifierLog  OBJECT-TYPE
	SYNTAX     TruthValue
	MAX-ACCESS read-write
	STATUS     current
	DESCRIPTION
		"This alarm is logged "
	::= { amplifierEntry 5 }

amplifierFault  OBJECT-TYPE
	SYNTAX     TruthValue
	MAX-ACCESS read-write
	STATUS     current
	DESCRIPTION
		"This alarm sum to Fault alarm "
	::= { amplifierEntry 6 }

amplifierWarning  OBJECT-TYPE
	SYNTAX     TruthValue
	MAX-ACCESS read-write
	STATUS     current
	DESCRIPTION
		"This alarm sum to Faul alarm "
	::= { amplifierEntry 7 }

amplifierLed  OBJECT-TYPE
	SYNTAX     TruthValue
	MAX-ACCESS read-write
	STATUS     current
	DESCRIPTION
		"This alarm modify LED status "
	::= { amplifierEntry 8 }

amplifier1p1  OBJECT-TYPE
	SYNTAX     TruthValue
	MAX-ACCESS read-write
	STATUS     current
	DESCRIPTION
		"This alarm is a switching cause"
	::= { amplifierEntry 9 }

amplifierExt1  OBJECT-TYPE
	SYNTAX     TruthValue
	MAX-ACCESS read-write
	STATUS     current
	DESCRIPTION
		"This alarm sum to External relay 1 "
	::= { amplifierEntry 10 }

amplifierExt2  OBJECT-TYPE
	SYNTAX     TruthValue
	MAX-ACCESS read-write
	STATUS     current
	DESCRIPTION
		"This alarm sum to External delay 2 "
	::= { amplifierEntry 11 }

amplifierTrap  OBJECT-TYPE
	SYNTAX     TruthValue
	MAX-ACCESS read-write
	STATUS     current
	DESCRIPTION
		"This alarm generates SNMP trap "
	::= { amplifierEntry 12 }

amplifierDD  OBJECT-TYPE
	SYNTAX     TruthValue
	MAX-ACCESS read-write
	STATUS     current
	DESCRIPTION
		"This alarm is a switching cause"
	::= { amplifierEntry 13 }

amplifierTrapHysteresis  OBJECT-TYPE
	SYNTAX     Unsigned32(0..255)
	MAX-ACCESS read-write
	STATUS     current
	DESCRIPTION
		"Hysteresis trap"
	::= { amplifierEntry 14 }

amplifierStage1Table  OBJECT-TYPE
	SYNTAX SEQUENCE OF AmplifierStage1Entry
	MAX-ACCESS not-accessible
	STATUS     current
	DESCRIPTION
		"Amplifier Stage 1 alarms table "
	::= { alarmsConfiguration 6 }

amplifierStage1Entry  OBJECT-TYPE
	SYNTAX 	AmplifierStage1Entry
	MAX-ACCESS not-accessible
	STATUS     current
	DESCRIPTION
		"Amplifier alarms table entry "
	INDEX { amplifierStage1Index }
	::= { amplifierStage1Table 1 }

AmplifierStage1Entry ::= SEQUENCE {
	amplifierStage1Index
		Unsigned32,
	amplifierStage1AlarmName
		DisplayString,
	amplifierStage1AlarmStatus
		AlarmStatus,
	amplifierStage1On
		TruthValue,
	amplifierStage1Log
		TruthValue,
	amplifierStage1Fault
		TruthValue,
	amplifierStage1Warning
		TruthValue,
	amplifierStage1Led
		TruthValue,
	amplifierStage11p1
		TruthValue,
	amplifierStage1Ext1
		TruthValue,
	amplifierStage1Ext2
		TruthValue,
	amplifierStage1Trap
		TruthValue,
	amplifierStage1DD
		TruthValue,
	amplifierStage1TrapHysteresis
		Unsigned32
}

amplifierStage1Index  OBJECT-TYPE
	SYNTAX     Unsigned32 (1..5)
	MAX-ACCESS not-accessible
	STATUS     current
	DESCRIPTION
		"Amplifier Stage 1 Alarm Index"
	::= { amplifierStage1Entry 1 }

amplifierStage1AlarmName  OBJECT-TYPE
	SYNTAX     DisplayString
	MAX-ACCESS read-only
	STATUS     current
	DESCRIPTION
		"Amplifier Stage 1 Alarm Name"
	::= { amplifierStage1Entry 2 }

amplifierStage1AlarmStatus  OBJECT-TYPE
	SYNTAX     AlarmStatus
	MAX-ACCESS read-only
	STATUS     current
	DESCRIPTION
		"Amplifier stage 1"
	::= { amplifierStage1Entry 3 }

amplifierStage1On  OBJECT-TYPE
	SYNTAX     TruthValue
	MAX-ACCESS read-write
	STATUS     current
	DESCRIPTION
		"On/Off alarm viwer.

		When you set off this amlarm, it will be on 3th status, so alarm will be on unknown status."
	::= { amplifierStage1Entry 4 }

amplifierStage1Log  OBJECT-TYPE
	SYNTAX     TruthValue
	MAX-ACCESS read-write
	STATUS     current
	DESCRIPTION
		"This alarm is logged "
	::= { amplifierStage1Entry 5 }

amplifierStage1Fault  OBJECT-TYPE
	SYNTAX     TruthValue
	MAX-ACCESS read-write
	STATUS     current
	DESCRIPTION
		"This alarm sum to Fault alarm "
	::= { amplifierStage1Entry 6 }

amplifierStage1Warning  OBJECT-TYPE
	SYNTAX     TruthValue
	MAX-ACCESS read-write
	STATUS     current
	DESCRIPTION
		"This alarm sum to Faul alarm "
	::= { amplifierStage1Entry 7 }

amplifierStage1Led  OBJECT-TYPE
	SYNTAX     TruthValue
	MAX-ACCESS read-write
	STATUS     current
	DESCRIPTION
		"This alarm modify LED status "
	::= { amplifierStage1Entry 8 }

amplifierStage11p1  OBJECT-TYPE
	SYNTAX     TruthValue
	MAX-ACCESS read-write
	STATUS     current
	DESCRIPTION
		"This alarm is a switching cause"
	::= { amplifierStage1Entry 9 }

amplifierStage1Ext1  OBJECT-TYPE
	SYNTAX     TruthValue
	MAX-ACCESS read-write
	STATUS     current
	DESCRIPTION
		"This alarm sum to External relay 1 "
	::= { amplifierStage1Entry 10 }

amplifierStage1Ext2  OBJECT-TYPE
	SYNTAX     TruthValue
	MAX-ACCESS read-write
	STATUS     current
	DESCRIPTION
		"This alarm sum to External delay 2 "
	::= { amplifierStage1Entry 11 }

amplifierStage1Trap  OBJECT-TYPE
	SYNTAX     TruthValue
	MAX-ACCESS read-write
	STATUS     current
	DESCRIPTION
		"This alarm generates SNMP trap "
	::= { amplifierStage1Entry 12 }

amplifierStage1DD  OBJECT-TYPE
	SYNTAX     TruthValue
	MAX-ACCESS read-write
	STATUS     current
	DESCRIPTION
		"This alarm is a switching cause"
	::= { amplifierStage1Entry 13 }

amplifierStage1TrapHysteresis  OBJECT-TYPE
	SYNTAX     Unsigned32(0..255)
	MAX-ACCESS read-write
	STATUS     current
	DESCRIPTION
		"Hysteresis trap"
	::= { amplifierStage1Entry 14 }

amplifierStage2Table  OBJECT-TYPE
	SYNTAX SEQUENCE OF AmplifierStage2Entry
	MAX-ACCESS not-accessible
	STATUS     current
	DESCRIPTION
		"Amplifier Stage 2 alarms table "
	::= { alarmsConfiguration 7 }

amplifierStage2Entry  OBJECT-TYPE
	SYNTAX 	AmplifierStage2Entry
	MAX-ACCESS not-accessible
	STATUS     current
	DESCRIPTION
		"Amplifier alarms table entry "
	INDEX { amplifierStage2Index }
	::= { amplifierStage2Table 1 }

AmplifierStage2Entry ::= SEQUENCE {
	amplifierStage2Index
		Unsigned32,
	amplifierStage2AlarmName
		DisplayString,
	amplifierStage2AlarmStatus
		AlarmStatus,
	amplifierStage2On
		TruthValue,
	amplifierStage2Log
		TruthValue,
	amplifierStage2Fault
		TruthValue,
	amplifierStage2Warning
		TruthValue,
	amplifierStage2Led
		TruthValue,
	amplifierStage21p1
		TruthValue,
	amplifierStage2Ext1
		TruthValue,
	amplifierStage2Ext2
		TruthValue,
	amplifierStage2Trap
		TruthValue,
	amplifierStage2DD
		TruthValue,
	amplifierStage2TrapHysteresis
		Unsigned32
}

amplifierStage2Index  OBJECT-TYPE
	SYNTAX     Unsigned32 (1..5)
	MAX-ACCESS not-accessible
	STATUS     current
	DESCRIPTION
		"Amplifier Stage 2 Alarm Index"
	::= { amplifierStage2Entry 1 }

amplifierStage2AlarmName  OBJECT-TYPE
	SYNTAX     DisplayString
	MAX-ACCESS read-only
	STATUS     current
	DESCRIPTION
		"Amplifier Stage 2 Alarm Name"
	::= { amplifierStage2Entry 2 }

amplifierStage2AlarmStatus  OBJECT-TYPE
	SYNTAX     AlarmStatus
	MAX-ACCESS read-only
	STATUS     current
	DESCRIPTION
		"Amplifier stage 2"
	::= { amplifierStage2Entry 3 }

amplifierStage2On  OBJECT-TYPE
	SYNTAX     TruthValue
	MAX-ACCESS read-write
	STATUS     current
	DESCRIPTION
		"On/Off alarm viwer.

		When you set off this amlarm, it will be on 3th status, so alarm will be on unknown status."
	::= { amplifierStage2Entry 4 }

amplifierStage2Log  OBJECT-TYPE
	SYNTAX     TruthValue
	MAX-ACCESS read-write
	STATUS     current
	DESCRIPTION
		"This alarm is logged "
	::= { amplifierStage2Entry 5 }

amplifierStage2Fault  OBJECT-TYPE
	SYNTAX     TruthValue
	MAX-ACCESS read-write
	STATUS     current
	DESCRIPTION
		"This alarm sum to Fault alarm "
	::= { amplifierStage2Entry 6 }

amplifierStage2Warning  OBJECT-TYPE
	SYNTAX     TruthValue
	MAX-ACCESS read-write
	STATUS     current
	DESCRIPTION
		"This alarm sum to Faul alarm "
	::= { amplifierStage2Entry 7 }

amplifierStage2Led  OBJECT-TYPE
	SYNTAX     TruthValue
	MAX-ACCESS read-write
	STATUS     current
	DESCRIPTION
		"This alarm modify LED status "
	::= { amplifierStage2Entry 8 }

amplifierStage21p1  OBJECT-TYPE
	SYNTAX     TruthValue
	MAX-ACCESS read-write
	STATUS     current
	DESCRIPTION
		"This alarm is a switching cause"
	::= { amplifierStage2Entry 9 }

amplifierStage2Ext1  OBJECT-TYPE
	SYNTAX     TruthValue
	MAX-ACCESS read-write
	STATUS     current
	DESCRIPTION
		"This alarm sum to External relay 1 "
	::= { amplifierStage2Entry 10 }

amplifierStage2Ext2  OBJECT-TYPE
	SYNTAX     TruthValue
	MAX-ACCESS read-write
	STATUS     current
	DESCRIPTION
		"This alarm sum to External delay 2 "
	::= { amplifierStage2Entry 11 }

amplifierStage2Trap  OBJECT-TYPE
	SYNTAX     TruthValue
	MAX-ACCESS read-write
	STATUS     current
	DESCRIPTION
		"This alarm generates SNMP trap "
	::= { amplifierStage2Entry 12 }

amplifierStage2DD  OBJECT-TYPE
	SYNTAX     TruthValue
	MAX-ACCESS read-write
	STATUS     current
	DESCRIPTION
		"This alarm is a switching cause"
	::= { amplifierStage2Entry 13 }

amplifierStage2TrapHysteresis  OBJECT-TYPE
	SYNTAX     Unsigned32(0..255)
	MAX-ACCESS read-write
	STATUS     current
	DESCRIPTION
		"Hysteresis trap"
	::= { amplifierStage2Entry 14 }

amplifierStage3Table  OBJECT-TYPE
	SYNTAX SEQUENCE OF AmplifierStage3Entry
	MAX-ACCESS not-accessible
	STATUS     current
	DESCRIPTION
		"Amplifier Stage 3 alarms table "
	::= { alarmsConfiguration 8 }

amplifierStage3Entry  OBJECT-TYPE
	SYNTAX 	AmplifierStage3Entry
	MAX-ACCESS not-accessible
	STATUS     current
	DESCRIPTION
		"Amplifier alarms table entry "
	INDEX { amplifierStage3Index }
	::= { amplifierStage3Table 1 }

AmplifierStage3Entry ::= SEQUENCE {
	amplifierStage3Index
		Unsigned32,
	amplifierStage3AlarmName
		DisplayString,
	amplifierStage3AlarmStatus
		AlarmStatus,
	amplifierStage3On
		TruthValue,
	amplifierStage3Log
		TruthValue,
	amplifierStage3Fault
		TruthValue,
	amplifierStage3Warning
		TruthValue,
	amplifierStage3Led
		TruthValue,
	amplifierStage31p1
		TruthValue,
	amplifierStage3Ext1
		TruthValue,
	amplifierStage3Ext2
		TruthValue,
	amplifierStage3Trap
		TruthValue,
	amplifierStage3DD
		TruthValue,
	amplifierStage3TrapHysteresis
		Unsigned32
}

amplifierStage3Index  OBJECT-TYPE
	SYNTAX     Unsigned32 (1..5)
	MAX-ACCESS not-accessible
	STATUS     current
	DESCRIPTION
		"Amplifier Stage 3 Alarm Index"
	::= { amplifierStage3Entry 1 }

amplifierStage3AlarmName  OBJECT-TYPE
	SYNTAX     DisplayString
	MAX-ACCESS read-only
	STATUS     current
	DESCRIPTION
		"Amplifier Stage 3 Alarm Name"
	::= { amplifierStage3Entry 2 }

amplifierStage3AlarmStatus  OBJECT-TYPE
	SYNTAX     AlarmStatus
	MAX-ACCESS read-only
	STATUS     current
	DESCRIPTION
		"Amplifier stage 3"
	::= { amplifierStage3Entry 3 }

amplifierStage3On  OBJECT-TYPE
	SYNTAX     TruthValue
	MAX-ACCESS read-write
	STATUS     current
	DESCRIPTION
		"On/Off alarm viwer.

		When you set off this amlarm, it will be on 3th status, so alarm will be on unknown status."
	::= { amplifierStage3Entry 4 }

amplifierStage3Log  OBJECT-TYPE
	SYNTAX     TruthValue
	MAX-ACCESS read-write
	STATUS     current
	DESCRIPTION
		"This alarm is logged "
	::= { amplifierStage3Entry 5 }

amplifierStage3Fault  OBJECT-TYPE
	SYNTAX     TruthValue
	MAX-ACCESS read-write
	STATUS     current
	DESCRIPTION
		"This alarm sum to Fault alarm "
	::= { amplifierStage3Entry 6 }

amplifierStage3Warning  OBJECT-TYPE
	SYNTAX     TruthValue
	MAX-ACCESS read-write
	STATUS     current
	DESCRIPTION
		"This alarm sum to Faul alarm "
	::= { amplifierStage3Entry 7 }

amplifierStage3Led  OBJECT-TYPE
	SYNTAX     TruthValue
	MAX-ACCESS read-write
	STATUS     current
	DESCRIPTION
		"This alarm modify LED status "
	::= { amplifierStage3Entry 8 }

amplifierStage31p1  OBJECT-TYPE
	SYNTAX     TruthValue
	MAX-ACCESS read-write
	STATUS     current
	DESCRIPTION
		"This alarm is a switching cause"
	::= { amplifierStage3Entry 9 }

amplifierStage3Ext1  OBJECT-TYPE
	SYNTAX     TruthValue
	MAX-ACCESS read-write
	STATUS     current
	DESCRIPTION
		"This alarm sum to External relay 1 "
	::= { amplifierStage3Entry 10 }

amplifierStage3Ext2  OBJECT-TYPE
	SYNTAX     TruthValue
	MAX-ACCESS read-write
	STATUS     current
	DESCRIPTION
		"This alarm sum to External delay 2 "
	::= { amplifierStage3Entry 11 }

amplifierStage3Trap  OBJECT-TYPE
	SYNTAX     TruthValue
	MAX-ACCESS read-write
	STATUS     current
	DESCRIPTION
		"This alarm generates SNMP trap "
	::= { amplifierStage3Entry 12 }

amplifierStage3DD  OBJECT-TYPE
	SYNTAX     TruthValue
	MAX-ACCESS read-write
	STATUS     current
	DESCRIPTION
		"This alarm is a switching cause"
	::= { amplifierStage3Entry 13 }

amplifierStage3TrapHysteresis  OBJECT-TYPE
	SYNTAX     Unsigned32(0..255)
	MAX-ACCESS read-write
	STATUS     current
	DESCRIPTION
		"Hysteresis trap"
	::= { amplifierStage3Entry 14 }

amplifierStage4Table  OBJECT-TYPE
	SYNTAX SEQUENCE OF AmplifierStage4Entry
	MAX-ACCESS not-accessible
	STATUS     current
	DESCRIPTION
		"Amplifier Stage 4 alarms table "
	::= { alarmsConfiguration 9 }

amplifierStage4Entry  OBJECT-TYPE
	SYNTAX 	AmplifierStage4Entry
	MAX-ACCESS not-accessible
	STATUS     current
	DESCRIPTION
		"Amplifier alarms table entry "
	INDEX { amplifierStage4Index }
	::= { amplifierStage4Table 1 }

AmplifierStage4Entry ::= SEQUENCE {
	amplifierStage4Index
		Unsigned32,
	amplifierStage4AlarmName
		DisplayString,
	amplifierStage4AlarmStatus
		AlarmStatus,
	amplifierStage4On
		TruthValue,
	amplifierStage4Log
		TruthValue,
	amplifierStage4Fault
		TruthValue,
	amplifierStage4Warning
		TruthValue,
	amplifierStage4Led
		TruthValue,
	amplifierStage41p1
		TruthValue,
	amplifierStage4Ext1
		TruthValue,
	amplifierStage4Ext2
		TruthValue,
	amplifierStage4Trap
		TruthValue,
	amplifierStage4DD
		TruthValue,
	amplifierStage4TrapHysteresis
		Unsigned32
}

amplifierStage4Index  OBJECT-TYPE
	SYNTAX     Unsigned32 (1..5)
	MAX-ACCESS not-accessible
	STATUS     current
	DESCRIPTION
		"Amplifier Stage 4 Alarm Index"
	::= { amplifierStage4Entry 1 }

amplifierStage4AlarmName  OBJECT-TYPE
	SYNTAX     DisplayString
	MAX-ACCESS read-only
	STATUS     current
	DESCRIPTION
		"Amplifier Stage 4 Alarm Name"
	::= { amplifierStage4Entry 2 }

amplifierStage4AlarmStatus  OBJECT-TYPE
	SYNTAX     AlarmStatus
	MAX-ACCESS read-only
	STATUS     current
	DESCRIPTION
		"Amplifier stage 4"
	::= { amplifierStage4Entry 3 }

amplifierStage4On  OBJECT-TYPE
	SYNTAX     TruthValue
	MAX-ACCESS read-write
	STATUS     current
	DESCRIPTION
		"On/Off alarm viwer.

		When you set off this amlarm, it will be on 3th status, so alarm will be on unknown status."
	::= { amplifierStage4Entry 4 }

amplifierStage4Log  OBJECT-TYPE
	SYNTAX     TruthValue
	MAX-ACCESS read-write
	STATUS     current
	DESCRIPTION
		"This alarm is logged "
	::= { amplifierStage4Entry 5 }

amplifierStage4Fault  OBJECT-TYPE
	SYNTAX     TruthValue
	MAX-ACCESS read-write
	STATUS     current
	DESCRIPTION
		"This alarm sum to Fault alarm "
	::= { amplifierStage4Entry 6 }

amplifierStage4Warning  OBJECT-TYPE
	SYNTAX     TruthValue
	MAX-ACCESS read-write
	STATUS     current
	DESCRIPTION
		"This alarm sum to Faul alarm "
	::= { amplifierStage4Entry 7 }

amplifierStage4Led  OBJECT-TYPE
	SYNTAX     TruthValue
	MAX-ACCESS read-write
	STATUS     current
	DESCRIPTION
		"This alarm modify LED status "
	::= { amplifierStage4Entry 8 }

amplifierStage41p1  OBJECT-TYPE
	SYNTAX     TruthValue
	MAX-ACCESS read-write
	STATUS     current
	DESCRIPTION
		"This alarm is a switching cause"
	::= { amplifierStage4Entry 9 }

amplifierStage4Ext1  OBJECT-TYPE
	SYNTAX     TruthValue
	MAX-ACCESS read-write
	STATUS     current
	DESCRIPTION
		"This alarm sum to External relay 1 "
	::= { amplifierStage4Entry 10 }

amplifierStage4Ext2  OBJECT-TYPE
	SYNTAX     TruthValue
	MAX-ACCESS read-write
	STATUS     current
	DESCRIPTION
		"This alarm sum to External delay 2 "
	::= { amplifierStage4Entry 11 }

amplifierStage4Trap  OBJECT-TYPE
	SYNTAX     TruthValue
	MAX-ACCESS read-write
	STATUS     current
	DESCRIPTION
		"This alarm generates SNMP trap "
	::= { amplifierStage4Entry 12 }

amplifierStage4DD  OBJECT-TYPE
	SYNTAX     TruthValue
	MAX-ACCESS read-write
	STATUS     current
	DESCRIPTION
		"This alarm is a switching cause"
	::= { amplifierStage4Entry 13 }

amplifierStage4TrapHysteresis  OBJECT-TYPE
	SYNTAX     Unsigned32(0..255)
	MAX-ACCESS read-write
	STATUS     current
	DESCRIPTION
		"Hysteresis trap"
	::= { amplifierStage4Entry 14 }

-- amplifier > 5

amplifierStagesTable  OBJECT-TYPE
	SYNTAX SEQUENCE OF AmplifierStagesEntry
	MAX-ACCESS not-accessible
	STATUS     current
	DESCRIPTION
		"Amplifier Stages alarms table "
	::= { alarmsConfiguration 13 }

amplifierStagesEntry  OBJECT-TYPE
	SYNTAX 	AmplifierStagesEntry
	MAX-ACCESS not-accessible
	STATUS     current
	DESCRIPTION
		"Amplifier alarms table entry "
	INDEX { amplifierStagesIndex }
	::= { amplifierStagesTable 1 }

AmplifierStagesEntry ::= SEQUENCE {
	amplifierStagesIndex
		Unsigned32,
	amplifierStagesAlarmName
		DisplayString,
	amplifierStagesAlarmStatus
		AlarmStatus,
	amplifierStagesOn
		TruthValue,
	amplifierStagesLog
		TruthValue,
	amplifierStagesFault
		TruthValue,
	amplifierStagesWarning
		TruthValue,
	amplifierStagesLed
		TruthValue,
	amplifierStages1p1
		TruthValue,
	amplifierStagesExt1
		TruthValue,
	amplifierStagesExt2
		TruthValue,
	amplifierStagesTrap
		TruthValue,
	amplifierStagesDD
		TruthValue,
	amplifierStagesTrapHysteresis
		Unsigned32
}

amplifierStagesIndex  OBJECT-TYPE
	SYNTAX     Unsigned32 (1..5)
	MAX-ACCESS not-accessible
	STATUS     current
	DESCRIPTION
		"Amplifier Stages Alarm Index"
	::= { amplifierStagesEntry 1 }

amplifierStagesAlarmName  OBJECT-TYPE
	SYNTAX     DisplayString
	MAX-ACCESS read-only
	STATUS     current
	DESCRIPTION
		"Amplifier Stages Alarm Name"
	::= { amplifierStagesEntry 2 }

amplifierStagesAlarmStatus  OBJECT-TYPE
	SYNTAX     AlarmStatus
	MAX-ACCESS read-only
	STATUS     current
	DESCRIPTION
		"Amplifier stages"
	::= { amplifierStagesEntry 3 }

amplifierStagesOn  OBJECT-TYPE
	SYNTAX     TruthValue
	MAX-ACCESS read-write
	STATUS     current
	DESCRIPTION
		"On/Off alarm viwer.

		When you set off this amlarm, it will be on 3th status, so alarm will be on unknown status."
	::= { amplifierStagesEntry 4 }

amplifierStagesLog  OBJECT-TYPE
	SYNTAX     TruthValue
	MAX-ACCESS read-write
	STATUS     current
	DESCRIPTION
		"This alarm is logged "
	::= { amplifierStagesEntry 5 }

amplifierStagesFault  OBJECT-TYPE
	SYNTAX     TruthValue
	MAX-ACCESS read-write
	STATUS     current
	DESCRIPTION
		"This alarm sum to Fault alarm "
	::= { amplifierStagesEntry 6 }

amplifierStagesWarning  OBJECT-TYPE
	SYNTAX     TruthValue
	MAX-ACCESS read-write
	STATUS     current
	DESCRIPTION
		"This alarm sum to Faul alarm "
	::= { amplifierStagesEntry 7 }

amplifierStagesLed  OBJECT-TYPE
	SYNTAX     TruthValue
	MAX-ACCESS read-write
	STATUS     current
	DESCRIPTION
		"This alarm modify LED status "
	::= { amplifierStagesEntry 8 }

amplifierStages1p1  OBJECT-TYPE
	SYNTAX     TruthValue
	MAX-ACCESS read-write
	STATUS     current
	DESCRIPTION
		"This alarm is a switching cause"
	::= { amplifierStagesEntry 9 }

amplifierStagesExt1  OBJECT-TYPE
	SYNTAX     TruthValue
	MAX-ACCESS read-write
	STATUS     current
	DESCRIPTION
		"This alarm sum to External relay 1 "
	::= { amplifierStagesEntry 10 }

amplifierStagesExt2  OBJECT-TYPE
	SYNTAX     TruthValue
	MAX-ACCESS read-write
	STATUS     current
	DESCRIPTION
		"This alarm sum to External delay 2 "
	::= { amplifierStagesEntry 11 }

amplifierStagesTrap  OBJECT-TYPE
	SYNTAX     TruthValue
	MAX-ACCESS read-write
	STATUS     current
	DESCRIPTION
		"This alarm generates SNMP trap "
	::= { amplifierStagesEntry 12 }

amplifierStagesDD  OBJECT-TYPE
	SYNTAX     TruthValue
	MAX-ACCESS read-write
	STATUS     current
	DESCRIPTION
		"This alarm is a switching cause"
	::= { amplifierStagesEntry 13 }

amplifierStagesTrapHysteresis  OBJECT-TYPE
	SYNTAX     Unsigned32(0..255)
	MAX-ACCESS read-write
	STATUS     current
	DESCRIPTION
		"Hysteresis trap"
	::= { amplifierStagesEntry 14 }

asiTable  OBJECT-TYPE
	SYNTAX SEQUENCE OF AsiEntry
	MAX-ACCESS not-accessible
	STATUS     current
	DESCRIPTION
		"ASI alarms table "
	::= { alarmsConfiguration 10 }

asiEntry  OBJECT-TYPE
	SYNTAX 	AsiEntry
	MAX-ACCESS not-accessible
	STATUS     current
	DESCRIPTION
		"ASI alarms table entry "
	INDEX { asiIndex }
	::= { asiTable 1 }

AsiEntry ::= SEQUENCE {
	asiIndex
		Unsigned32,
	asiAlarmName
		DisplayString,
	asiAlarmStatus
		AlarmStatus,
	asiOn
		TruthValue,
	asiLog
		TruthValue,
	asiFault
		TruthValue,
	asiWarning
		TruthValue,
	asiLed
		TruthValue,
	asi1p1
		TruthValue,
	asiExt1
		TruthValue,
	asiExt2
		TruthValue,
	asiTrap
		TruthValue,
	asiDD
		TruthValue,
	asiTrapHysteresis
		Unsigned32
}

asiIndex  OBJECT-TYPE
	SYNTAX     Unsigned32 (1..3)
	MAX-ACCESS not-accessible
	STATUS     current
	DESCRIPTION
		"ASI Alarm Index"
	::= { asiEntry 1 }

asiAlarmName  OBJECT-TYPE
	SYNTAX     DisplayString
	MAX-ACCESS read-only
	STATUS     current
	DESCRIPTION
		"ASI Alarm Name"
	::= { asiEntry 2 }

asiAlarmStatus  OBJECT-TYPE
	SYNTAX     AlarmStatus
	MAX-ACCESS read-only
	STATUS     current
	DESCRIPTION
		"Amplifier"
	::= { asiEntry 3 }

asiOn  OBJECT-TYPE
	SYNTAX     TruthValue
	MAX-ACCESS read-write
	STATUS     current
	DESCRIPTION
		"On/Off alarm viwer.

		When you set off this amlarm, it will be on 3th status, so alarm will be on unknown status."
	::= { asiEntry 4 }

asiLog  OBJECT-TYPE
	SYNTAX     TruthValue
	MAX-ACCESS read-write
	STATUS     current
	DESCRIPTION
		"This alarm is logged "
	::= { asiEntry 5 }

asiFault  OBJECT-TYPE
	SYNTAX     TruthValue
	MAX-ACCESS read-write
	STATUS     current
	DESCRIPTION
		"This alarm sum to Fault alarm "
	::= { asiEntry 6 }

asiWarning  OBJECT-TYPE
	SYNTAX     TruthValue
	MAX-ACCESS read-write
	STATUS     current
	DESCRIPTION
		"This alarm sum to Warning alarm "
	::= { asiEntry 7 }

asiLed  OBJECT-TYPE
	SYNTAX     TruthValue
	MAX-ACCESS read-write
	STATUS     current
	DESCRIPTION
		"This alarm modify LED status "
	::= { asiEntry 8 }

asi1p1  OBJECT-TYPE
	SYNTAX     TruthValue
	MAX-ACCESS read-write
	STATUS     current
	DESCRIPTION
		"This alarm is a switching cause"
	::= { asiEntry 9 }

asiExt1  OBJECT-TYPE
	SYNTAX     TruthValue
	MAX-ACCESS read-write
	STATUS     current
	DESCRIPTION
		"This alarm sum to External relay 1 "
	::= { asiEntry 10 }

asiExt2  OBJECT-TYPE
	SYNTAX     TruthValue
	MAX-ACCESS read-write
	STATUS     current
	DESCRIPTION
		"This alarm sum to External delay 2 "
	::= { asiEntry 11 }

asiTrap  OBJECT-TYPE
	SYNTAX     TruthValue
	MAX-ACCESS read-write
	STATUS     current
	DESCRIPTION
		"This alarm generates SNMP trap "
	::= { asiEntry 12 }

asiDD  OBJECT-TYPE
	SYNTAX     TruthValue
	MAX-ACCESS read-write
	STATUS     current
	DESCRIPTION
		"This alarm is a switching cause"
	::= { asiEntry 13 }

asiTrapHysteresis  OBJECT-TYPE
	SYNTAX     Unsigned32(0..255)
	MAX-ACCESS read-write
	STATUS     current
	DESCRIPTION
		"Hysteresis trap"
	::= { asiEntry 14 }

etiTable  OBJECT-TYPE
	SYNTAX SEQUENCE OF EtiEntry
	MAX-ACCESS not-accessible
	STATUS     current
	DESCRIPTION
		"ETI alarms table "
	::= { alarmsConfiguration 11 }

etiEntry  OBJECT-TYPE
	SYNTAX 	EtiEntry
	MAX-ACCESS not-accessible
	STATUS     current
	DESCRIPTION
		"ETI alarms table entry "
	INDEX { etiIndex }
	::= { etiTable 1 }

EtiEntry ::= SEQUENCE {
	etiIndex
		Unsigned32,
	etiAlarmName
		DisplayString,
	etiAlarmStatus
		AlarmStatus,
	etiOn
		TruthValue,
	etiLog
		TruthValue,
	etiFault
		TruthValue,
	etiWarning
		TruthValue,
	etiLed
		TruthValue,
	eti1p1
		TruthValue,
	etiExt1
		TruthValue,
	etiExt2
		TruthValue,
	etiTrap
		TruthValue,
	etiDD
		TruthValue,
	etiTrapHysteresis
		Unsigned32
}

etiIndex  OBJECT-TYPE
	SYNTAX     Unsigned32 (1..3)
	MAX-ACCESS not-accessible
	STATUS     current
	DESCRIPTION
		"ETI Alarm Index"
	::= { etiEntry 1 }

etiAlarmName  OBJECT-TYPE
	SYNTAX     DisplayString
	MAX-ACCESS read-only
	STATUS     current
	DESCRIPTION
		"ETI Alarm Name"
	::= { etiEntry 2 }

etiAlarmStatus  OBJECT-TYPE
	SYNTAX     AlarmStatus
	MAX-ACCESS read-only
	STATUS     current
	DESCRIPTION
		"Status"
	::= { etiEntry 3 }

etiOn  OBJECT-TYPE
	SYNTAX     TruthValue
	MAX-ACCESS read-write
	STATUS     current
	DESCRIPTION
		"On/Off alarm viwer.

		When you set off this amlarm, it will be on 3th status, so alarm will be on unknown status."
	::= { etiEntry 4 }

etiLog  OBJECT-TYPE
	SYNTAX     TruthValue
	MAX-ACCESS read-write
	STATUS     current
	DESCRIPTION
		"This alarm is logged "
	::= { etiEntry 5 }

etiFault  OBJECT-TYPE
	SYNTAX     TruthValue
	MAX-ACCESS read-write
	STATUS     current
	DESCRIPTION
		"This alarm sum to Fault alarm "
	::= { etiEntry 6 }

etiWarning  OBJECT-TYPE
	SYNTAX     TruthValue
	MAX-ACCESS read-write
	STATUS     current
	DESCRIPTION
		"This alarm sum to Warning alarm "
	::= { etiEntry 7 }

etiLed  OBJECT-TYPE
	SYNTAX     TruthValue
	MAX-ACCESS read-write
	STATUS     current
	DESCRIPTION
		"This alarm modify LED status "
	::= { etiEntry 8 }

eti1p1  OBJECT-TYPE
	SYNTAX     TruthValue
	MAX-ACCESS read-write
	STATUS     current
	DESCRIPTION
		"This alarm is a switching cause"
	::= { etiEntry 9 }

etiExt1  OBJECT-TYPE
	SYNTAX     TruthValue
	MAX-ACCESS read-write
	STATUS     current
	DESCRIPTION
		"This alarm sum to External relay 1 "
	::= { etiEntry 10 }

etiExt2  OBJECT-TYPE
	SYNTAX     TruthValue
	MAX-ACCESS read-write
	STATUS     current
	DESCRIPTION
		"This alarm sum to External delay 2 "
	::= { etiEntry 11 }

etiTrap  OBJECT-TYPE
	SYNTAX     TruthValue
	MAX-ACCESS read-write
	STATUS     current
	DESCRIPTION
		"This alarm generates SNMP trap "
	::= { etiEntry 12 }

etiDD  OBJECT-TYPE
	SYNTAX     TruthValue
	MAX-ACCESS read-write
	STATUS     current
	DESCRIPTION
		"This alarm is a switching cause"
	::= { etiEntry 13 }

etiTrapHysteresis  OBJECT-TYPE
	SYNTAX     Unsigned32(0..255)
	MAX-ACCESS read-write
	STATUS     current
	DESCRIPTION
		"Hysteresis trap"
	::= { etiEntry 14 }

ipInputTable  OBJECT-TYPE
	SYNTAX SEQUENCE OF IpInputEntry
	MAX-ACCESS not-accessible
	STATUS     current
	DESCRIPTION
		"IP Input alarm table "
	::= { alarmsConfiguration 15 }

ipInputEntry  OBJECT-TYPE
	SYNTAX 	IpInputEntry
	MAX-ACCESS not-accessible
	STATUS     current
	DESCRIPTION
		"IP Input alarm table entry "
	INDEX { ipInputIndex }
	::= { ipInputTable 1 }

IpInputEntry ::= SEQUENCE {
	ipInputIndex
		Unsigned32,
	ipInputAlarmName
		DisplayString,
	ipInputAlarmStatus
		AlarmStatus,
	ipInputOn
		TruthValue,
	ipInputLog
		TruthValue,
	ipInputFault
		TruthValue,
	ipInputWarning
		TruthValue,
	ipInputLed
		TruthValue,
	ipInput1p1
		TruthValue,
	ipInputExt1
		TruthValue,
	ipInputExt2
		TruthValue,
	ipInputTrap
		TruthValue,
	ipInputDD
		TruthValue,
	ipInputTrapHysteresis
		Unsigned32
}

ipInputIndex  OBJECT-TYPE
	SYNTAX     Unsigned32 (1..3)
	MAX-ACCESS not-accessible
	STATUS     current
	DESCRIPTION
		"IP Input Alarm Index"
	::= { ipInputEntry 1 }

ipInputAlarmName  OBJECT-TYPE
	SYNTAX     DisplayString
	MAX-ACCESS read-only
	STATUS     current
	DESCRIPTION
		"IP Input Alarm Name"
	::= { ipInputEntry 2 }

ipInputAlarmStatus  OBJECT-TYPE
	SYNTAX     AlarmStatus
	MAX-ACCESS read-only
	STATUS     current
	DESCRIPTION
		"Amplifier"
	::= { ipInputEntry 3 }

ipInputOn  OBJECT-TYPE
	SYNTAX     TruthValue
	MAX-ACCESS read-write
	STATUS     current
	DESCRIPTION
		"On/Off alarm viwer.

		When you set off this amlarm, it will be on 3th status, so alarm will be on unknown status."
	::= { ipInputEntry 4 }

ipInputLog  OBJECT-TYPE
	SYNTAX     TruthValue
	MAX-ACCESS read-write
	STATUS     current
	DESCRIPTION
		"This alarm is logged "
	::= { ipInputEntry 5 }

ipInputFault  OBJECT-TYPE
	SYNTAX     TruthValue
	MAX-ACCESS read-write
	STATUS     current
	DESCRIPTION
		"This alarm sum to Fault alarm "
	::= { ipInputEntry 6 }

ipInputWarning  OBJECT-TYPE
	SYNTAX     TruthValue
	MAX-ACCESS read-write
	STATUS     current
	DESCRIPTION
		"This alarm sum to Warning alarm "
	::= { ipInputEntry 7 }

ipInputLed  OBJECT-TYPE
	SYNTAX     TruthValue
	MAX-ACCESS read-write
	STATUS     current
	DESCRIPTION
		"This alarm modify LED status "
	::= { ipInputEntry 8 }

ipInput1p1  OBJECT-TYPE
	SYNTAX     TruthValue
	MAX-ACCESS read-write
	STATUS     current
	DESCRIPTION
		"This alarm is a switching cause"
	::= { ipInputEntry 9 }

ipInputExt1  OBJECT-TYPE
	SYNTAX     TruthValue
	MAX-ACCESS read-write
	STATUS     current
	DESCRIPTION
		"This alarm sum to External relay 1 "
	::= { ipInputEntry 10 }

ipInputExt2  OBJECT-TYPE
	SYNTAX     TruthValue
	MAX-ACCESS read-write
	STATUS     current
	DESCRIPTION
		"This alarm sum to External delay 2 "
	::= { ipInputEntry 11 }

ipInputTrap  OBJECT-TYPE
	SYNTAX     TruthValue
	MAX-ACCESS read-write
	STATUS     current
	DESCRIPTION
		"This alarm generates SNMP trap "
	::= { ipInputEntry 12 }

ipInputDD  OBJECT-TYPE
	SYNTAX     TruthValue
	MAX-ACCESS read-write
	STATUS     current
	DESCRIPTION
		"This alarm is a switching cause"
	::= { ipInputEntry 13 }

ipInputTrapHysteresis  OBJECT-TYPE
	SYNTAX     Unsigned32(0..255)
	MAX-ACCESS read-write
	STATUS     current
	DESCRIPTION
		"Hysteresis trap"
	::= { ipInputEntry 14 }

rxSat1Table  OBJECT-TYPE
	SYNTAX SEQUENCE OF RxSat1Entry
	MAX-ACCESS not-accessible
	STATUS     current
	DESCRIPTION
		"RX Satellite 1 alarm table "
	::= { alarmsConfiguration 20 }

rxSat1Entry  OBJECT-TYPE
	SYNTAX 	RxSat1Entry
	MAX-ACCESS not-accessible
	STATUS     current
	DESCRIPTION
		"RX Satellite 1 alarm table entry "
	INDEX { rxSat1Index }
	::= { rxSat1Table 1 }

RxSat1Entry ::= SEQUENCE {
	rxSat1Index
		Unsigned32,
	rxSat1AlarmName
		DisplayString,
	rxSat1AlarmStatus
		AlarmStatus,
	rxSat1InputOn
		TruthValue,
	rxSat1Log
		TruthValue,
	rxSat1Fault
		TruthValue,
	rxSat1Warning
		TruthValue,
	rxSat1Led
		TruthValue,
	rxSat11p1
		TruthValue,
	rxSat1Ext1
		TruthValue,
	rxSat1Ext2
		TruthValue,
	rxSat1Trap
		TruthValue,
	rxSat1DD
		TruthValue,
	rxSat1TrapHysteresis
		Unsigned32
}

rxSat1Index  OBJECT-TYPE
	SYNTAX     Unsigned32 (1..5)
	MAX-ACCESS not-accessible
	STATUS     current
	DESCRIPTION
		"Satillite receiver 1 Alarm Index"
	::= { rxSat1Entry 1 }

rxSat1AlarmName  OBJECT-TYPE
	SYNTAX     DisplayString
	MAX-ACCESS read-only
	STATUS     current
	DESCRIPTION
		"Satellite receiver 1 Alarm Name"
	::= { rxSat1Entry 2 }

rxSat1AlarmStatus  OBJECT-TYPE
	SYNTAX     AlarmStatus
	MAX-ACCESS read-only
	STATUS     current
	DESCRIPTION
		"Amplifier"
	::= { rxSat1Entry 3 }

rxSat1InputOn  OBJECT-TYPE
	SYNTAX     TruthValue
	MAX-ACCESS read-write
	STATUS     current
	DESCRIPTION
		"On/Off alarm viwer.

		When you set off this amlarm, it will be on 3th status, so alarm will be on unknown status."
	::= { rxSat1Entry 4 }

rxSat1Log  OBJECT-TYPE
	SYNTAX     TruthValue
	MAX-ACCESS read-write
	STATUS     current
	DESCRIPTION
		"This alarm is logged "
	::= { rxSat1Entry 5 }

rxSat1Fault  OBJECT-TYPE
	SYNTAX     TruthValue
	MAX-ACCESS read-write
	STATUS     current
	DESCRIPTION
		"This alarm sum to Fault alarm "
	::= { rxSat1Entry 6 }

rxSat1Warning  OBJECT-TYPE
	SYNTAX     TruthValue
	MAX-ACCESS read-write
	STATUS     current
	DESCRIPTION
		"This alarm sum to Warning alarm "
	::= { rxSat1Entry 7 }

rxSat1Led  OBJECT-TYPE
	SYNTAX     TruthValue
	MAX-ACCESS read-write
	STATUS     current
	DESCRIPTION
		"This alarm modify LED status "
	::= { rxSat1Entry 8 }

rxSat11p1  OBJECT-TYPE
	SYNTAX     TruthValue
	MAX-ACCESS read-write
	STATUS     current
	DESCRIPTION
		"This alarm is a switching cause"
	::= { rxSat1Entry 9 }

rxSat1Ext1  OBJECT-TYPE
	SYNTAX     TruthValue
	MAX-ACCESS read-write
	STATUS     current
	DESCRIPTION
		"This alarm sum to External relay 1 "
	::= { rxSat1Entry 10 }

rxSat1Ext2  OBJECT-TYPE
	SYNTAX     TruthValue
	MAX-ACCESS read-write
	STATUS     current
	DESCRIPTION
		"This alarm sum to External delay 2 "
	::= { rxSat1Entry 11 }

rxSat1Trap  OBJECT-TYPE
	SYNTAX     TruthValue
	MAX-ACCESS read-write
	STATUS     current
	DESCRIPTION
		"This alarm generates SNMP trap "
	::= { rxSat1Entry 12 }

rxSat1DD  OBJECT-TYPE
	SYNTAX     TruthValue
	MAX-ACCESS read-write
	STATUS     current
	DESCRIPTION
		"This alarm is a switching cause"
	::= { rxSat1Entry 13 }

rxSat1TrapHysteresis  OBJECT-TYPE
	SYNTAX     Unsigned32(0..255)
	MAX-ACCESS read-write
	STATUS     current
	DESCRIPTION
		"Hysteresis trap"
	::= { rxSat1Entry 14 }

rxSat2Table  OBJECT-TYPE
	SYNTAX SEQUENCE OF RxSat2Entry
	MAX-ACCESS not-accessible
	STATUS     current
	DESCRIPTION
		"RX Satellite 2 alarm table "
	::= { alarmsConfiguration 21 }

rxSat2Entry  OBJECT-TYPE
	SYNTAX 	RxSat2Entry
	MAX-ACCESS not-accessible
	STATUS     current
	DESCRIPTION
		"RX Satellite 2 alarm table entry"
	INDEX { rxSat2Index }
	::= { rxSat2Table 1 }

RxSat2Entry ::= SEQUENCE {
	rxSat2Index
		Unsigned32,
	rxSat2AlarmName
		DisplayString,
	rxSat2AlarmStatus
		AlarmStatus,
	rxSat2InputOn
		TruthValue,
	rxSat2Log
		TruthValue,
	rxSat2Fault
		TruthValue,
	rxSat2Warning
		TruthValue,
	rxSat2Led
		TruthValue,
	rxSat21p1
		TruthValue,
	rxSat2Ext1
		TruthValue,
	rxSat2Ext2
		TruthValue,
	rxSat2Trap
		TruthValue,
	rxSat2DD
		TruthValue,
	rxSat2TrapHysteresis
		Unsigned32
}

rxSat2Index  OBJECT-TYPE
	SYNTAX     Unsigned32 (1..5)
	MAX-ACCESS not-accessible
	STATUS     current
	DESCRIPTION
		"Satillite receiver 2 Alarm Index"
	::= { rxSat2Entry 1 }

rxSat2AlarmName  OBJECT-TYPE
	SYNTAX     DisplayString
	MAX-ACCESS read-only
	STATUS     current
	DESCRIPTION
		"Satellite receiver 2 Alarm Name"
	::= { rxSat2Entry 2 }

rxSat2AlarmStatus  OBJECT-TYPE
	SYNTAX     AlarmStatus
	MAX-ACCESS read-only
	STATUS     current
	DESCRIPTION
		"Amplifier"
	::= { rxSat2Entry 3 }

rxSat2InputOn  OBJECT-TYPE
	SYNTAX     TruthValue
	MAX-ACCESS read-write
	STATUS     current
	DESCRIPTION
		"On/Off alarm viwer.

		When you set off this amlarm, it will be on 3th status, so alarm will be on unknown status."
	::= { rxSat2Entry 4 }

rxSat2Log  OBJECT-TYPE
	SYNTAX     TruthValue
	MAX-ACCESS read-write
	STATUS     current
	DESCRIPTION
		"This alarm is logged "
	::= { rxSat2Entry 5 }

rxSat2Fault  OBJECT-TYPE
	SYNTAX     TruthValue
	MAX-ACCESS read-write
	STATUS     current
	DESCRIPTION
		"This alarm sum to Fault alarm "
	::= { rxSat2Entry 6 }

rxSat2Warning  OBJECT-TYPE
	SYNTAX     TruthValue
	MAX-ACCESS read-write
	STATUS     current
	DESCRIPTION
		"This alarm sum to Warning alarm "
	::= { rxSat2Entry 7 }

rxSat2Led  OBJECT-TYPE
	SYNTAX     TruthValue
	MAX-ACCESS read-write
	STATUS     current
	DESCRIPTION
		"This alarm modify LED status "
	::= { rxSat2Entry 8 }

rxSat21p1  OBJECT-TYPE
	SYNTAX     TruthValue
	MAX-ACCESS read-write
	STATUS     current
	DESCRIPTION
		"This alarm is a switching cause"
	::= { rxSat2Entry 9 }

rxSat2Ext1  OBJECT-TYPE
	SYNTAX     TruthValue
	MAX-ACCESS read-write
	STATUS     current
	DESCRIPTION
		"This alarm sum to External relay 1 "
	::= { rxSat2Entry 10 }

rxSat2Ext2  OBJECT-TYPE
	SYNTAX     TruthValue
	MAX-ACCESS read-write
	STATUS     current
	DESCRIPTION
		"This alarm sum to External delay 2 "
	::= { rxSat2Entry 11 }

rxSat2Trap  OBJECT-TYPE
	SYNTAX     TruthValue
	MAX-ACCESS read-write
	STATUS     current
	DESCRIPTION
		"This alarm generates SNMP trap "
	::= { rxSat2Entry 12 }

rxSat2DD  OBJECT-TYPE
	SYNTAX     TruthValue
	MAX-ACCESS read-write
	STATUS     current
	DESCRIPTION
		"This alarm is a switching cause"
	::= { rxSat2Entry 13 }

rxSat2TrapHysteresis  OBJECT-TYPE
	SYNTAX     Unsigned32(0..255)
	MAX-ACCESS read-write
	STATUS     current
	DESCRIPTION
		"Hysteresis trap"
	::= { rxSat2Entry 14 }

rxDtt1Table  OBJECT-TYPE
	SYNTAX SEQUENCE OF RxDtt1Entry
	MAX-ACCESS not-accessible
	STATUS     current
	DESCRIPTION
		"RX Terrestrial 1 alarm table "
	::= { alarmsConfiguration 25 }

rxDtt1Entry  OBJECT-TYPE
	SYNTAX 	RxDtt1Entry
	MAX-ACCESS not-accessible
	STATUS     current
	DESCRIPTION
		"RX Terrestrial 1 alarm table entry"
	INDEX { rxDtt1Index }
	::= { rxDtt1Table 1 }

RxDtt1Entry ::= SEQUENCE {
	rxDtt1Index
		Unsigned32,
	rxDtt1AlarmName
		DisplayString,
	rxDtt1AlarmStatus
		AlarmStatus,
	rxDtt1InputOn
		TruthValue,
	rxDtt1Log
		TruthValue,
	rxDtt1Fault
		TruthValue,
	rxDtt1Warning
		TruthValue,
	rxDtt1Led
		TruthValue,
	rxDtt11p1
		TruthValue,
	rxDtt1Ext1
		TruthValue,
	rxDtt1Ext2
		TruthValue,
	rxDtt1Trap
		TruthValue,
	rxDtt1DD
		TruthValue,
	rxDtt1TrapHysteresis
		Unsigned32
}

rxDtt1Index  OBJECT-TYPE
	SYNTAX     Unsigned32 (1..4)
	MAX-ACCESS not-accessible
	STATUS     current
	DESCRIPTION
		"Terrestial receiver 1 Alarm Index"
	::= { rxDtt1Entry 1 }

rxDtt1AlarmName  OBJECT-TYPE
	SYNTAX     DisplayString
	MAX-ACCESS read-only
	STATUS     current
	DESCRIPTION
		"Terrestial receiver 1 Alarm Name"
	::= { rxDtt1Entry 2 }

rxDtt1AlarmStatus  OBJECT-TYPE
	SYNTAX     AlarmStatus
	MAX-ACCESS read-only
	STATUS     current
	DESCRIPTION
		"Amplifier"
	::= { rxDtt1Entry 3 }

rxDtt1InputOn  OBJECT-TYPE
	SYNTAX     TruthValue
	MAX-ACCESS read-write
	STATUS     current
	DESCRIPTION
		"On/Off alarm viwer.

		When you set off this amlarm, it will be on 3th status, so alarm will be on unknown status."
	::= { rxDtt1Entry 4 }

rxDtt1Log  OBJECT-TYPE
	SYNTAX     TruthValue
	MAX-ACCESS read-write
	STATUS     current
	DESCRIPTION
		"This alarm is logged "
	::= { rxDtt1Entry 5 }

rxDtt1Fault  OBJECT-TYPE
	SYNTAX     TruthValue
	MAX-ACCESS read-write
	STATUS     current
	DESCRIPTION
		"This alarm sum to Fault alarm "
	::= { rxDtt1Entry 6 }

rxDtt1Warning  OBJECT-TYPE
	SYNTAX     TruthValue
	MAX-ACCESS read-write
	STATUS     current
	DESCRIPTION
		"This alarm sum to Warning alarm "
	::= { rxDtt1Entry 7 }

rxDtt1Led  OBJECT-TYPE
	SYNTAX     TruthValue
	MAX-ACCESS read-write
	STATUS     current
	DESCRIPTION
		"This alarm modify LED status "
	::= { rxDtt1Entry 8 }

rxDtt11p1  OBJECT-TYPE
	SYNTAX     TruthValue
	MAX-ACCESS read-write
	STATUS     current
	DESCRIPTION
		"This alarm is a switching cause"
	::= { rxDtt1Entry 9 }

rxDtt1Ext1  OBJECT-TYPE
	SYNTAX     TruthValue
	MAX-ACCESS read-write
	STATUS     current
	DESCRIPTION
		"This alarm sum to External relay 1 "
	::= { rxDtt1Entry 10 }

rxDtt1Ext2  OBJECT-TYPE
	SYNTAX     TruthValue
	MAX-ACCESS read-write
	STATUS     current
	DESCRIPTION
		"This alarm sum to External delay 2 "
	::= { rxDtt1Entry 11 }

rxDtt1Trap  OBJECT-TYPE
	SYNTAX     TruthValue
	MAX-ACCESS read-write
	STATUS     current
	DESCRIPTION
		"This alarm generates SNMP trap "
	::= { rxDtt1Entry 12 }

rxDtt1DD  OBJECT-TYPE
	SYNTAX     TruthValue
	MAX-ACCESS read-write
	STATUS     current
	DESCRIPTION
		"This alarm is a switching cause"
	::= { rxDtt1Entry 13 }

rxDtt1TrapHysteresis  OBJECT-TYPE
	SYNTAX     Unsigned32(0..255)
	MAX-ACCESS read-write
	STATUS     current
	DESCRIPTION
		"Hysteresis trap"
	::= { rxDtt1Entry 14 }

rxDtt2Table  OBJECT-TYPE
	SYNTAX SEQUENCE OF RxDtt2Entry
	MAX-ACCESS not-accessible
	STATUS     current
	DESCRIPTION
		"RX Terrestrial 2 alarm table "
	::= { alarmsConfiguration 26 }

rxDtt2Entry  OBJECT-TYPE
	SYNTAX 	RxDtt2Entry
	MAX-ACCESS not-accessible
	STATUS     current
	DESCRIPTION
		"RX Terrestrial 2 alarm table entry"
	INDEX { rxDtt2Index }
	::= { rxDtt2Table 1 }

RxDtt2Entry ::= SEQUENCE {
	rxDtt2Index
		Unsigned32,
	rxDtt2AlarmName
		DisplayString,
	rxDtt2AlarmStatus
		AlarmStatus,
	rxDtt2InputOn
		TruthValue,
	rxDtt2Log
		TruthValue,
	rxDtt2Fault
		TruthValue,
	rxDtt2Warning
		TruthValue,
	rxDtt2Led
		TruthValue,
	rxDtt21p1
		TruthValue,
	rxDtt2Ext1
		TruthValue,
	rxDtt2Ext2
		TruthValue,
	rxDtt2Trap
		TruthValue,
	rxDtt2DD
		TruthValue,
	rxDtt2TrapHysteresis
		Unsigned32
}

rxDtt2Index  OBJECT-TYPE
	SYNTAX     Unsigned32 (1..4)
	MAX-ACCESS not-accessible
	STATUS     current
	DESCRIPTION
		"Terrestial receiver 2 Alarm Index"
	::= { rxDtt2Entry 1 }

rxDtt2AlarmName  OBJECT-TYPE
	SYNTAX     DisplayString
	MAX-ACCESS read-only
	STATUS     current
	DESCRIPTION
		"Terrestial receiver 2 Alarm Name"
	::= { rxDtt2Entry 2 }

rxDtt2AlarmStatus  OBJECT-TYPE
	SYNTAX     AlarmStatus
	MAX-ACCESS read-only
	STATUS     current
	DESCRIPTION
		"Amplifier"
	::= { rxDtt2Entry 3 }

rxDtt2InputOn  OBJECT-TYPE
	SYNTAX     TruthValue
	MAX-ACCESS read-write
	STATUS     current
	DESCRIPTION
		"On/Off alarm viwer.

		When you set off this amlarm, it will be on 3th status, so alarm will be on unknown status."
	::= { rxDtt2Entry 4 }

rxDtt2Log  OBJECT-TYPE
	SYNTAX     TruthValue
	MAX-ACCESS read-write
	STATUS     current
	DESCRIPTION
		"This alarm is logged "
	::= { rxDtt2Entry 5 }

rxDtt2Fault  OBJECT-TYPE
	SYNTAX     TruthValue
	MAX-ACCESS read-write
	STATUS     current
	DESCRIPTION
		"This alarm sum to Fault alarm "
	::= { rxDtt2Entry 6 }

rxDtt2Warning  OBJECT-TYPE
	SYNTAX     TruthValue
	MAX-ACCESS read-write
	STATUS     current
	DESCRIPTION
		"This alarm sum to Warning alarm "
	::= { rxDtt2Entry 7 }

rxDtt2Led  OBJECT-TYPE
	SYNTAX     TruthValue
	MAX-ACCESS read-write
	STATUS     current
	DESCRIPTION
		"This alarm modify LED status "
	::= { rxDtt2Entry 8 }

rxDtt21p1  OBJECT-TYPE
	SYNTAX     TruthValue
	MAX-ACCESS read-write
	STATUS     current
	DESCRIPTION
		"This alarm is a switching cause"
	::= { rxDtt2Entry 9 }

rxDtt2Ext1  OBJECT-TYPE
	SYNTAX     TruthValue
	MAX-ACCESS read-write
	STATUS     current
	DESCRIPTION
		"This alarm sum to External relay 1 "
	::= { rxDtt2Entry 10 }

rxDtt2Ext2  OBJECT-TYPE
	SYNTAX     TruthValue
	MAX-ACCESS read-write
	STATUS     current
	DESCRIPTION
		"This alarm sum to External delay 2 "
	::= { rxDtt2Entry 11 }

rxDtt2Trap  OBJECT-TYPE
	SYNTAX     TruthValue
	MAX-ACCESS read-write
	STATUS     current
	DESCRIPTION
		"This alarm generates SNMP trap "
	::= { rxDtt2Entry 12 }

rxDtt2DD  OBJECT-TYPE
	SYNTAX     TruthValue
	MAX-ACCESS read-write
	STATUS     current
	DESCRIPTION
		"This alarm is a switching cause"
	::= { rxDtt2Entry 13 }

rxDtt2TrapHysteresis  OBJECT-TYPE
	SYNTAX     Unsigned32(0..255)
	MAX-ACCESS read-write
	STATUS     current
	DESCRIPTION
		"Hysteresis trap"
	::= { rxDtt2Entry 14 }

rfInTable  OBJECT-TYPE
	SYNTAX SEQUENCE OF RfInEntry
	MAX-ACCESS not-accessible
	STATUS     current
	DESCRIPTION
		"RF input alarm table "
	::= { alarmsConfiguration 30 }

rfInEntry  OBJECT-TYPE
	SYNTAX 	RfInEntry
	MAX-ACCESS not-accessible
	STATUS     current
	DESCRIPTION
		"RF input alarm table entry"
	INDEX { rfInIndex }
	::= { rfInTable 1 }

RfInEntry ::= SEQUENCE {
	rfInIndex
		Unsigned32,
	rfInAlarmName
		DisplayString,
	rfInAlarmStatus
		AlarmStatus,
	rfInInputOn
		TruthValue,
	rfInLog
		TruthValue,
	rfInFault
		TruthValue,
	rfInWarning
		TruthValue,
	rfInLed
		TruthValue,
	rfIn1p1
		TruthValue,
	rfInExt1
		TruthValue,
	rfInExt2
		TruthValue,
	rfInTrap
		TruthValue,
	rfInDD
		TruthValue,
	rfInTrapHysteresis
		Unsigned32
}

rfInIndex  OBJECT-TYPE
	SYNTAX     Unsigned32 (1)
	MAX-ACCESS not-accessible
	STATUS     current
	DESCRIPTION
		"RF Input Alarm Index"
	::= { rfInEntry 1 }

rfInAlarmName  OBJECT-TYPE
	SYNTAX     DisplayString
	MAX-ACCESS read-only
	STATUS     current
	DESCRIPTION
		"RF In Alarm Name"
	::= { rfInEntry 2 }

rfInAlarmStatus  OBJECT-TYPE
	SYNTAX     AlarmStatus
	MAX-ACCESS read-only
	STATUS     current
	DESCRIPTION
		"General Alarm Status"
	::= { rfInEntry 3 }

rfInInputOn  OBJECT-TYPE
	SYNTAX     TruthValue
	MAX-ACCESS read-write
	STATUS     current
	DESCRIPTION
		"On/Off alarm viwer.

		When you set off this amlarm, it will be on 3th status, so alarm will be on unknown status."
	::= { rfInEntry 4 }

rfInLog  OBJECT-TYPE
	SYNTAX     TruthValue
	MAX-ACCESS read-write
	STATUS     current
	DESCRIPTION
		"This alarm is logged "
	::= { rfInEntry 5 }

rfInFault  OBJECT-TYPE
	SYNTAX     TruthValue
	MAX-ACCESS read-write
	STATUS     current
	DESCRIPTION
		"This alarm sum to Fault alarm "
	::= { rfInEntry 6 }

rfInWarning  OBJECT-TYPE
	SYNTAX     TruthValue
	MAX-ACCESS read-write
	STATUS     current
	DESCRIPTION
		"This alarm sum to Warning alarm "
	::= { rfInEntry 7 }

rfInLed  OBJECT-TYPE
	SYNTAX     TruthValue
	MAX-ACCESS read-write
	STATUS     current
	DESCRIPTION
		"This alarm modify LED status "
	::= { rfInEntry 8 }

rfIn1p1  OBJECT-TYPE
	SYNTAX     TruthValue
	MAX-ACCESS read-write
	STATUS     current
	DESCRIPTION
		"This alarm is a switching cause"
	::= { rfInEntry 9 }

rfInExt1  OBJECT-TYPE
	SYNTAX     TruthValue
	MAX-ACCESS read-write
	STATUS     current
	DESCRIPTION
		"This alarm sum to External relay 1 "
	::= { rfInEntry 10 }

rfInExt2  OBJECT-TYPE
	SYNTAX     TruthValue
	MAX-ACCESS read-write
	STATUS     current
	DESCRIPTION
		"This alarm sum to External delay 2 "
	::= { rfInEntry 11 }

rfInTrap  OBJECT-TYPE
	SYNTAX     TruthValue
	MAX-ACCESS read-write
	STATUS     current
	DESCRIPTION
		"This alarm generates SNMP trap "
	::= { rfInEntry 12 }

rfInDD  OBJECT-TYPE
	SYNTAX     TruthValue
	MAX-ACCESS read-write
	STATUS     current
	DESCRIPTION
		"This alarm is a switching cause"
	::= { rfInEntry 13 }

rfInTrapHysteresis  OBJECT-TYPE
	SYNTAX     Unsigned32(0..255)
	MAX-ACCESS read-write
	STATUS     current
	DESCRIPTION
		"Hysteresis trap"
	::= { rfInEntry 14 }

rackCoolingAlarmConfTable  OBJECT-TYPE
	SYNTAX SEQUENCE OF RackCoolingAlarmConfEntry
	MAX-ACCESS not-accessible
	STATUS     current
	DESCRIPTION
		"Rack cooling alarm configuration table "
	::= { alarmsConfiguration 34 }

rackCoolingAlarmConfEntry  OBJECT-TYPE
	SYNTAX 	RackCoolingAlarmConfEntry
	MAX-ACCESS not-accessible
	STATUS     current
	DESCRIPTION
		"Rack cooling alarm configuration table entry "
	INDEX { rackCoolingACIndex }
	::= { rackCoolingAlarmConfTable 1 }

RackCoolingAlarmConfEntry ::= SEQUENCE {
	rackCoolingACIndex
		Unsigned32,
	rackCoolingAlarmName
		DisplayString,
	rackCoolingAlarmStatus
		AlarmStatus,
	rackCoolingInputOn
		TruthValue,
	rackCoolingLog
		TruthValue,
	rackCoolingFault
		TruthValue,
	rackCoolingWarning
		TruthValue,
	rackCoolingLed
		TruthValue,
	rackCooling1p1
		TruthValue,
	rackCoolingExt1
		TruthValue,
	rackCoolingExt2
		TruthValue,
	rackCoolingTrap
		TruthValue,
	rackCoolingDD
		TruthValue,
	rackCoolingTrapHysteresis
		Unsigned32
}

rackCoolingACIndex  OBJECT-TYPE
	SYNTAX     Unsigned32 (1..3)
	MAX-ACCESS not-accessible
	STATUS     current
	DESCRIPTION
		"Rack cooling Alarm Configuration Index"
	::= { rackCoolingAlarmConfEntry 1 }

rackCoolingAlarmName  OBJECT-TYPE
	SYNTAX     DisplayString
	MAX-ACCESS read-only
	STATUS     current
	DESCRIPTION
		"Rack cooling alarm Name"
	::= { rackCoolingAlarmConfEntry 2 }

rackCoolingAlarmStatus  OBJECT-TYPE
	SYNTAX     AlarmStatus
	MAX-ACCESS read-only
	STATUS     current
	DESCRIPTION
		"General Alarm Status"
	::= { rackCoolingAlarmConfEntry 3 }

rackCoolingInputOn  OBJECT-TYPE
	SYNTAX     TruthValue
	MAX-ACCESS read-write
	STATUS     current
	DESCRIPTION
		"On/Off alarm viwer.

		When you set off this amlarm, it will be on 3th status, so alarm will be on unknown status."
	::= { rackCoolingAlarmConfEntry 4 }

rackCoolingLog  OBJECT-TYPE
	SYNTAX     TruthValue
	MAX-ACCESS read-write
	STATUS     current
	DESCRIPTION
		"This alarm is logged "
	::= { rackCoolingAlarmConfEntry 5 }

rackCoolingFault  OBJECT-TYPE
	SYNTAX     TruthValue
	MAX-ACCESS read-write
	STATUS     current
	DESCRIPTION
		"This alarm sum to Fault alarm "
	::= { rackCoolingAlarmConfEntry 6 }

rackCoolingWarning  OBJECT-TYPE
	SYNTAX     TruthValue
	MAX-ACCESS read-write
	STATUS     current
	DESCRIPTION
		"This alarm sum to Warning alarm "
	::= { rackCoolingAlarmConfEntry 7 }

rackCoolingLed  OBJECT-TYPE
	SYNTAX     TruthValue
	MAX-ACCESS read-write
	STATUS     current
	DESCRIPTION
		"This alarm modify LED status "
	::= { rackCoolingAlarmConfEntry 8 }

rackCooling1p1  OBJECT-TYPE
	SYNTAX     TruthValue
	MAX-ACCESS read-write
	STATUS     current
	DESCRIPTION
		"This alarm is a switching cause"
	::= { rackCoolingAlarmConfEntry 9 }

rackCoolingExt1  OBJECT-TYPE
	SYNTAX     TruthValue
	MAX-ACCESS read-write
	STATUS     current
	DESCRIPTION
		"This alarm sum to External relay 1 "
	::= { rackCoolingAlarmConfEntry 10 }

rackCoolingExt2  OBJECT-TYPE
	SYNTAX     TruthValue
	MAX-ACCESS read-write
	STATUS     current
	DESCRIPTION
		"This alarm sum to External delay 2 "
	::= { rackCoolingAlarmConfEntry 11 }

rackCoolingTrap  OBJECT-TYPE
	SYNTAX     TruthValue
	MAX-ACCESS read-write
	STATUS     current
	DESCRIPTION
		"This alarm generates SNMP trap "
	::= { rackCoolingAlarmConfEntry 12 }

rackCoolingDD  OBJECT-TYPE
	SYNTAX     TruthValue
	MAX-ACCESS read-write
	STATUS     current
	DESCRIPTION
		"This alarm is a switching cause"
	::= { rackCoolingAlarmConfEntry 13 }

rackCoolingTrapHysteresis  OBJECT-TYPE
	SYNTAX     Unsigned32(0..255)
	MAX-ACCESS read-write
	STATUS     current
	DESCRIPTION
		"Hysteresis trap"
	::= { rackCoolingAlarmConfEntry 14 }

cancellerTable  OBJECT-TYPE
	SYNTAX SEQUENCE OF CancellerEntry
	MAX-ACCESS not-accessible
	STATUS     current
	DESCRIPTION
		"Canceller alarm table "
	::= { alarmsConfiguration 35 }

cancellerEntry  OBJECT-TYPE
	SYNTAX 	CancellerEntry
	MAX-ACCESS not-accessible
	STATUS     current
	DESCRIPTION
		"Canceller alarm table entry "
	INDEX { cancellerIndex }
	::= { cancellerTable 1 }

CancellerEntry ::= SEQUENCE {
	cancellerIndex
		Unsigned32,
	cancellerAlarmName
		DisplayString,
	cancellerAlarmStatus
		AlarmStatus,
	cancellerInputOn
		TruthValue,
	cancellerLog
		TruthValue,
	cancellerFault
		TruthValue,
	cancellerWarning
		TruthValue,
	cancellerLed
		TruthValue,
	canceller1p1
		TruthValue,
	cancellerExt1
		TruthValue,
	cancellerExt2
		TruthValue,
	cancellerTrap
		TruthValue,
	cancellerDD
		TruthValue,
	cancellerTrapHysteresis
		Unsigned32
}

cancellerIndex  OBJECT-TYPE
	SYNTAX     Unsigned32 (1..3)
	MAX-ACCESS not-accessible
	STATUS     current
	DESCRIPTION
		"RF Input Alarm Index"
	::= { cancellerEntry 1 }

cancellerAlarmName  OBJECT-TYPE
	SYNTAX     DisplayString
	MAX-ACCESS read-only
	STATUS     current
	DESCRIPTION
		"RF In Alarm Name"
	::= { cancellerEntry 2 }

cancellerAlarmStatus  OBJECT-TYPE
	SYNTAX     AlarmStatus
	MAX-ACCESS read-only
	STATUS     current
	DESCRIPTION
		"General Alarm Status"
	::= { cancellerEntry 3 }

cancellerInputOn  OBJECT-TYPE
	SYNTAX     TruthValue
	MAX-ACCESS read-write
	STATUS     current
	DESCRIPTION
		"On/Off alarm viwer.

		When you set off this amlarm, it will be on 3th status, so alarm will be on unknown status."
	::= { cancellerEntry 4 }

cancellerLog  OBJECT-TYPE
	SYNTAX     TruthValue
	MAX-ACCESS read-write
	STATUS     current
	DESCRIPTION
		"This alarm is logged "
	::= { cancellerEntry 5 }

cancellerFault  OBJECT-TYPE
	SYNTAX     TruthValue
	MAX-ACCESS read-write
	STATUS     current
	DESCRIPTION
		"This alarm sum to Fault alarm "
	::= { cancellerEntry 6 }

cancellerWarning  OBJECT-TYPE
	SYNTAX     TruthValue
	MAX-ACCESS read-write
	STATUS     current
	DESCRIPTION
		"This alarm sum to Warning alarm "
	::= { cancellerEntry 7 }

cancellerLed  OBJECT-TYPE
	SYNTAX     TruthValue
	MAX-ACCESS read-write
	STATUS     current
	DESCRIPTION
		"This alarm modify LED status "
	::= { cancellerEntry 8 }

canceller1p1  OBJECT-TYPE
	SYNTAX     TruthValue
	MAX-ACCESS read-write
	STATUS     current
	DESCRIPTION
		"This alarm is a switching cause"
	::= { cancellerEntry 9 }

cancellerExt1  OBJECT-TYPE
	SYNTAX     TruthValue
	MAX-ACCESS read-write
	STATUS     current
	DESCRIPTION
		"This alarm sum to External relay 1 "
	::= { cancellerEntry 10 }

cancellerExt2  OBJECT-TYPE
	SYNTAX     TruthValue
	MAX-ACCESS read-write
	STATUS     current
	DESCRIPTION
		"This alarm sum to External delay 2 "
	::= { cancellerEntry 11 }

cancellerTrap  OBJECT-TYPE
	SYNTAX     TruthValue
	MAX-ACCESS read-write
	STATUS     current
	DESCRIPTION
		"This alarm generates SNMP trap "
	::= { cancellerEntry 12 }

cancellerDD  OBJECT-TYPE
	SYNTAX     TruthValue
	MAX-ACCESS read-write
	STATUS     current
	DESCRIPTION
		"This alarm is a switching cause"
	::= { cancellerEntry 13 }

cancellerTrapHysteresis  OBJECT-TYPE
	SYNTAX     Unsigned32(0..255)
	MAX-ACCESS read-write
	STATUS     current
	DESCRIPTION
		"Hysteresis trap"
	::= { cancellerEntry 14 }

modulatorTable  OBJECT-TYPE
	SYNTAX SEQUENCE OF ModulatorEntry
	MAX-ACCESS not-accessible
	STATUS     current
	DESCRIPTION
		"Modulator alarm table "
	::= { alarmsConfiguration 40 }

modulatorEntry  OBJECT-TYPE
	SYNTAX 	ModulatorEntry
	MAX-ACCESS not-accessible
	STATUS     current
	DESCRIPTION
		"Modulator alarm table entry "
	INDEX { modulatorIndex }
	::= { modulatorTable 1 }

ModulatorEntry ::= SEQUENCE {
	modulatorIndex
		Unsigned32,
	modulatorAlarmName
		DisplayString,
	modulatorAlarmStatus
		AlarmStatus,
	modulatorInputOn
		TruthValue,
	modulatorLog
		TruthValue,
	modulatorFault
		TruthValue,
	modulatorWarning
		TruthValue,
	modulatorLed
		TruthValue,
	modulator1p1
		TruthValue,
	modulatorExt1
		TruthValue,
	modulatorExt2
		TruthValue,
	modulatorTrap
		TruthValue,
	modulatorDD
		TruthValue,
	modulatorTrapHysteresis
		Unsigned32
}

modulatorIndex  OBJECT-TYPE
	SYNTAX     Unsigned32 (1..10)
	MAX-ACCESS not-accessible
	STATUS     current
	DESCRIPTION
		"Modulator Alarm Index"
	::= { modulatorEntry 1 }

modulatorAlarmName  OBJECT-TYPE
	SYNTAX     DisplayString
	MAX-ACCESS read-only
	STATUS     current
	DESCRIPTION
		"Modulator Alarm Name"
	::= { modulatorEntry 2 }

modulatorAlarmStatus  OBJECT-TYPE
	SYNTAX     AlarmStatus
	MAX-ACCESS read-only
	STATUS     current
	DESCRIPTION
		"Amplifier"
	::= { modulatorEntry 3 }

modulatorInputOn  OBJECT-TYPE
	SYNTAX     TruthValue
	MAX-ACCESS read-write
	STATUS     current
	DESCRIPTION
		"On/Off alarm viwer.

		When you set off this amlarm, it will be on 3th status, so alarm will be on unknown status."
	::= { modulatorEntry 4 }

modulatorLog  OBJECT-TYPE
	SYNTAX     TruthValue
	MAX-ACCESS read-write
	STATUS     current
	DESCRIPTION
		"This alarm is logged "
	::= { modulatorEntry 5 }

modulatorFault  OBJECT-TYPE
	SYNTAX     TruthValue
	MAX-ACCESS read-write
	STATUS     current
	DESCRIPTION
		"This alarm sum to Fault alarm "
	::= { modulatorEntry 6 }

modulatorWarning  OBJECT-TYPE
	SYNTAX     TruthValue
	MAX-ACCESS read-write
	STATUS     current
	DESCRIPTION
		"This alarm sum to Warning alarm "
	::= { modulatorEntry 7 }

modulatorLed  OBJECT-TYPE
	SYNTAX     TruthValue
	MAX-ACCESS read-write
	STATUS     current
	DESCRIPTION
		"This alarm modify LED status "
	::= { modulatorEntry 8 }

modulator1p1  OBJECT-TYPE
	SYNTAX     TruthValue
	MAX-ACCESS read-write
	STATUS     current
	DESCRIPTION
		"This alarm is a switching cause"
	::= { modulatorEntry 9 }

modulatorExt1  OBJECT-TYPE
	SYNTAX     TruthValue
	MAX-ACCESS read-write
	STATUS     current
	DESCRIPTION
		"This alarm sum to External relay 1 "
	::= { modulatorEntry 10 }

modulatorExt2  OBJECT-TYPE
	SYNTAX     TruthValue
	MAX-ACCESS read-write
	STATUS     current
	DESCRIPTION
		"This alarm sum to External delay 2 "
	::= { modulatorEntry 11 }

modulatorTrap  OBJECT-TYPE
	SYNTAX     TruthValue
	MAX-ACCESS read-write
	STATUS     current
	DESCRIPTION
		"This alarm generates SNMP trap "
	::= { modulatorEntry 12 }

modulatorDD  OBJECT-TYPE
	SYNTAX     TruthValue
	MAX-ACCESS read-write
	STATUS     current
	DESCRIPTION
		"This alarm is a switching cause"
	::= { modulatorEntry 13 }

modulatorTrapHysteresis  OBJECT-TYPE
	SYNTAX     Unsigned32(0..255)
	MAX-ACCESS read-write
	STATUS     current
	DESCRIPTION
		"Hysteresis trap"
	::= { modulatorEntry 14 }

rfOutTable  OBJECT-TYPE
	SYNTAX SEQUENCE OF RfOutEntry
	MAX-ACCESS not-accessible
	STATUS     current
	DESCRIPTION
		"RF Output alarm table "
	::= { alarmsConfiguration 45 }

rfOutEntry  OBJECT-TYPE
	SYNTAX 	RfOutEntry
	MAX-ACCESS not-accessible
	STATUS     current
	DESCRIPTION
		"RF Output alarm table entry "
	INDEX { rfOutIndex }
	::= { rfOutTable 1 }

RfOutEntry ::= SEQUENCE {
	rfOutIndex
		Unsigned32,
	rfOutAlarmName
		DisplayString,
	rfOutAlarmStatus
		AlarmStatus,
	rfOutInputOn
		TruthValue,
	rfOutLog
		TruthValue,
	rfOutFault
		TruthValue,
	rfOutWarning
		TruthValue,
	rfOutLed
		TruthValue,
	rfOut1p1
		TruthValue,
	rfOutExt1
		TruthValue,
	rfOutExt2
		TruthValue,
	rfOutTrap
		TruthValue,
	rfOutDD
		TruthValue,
	rfOutTrapHysteresis
		Unsigned32
}

rfOutIndex  OBJECT-TYPE
	SYNTAX     Unsigned32 (1..11)
	MAX-ACCESS not-accessible
	STATUS     current
	DESCRIPTION
		"RF Output Alarm Index"
	::= { rfOutEntry 1 }

rfOutAlarmName  OBJECT-TYPE
	SYNTAX     DisplayString
	MAX-ACCESS read-only
	STATUS     current
	DESCRIPTION
		"RF Output Alarm Name"
	::= { rfOutEntry 2 }

rfOutAlarmStatus  OBJECT-TYPE
	SYNTAX     AlarmStatus
	MAX-ACCESS read-only
	STATUS     current
	DESCRIPTION
		"Amplifier"
	::= { rfOutEntry 3 }

rfOutInputOn  OBJECT-TYPE
	SYNTAX     TruthValue
	MAX-ACCESS read-write
	STATUS     current
	DESCRIPTION
		"On/Off alarm viwer.

		When you set off this amlarm, it will be on 3th status, so alarm will be on unknown status."
	::= { rfOutEntry 4 }

rfOutLog  OBJECT-TYPE
	SYNTAX     TruthValue
	MAX-ACCESS read-write
	STATUS     current
	DESCRIPTION
		"This alarm is logged "
	::= { rfOutEntry 5 }

rfOutFault  OBJECT-TYPE
	SYNTAX     TruthValue
	MAX-ACCESS read-write
	STATUS     current
	DESCRIPTION
		"This alarm sum to Fault alarm "
	::= { rfOutEntry 6 }

rfOutWarning  OBJECT-TYPE
	SYNTAX     TruthValue
	MAX-ACCESS read-write
	STATUS     current
	DESCRIPTION
		"This alarm sum to Warning alarm "
	::= { rfOutEntry 7 }

rfOutLed  OBJECT-TYPE
	SYNTAX     TruthValue
	MAX-ACCESS read-write
	STATUS     current
	DESCRIPTION
		"This alarm modify LED status "
	::= { rfOutEntry 8 }

rfOut1p1  OBJECT-TYPE
	SYNTAX     TruthValue
	MAX-ACCESS read-write
	STATUS     current
	DESCRIPTION
		"This alarm is a switching cause"
	::= { rfOutEntry 9 }

rfOutExt1  OBJECT-TYPE
	SYNTAX     TruthValue
	MAX-ACCESS read-write
	STATUS     current
	DESCRIPTION
		"This alarm sum to External relay 1 "
	::= { rfOutEntry 10 }

rfOutExt2  OBJECT-TYPE
	SYNTAX     TruthValue
	MAX-ACCESS read-write
	STATUS     current
	DESCRIPTION
		"This alarm sum to External delay 2 "
	::= { rfOutEntry 11 }

rfOutTrap  OBJECT-TYPE
	SYNTAX     TruthValue
	MAX-ACCESS read-write
	STATUS     current
	DESCRIPTION
		"This alarm generates SNMP trap "
	::= { rfOutEntry 12 }

rfOutDD  OBJECT-TYPE
	SYNTAX     TruthValue
	MAX-ACCESS read-write
	STATUS     current
	DESCRIPTION
		"This alarm is a switching cause"
	::= { rfOutEntry 13 }

rfOutTrapHysteresis  OBJECT-TYPE
	SYNTAX     Unsigned32(0..255)
	MAX-ACCESS read-write
	STATUS     current
	DESCRIPTION
		"Hysteresis trap"
	::= { rfOutEntry 14 }

synchronizationTable  OBJECT-TYPE
	SYNTAX SEQUENCE OF SynchronizationEntry
	MAX-ACCESS not-accessible
	STATUS     current
	DESCRIPTION
		"Syncrhonizaction alarm table "
	::= { alarmsConfiguration 55 }

synchronizationEntry  OBJECT-TYPE
	SYNTAX 	SynchronizationEntry
	MAX-ACCESS not-accessible
	STATUS     current
	DESCRIPTION
		"Syncrhonizaction alarm table entry"
	INDEX { synchronizationIndex }
	::= { synchronizationTable 1 }

SynchronizationEntry ::= SEQUENCE {
	synchronizationIndex
		Unsigned32,
	synchronizationAlarmName
		DisplayString,
	synchronizationAlarmStatus
		AlarmStatus,
	synchronizationOn
		TruthValue,
	synchronizationLog
		TruthValue,
	synchronizationFault
		TruthValue,
	synchronizationWarning
		TruthValue,
	synchronizationLed
		TruthValue,
	synchronization1p1
		TruthValue,
	synchronizationExt1
		TruthValue,
	synchronizationExt2
		TruthValue,
	synchronizationTrap
		TruthValue,
	synchronizationDD
		TruthValue,
	synchronizationTrapHysteresis
		Unsigned32
}

synchronizationIndex  OBJECT-TYPE
	SYNTAX     Unsigned32 (1..6)
	MAX-ACCESS not-accessible
	STATUS     current
	DESCRIPTION
		"Synchronization Alarm Index"
	::= { synchronizationEntry 1 }

synchronizationAlarmName  OBJECT-TYPE
	SYNTAX     DisplayString
	MAX-ACCESS read-only
	STATUS     current
	DESCRIPTION
		"Synchronization Alarm Name"
	::= { synchronizationEntry 2 }

synchronizationAlarmStatus  OBJECT-TYPE
	SYNTAX     AlarmStatus
	MAX-ACCESS read-only
	STATUS     current
	DESCRIPTION
		"Synchronization Alarm Status"
	::= { synchronizationEntry 3 }

synchronizationOn  OBJECT-TYPE
	SYNTAX     TruthValue
	MAX-ACCESS read-write
	STATUS     current
	DESCRIPTION
		"On/Off alarm viwer.

		When you set off this amlarm, it will be on 3th status, so alarm will be on unknown status."
	::= { synchronizationEntry 4 }

synchronizationLog  OBJECT-TYPE
	SYNTAX     TruthValue
	MAX-ACCESS read-write
	STATUS     current
	DESCRIPTION
		"This alarm is logged"
	::= { synchronizationEntry 5 }

synchronizationFault  OBJECT-TYPE
	SYNTAX     TruthValue
	MAX-ACCESS read-write
	STATUS     current
	DESCRIPTION
		"This alarm sum to Fault alarm"
	::= { synchronizationEntry 6 }

synchronizationWarning  OBJECT-TYPE
	SYNTAX     TruthValue
	MAX-ACCESS read-write
	STATUS     current
	DESCRIPTION
		"This alarm sum to Warning alarm"
	::= { synchronizationEntry 7 }

synchronizationLed  OBJECT-TYPE
	SYNTAX     TruthValue
	MAX-ACCESS read-write
	STATUS     current
	DESCRIPTION
		"This alarm affects to alarm led"
	::= { synchronizationEntry 8 }

synchronization1p1  OBJECT-TYPE
	SYNTAX     TruthValue
	MAX-ACCESS read-write
	STATUS     current
	DESCRIPTION
		"This alarm is a switching 1+1 cause"
	::= { synchronizationEntry 9 }

synchronizationExt1  OBJECT-TYPE
	SYNTAX     TruthValue
	MAX-ACCESS read-write
	STATUS     current
	DESCRIPTION
		"This alarm affects to external relay 1"
	::= { synchronizationEntry 10 }

synchronizationExt2  OBJECT-TYPE
	SYNTAX     TruthValue
	MAX-ACCESS read-write
	STATUS     current
	DESCRIPTION
		"This alarm affects to external relay 2"
	::= { synchronizationEntry 11 }

synchronizationTrap  OBJECT-TYPE
	SYNTAX     TruthValue
	MAX-ACCESS read-write
	STATUS     current
	DESCRIPTION
		"This alarm will send a trap"
	::= { synchronizationEntry 12 }

synchronizationDD  OBJECT-TYPE
	SYNTAX     TruthValue
	MAX-ACCESS read-write
	STATUS     current
	DESCRIPTION
		"This alarm is a switching Dual Drive cause"
	::= { synchronizationEntry 13 }

synchronizationTrapHysteresis  OBJECT-TYPE
	SYNTAX     Unsigned32(0..255)
	MAX-ACCESS read-write
	STATUS     current
	DESCRIPTION
		"Hysteresis trap"
	::= { synchronizationEntry 14 }

errorHwTable  OBJECT-TYPE
	SYNTAX SEQUENCE OF ErrorHwEntry
	MAX-ACCESS not-accessible
	STATUS     current
	DESCRIPTION
		"Hardware error alarm table "
	::= { alarmsConfiguration 65 }

errorHwEntry  OBJECT-TYPE
	SYNTAX 	ErrorHwEntry
	MAX-ACCESS not-accessible
	STATUS     current
	DESCRIPTION
		"Hardware error alarm table entry "
	INDEX { errorHwIndex }
	::= { errorHwTable 1 }

ErrorHwEntry ::= SEQUENCE {
	errorHwIndex
		Unsigned32,
	errorHwAlarmName
		DisplayString,
	errorHwAlarmStatus
		AlarmStatus,
	errorHwOn
		TruthValue,
	errorHwLog
		TruthValue,
	errorHwFault
		TruthValue,
	errorHwWarning
		TruthValue,
	errorHwLed
		TruthValue,
	errorHw1p1
		TruthValue,
	errorHwExt1
		TruthValue,
	errorHwExt2
		TruthValue,
	errorHwTrap
		TruthValue,
	errorHwDD
		TruthValue,
	errorHwTrapHysteresis
		Unsigned32
}

errorHwIndex  OBJECT-TYPE
	SYNTAX     Unsigned32 (1..5)
	MAX-ACCESS not-accessible
	STATUS     current
	DESCRIPTION
		"Hardware Alarm Index"
	::= { errorHwEntry 1 }

errorHwAlarmName  OBJECT-TYPE
	SYNTAX     DisplayString
	MAX-ACCESS read-only
	STATUS     current
	DESCRIPTION
		"HW alarm name "
	::= { errorHwEntry 2 }

errorHwAlarmStatus  OBJECT-TYPE
	SYNTAX     AlarmStatus
	MAX-ACCESS read-only
	STATUS     current
	DESCRIPTION
		"Amplifier"
	::= { errorHwEntry 3 }

errorHwOn  OBJECT-TYPE
	SYNTAX     TruthValue
	MAX-ACCESS read-write
	STATUS     current
	DESCRIPTION
		"On/Off alarm viwer.

		When you set off this amlarm, it will be on 3th status, so alarm will be on unknown status."
	::= { errorHwEntry 4 }

errorHwLog  OBJECT-TYPE
	SYNTAX     TruthValue
	MAX-ACCESS read-write
	STATUS     current
	DESCRIPTION
		"This alarm is logged "
	::= { errorHwEntry 5 }

errorHwFault  OBJECT-TYPE
	SYNTAX     TruthValue
	MAX-ACCESS read-write
	STATUS     current
	DESCRIPTION
		"This alarm sum to Fault alarm "
	::= { errorHwEntry 6 }

errorHwWarning  OBJECT-TYPE
	SYNTAX     TruthValue
	MAX-ACCESS read-write
	STATUS     current
	DESCRIPTION
		"This alarm sum to Warning alarm "
	::= { errorHwEntry 7 }

errorHwLed  OBJECT-TYPE
	SYNTAX     TruthValue
	MAX-ACCESS read-write
	STATUS     current
	DESCRIPTION
		"This alarm modify LED status "
	::= { errorHwEntry 8 }

errorHw1p1  OBJECT-TYPE
	SYNTAX     TruthValue
	MAX-ACCESS read-write
	STATUS     current
	DESCRIPTION
		"This alarm is a switching cause"
	::= { errorHwEntry 9 }

errorHwExt1  OBJECT-TYPE
	SYNTAX     TruthValue
	MAX-ACCESS read-write
	STATUS     current
	DESCRIPTION
		"This alarm sum to External relay 1 "
	::= { errorHwEntry 10 }

errorHwExt2  OBJECT-TYPE
	SYNTAX     TruthValue
	MAX-ACCESS read-write
	STATUS     current
	DESCRIPTION
		"This alarm sum to External delay 2 "
	::= { errorHwEntry 11 }

errorHwTrap  OBJECT-TYPE
	SYNTAX     TruthValue
	MAX-ACCESS read-write
	STATUS     current
	DESCRIPTION
		"This alarm generates SNMP trap "
	::= { errorHwEntry 12 }

errorHwDD  OBJECT-TYPE
	SYNTAX     TruthValue
	MAX-ACCESS read-write
	STATUS     current
	DESCRIPTION
		"This alarm is a switching cause"
	::= { errorHwEntry 13 }

errorHwTrapHysteresis  OBJECT-TYPE
	SYNTAX     Unsigned32(0..255)
	MAX-ACCESS read-write
	STATUS     current
	DESCRIPTION
		"Hysteresis trap"
	::= { errorHwEntry 14 }

fanTable  OBJECT-TYPE
	SYNTAX SEQUENCE OF FanEntry
	MAX-ACCESS not-accessible
	STATUS     current
	DESCRIPTION
		"FAN alarm table "
	::= { alarmsConfiguration 70 }

fanEntry  OBJECT-TYPE
	SYNTAX 	FanEntry
	MAX-ACCESS not-accessible
	STATUS     current
	DESCRIPTION
		"FAN alarm table entry"
	INDEX { fanIndex }
	::= { fanTable 1 }

FanEntry ::= SEQUENCE {
	fanIndex
		Unsigned32,
	fanAlarmName
		DisplayString,
	fanAlarmStatus
		AlarmStatus,
	fanOn
		TruthValue,
	fanLog
		TruthValue,
	fanFault
		TruthValue,
	fanWarning
		TruthValue,
	fanLed
		TruthValue,
	fan1p1
		TruthValue,
	fanExt1
		TruthValue,
	fanExt2
		TruthValue,
	fanTrap
		TruthValue,
	fanDD
		TruthValue,
	fanTrapHysteresis
		Unsigned32
}

fanIndex  OBJECT-TYPE
	SYNTAX     Unsigned32 (1..4)
	MAX-ACCESS not-accessible
	STATUS     current
	DESCRIPTION
		"Fan Alarm Index"
	::= { fanEntry 1 }

fanAlarmName  OBJECT-TYPE
	SYNTAX     DisplayString
	MAX-ACCESS read-only
	STATUS     current
	DESCRIPTION
		"FAN alarm name "
	::= { fanEntry 2 }

fanAlarmStatus  OBJECT-TYPE
	SYNTAX     AlarmStatus
	MAX-ACCESS read-only
	STATUS     current
	DESCRIPTION
		"Amplifier"
	::= { fanEntry 3 }

fanOn  OBJECT-TYPE
	SYNTAX     TruthValue
	MAX-ACCESS read-write
	STATUS     current
	DESCRIPTION
		"On/Off alarm viwer.

		When you set off this amlarm, it will be on 3th status, so alarm will be on unknown status."
	::= { fanEntry 4 }

fanLog  OBJECT-TYPE
	SYNTAX     TruthValue
	MAX-ACCESS read-write
	STATUS     current
	DESCRIPTION
		"This alarm is logged "
	::= { fanEntry 5 }

fanFault  OBJECT-TYPE
	SYNTAX     TruthValue
	MAX-ACCESS read-write
	STATUS     current
	DESCRIPTION
		"This alarm sum to Fault alarm "
	::= { fanEntry 6 }

fanWarning  OBJECT-TYPE
	SYNTAX     TruthValue
	MAX-ACCESS read-write
	STATUS     current
	DESCRIPTION
		"This alarm sum to Warning alarm "
	::= { fanEntry 7 }

fanLed  OBJECT-TYPE
	SYNTAX     TruthValue
	MAX-ACCESS read-write
	STATUS     current
	DESCRIPTION
		"This alarm modify LED status "
	::= { fanEntry 8 }

fan1p1  OBJECT-TYPE
	SYNTAX     TruthValue
	MAX-ACCESS read-write
	STATUS     current
	DESCRIPTION
		"This alarm is a switching cause"
	::= { fanEntry 9 }

fanExt1  OBJECT-TYPE
	SYNTAX     TruthValue
	MAX-ACCESS read-write
	STATUS     current
	DESCRIPTION
		"This alarm sum to External relay 1 "
	::= { fanEntry 10 }

fanExt2  OBJECT-TYPE
	SYNTAX     TruthValue
	MAX-ACCESS read-write
	STATUS     current
	DESCRIPTION
		"This alarm sum to External delay 2 "
	::= { fanEntry 11 }

fanTrap  OBJECT-TYPE
	SYNTAX     TruthValue
	MAX-ACCESS read-write
	STATUS     current
	DESCRIPTION
		"This alarm generates SNMP trap "
	::= { fanEntry 12 }

fanDD  OBJECT-TYPE
	SYNTAX     TruthValue
	MAX-ACCESS read-write
	STATUS     current
	DESCRIPTION
		"This alarm is a switching cause"
	::= { fanEntry 13 }

fanTrapHysteresis  OBJECT-TYPE
	SYNTAX     Unsigned32(0..255)
	MAX-ACCESS read-write
	STATUS     current
	DESCRIPTION
		"Hysteresis trap"
	::= { fanEntry 14 }

externalTable  OBJECT-TYPE
	SYNTAX SEQUENCE OF ExternalEntry
	MAX-ACCESS not-accessible
	STATUS     current
	DESCRIPTION
		"External alarm table "
	::= { alarmsConfiguration 75 }

externalEntry  OBJECT-TYPE
	SYNTAX 	ExternalEntry
	MAX-ACCESS not-accessible
	STATUS     current
	DESCRIPTION
		"External alarm table entry "
	INDEX { externalIndex }
	::= { externalTable 1 }

ExternalEntry ::= SEQUENCE {
	externalIndex
		Unsigned32,
	externalAlarmName
		DisplayString,
	externalAlarmStatus
		AlarmStatus,
	externalOn
		TruthValue,
	externalLog
		TruthValue,
	externalFault
		TruthValue,
	externalWarning
		TruthValue,
	externalLed
		TruthValue,
	external1p1
		TruthValue,
	externalExt1
		TruthValue,
	externalExt2
		TruthValue,
	externalTrap
		TruthValue,
	externalDD
		TruthValue,
	externalTrapHysteresis
		Unsigned32
}

externalIndex  OBJECT-TYPE
	SYNTAX     Unsigned32 (1..3)
	MAX-ACCESS not-accessible
	STATUS     current
	DESCRIPTION
		"External Alarm Index"
	::= { externalEntry 1 }

externalAlarmName  OBJECT-TYPE
	SYNTAX     DisplayString
	MAX-ACCESS read-only
	STATUS     current
	DESCRIPTION
		"External alarm name "
	::= { externalEntry 2 }

externalAlarmStatus  OBJECT-TYPE
	SYNTAX     AlarmStatus
	MAX-ACCESS read-only
	STATUS     current
	DESCRIPTION
		"Amplifier"
	::= { externalEntry 3 }

externalOn  OBJECT-TYPE
	SYNTAX     TruthValue
	MAX-ACCESS read-write
	STATUS     current
	DESCRIPTION
		"On/Off alarm viwer.

		When you set off this amlarm, it will be on 3th status, so alarm will be on unknown status."
	::= { externalEntry 4 }

externalLog  OBJECT-TYPE
	SYNTAX     TruthValue
	MAX-ACCESS read-write
	STATUS     current
	DESCRIPTION
		"This alarm is logged "
	::= { externalEntry 5 }

externalFault  OBJECT-TYPE
	SYNTAX     TruthValue
	MAX-ACCESS read-write
	STATUS     current
	DESCRIPTION
		"This alarm sum to Fault alarm "
	::= { externalEntry 6 }

externalWarning  OBJECT-TYPE
	SYNTAX     TruthValue
	MAX-ACCESS read-write
	STATUS     current
	DESCRIPTION
		"This alarm sum to Warning alarm "
	::= { externalEntry 7 }

externalLed  OBJECT-TYPE
	SYNTAX     TruthValue
	MAX-ACCESS read-write
	STATUS     current
	DESCRIPTION
		"This alarm modify LED status "
	::= { externalEntry 8 }

external1p1  OBJECT-TYPE
	SYNTAX     TruthValue
	MAX-ACCESS read-write
	STATUS     current
	DESCRIPTION
		"This alarm is a switching cause"
	::= { externalEntry 9 }

externalExt1  OBJECT-TYPE
	SYNTAX     TruthValue
	MAX-ACCESS read-write
	STATUS     current
	DESCRIPTION
		"This alarm sum to External relay 1 "
	::= { externalEntry 10 }

externalExt2  OBJECT-TYPE
	SYNTAX     TruthValue
	MAX-ACCESS read-write
	STATUS     current
	DESCRIPTION
		"This alarm sum to External delay 2 "
	::= { externalEntry 11 }

externalTrap  OBJECT-TYPE
	SYNTAX     TruthValue
	MAX-ACCESS read-write
	STATUS     current
	DESCRIPTION
		"This alarm generates SNMP trap "
	::= { externalEntry 12 }

externalDD  OBJECT-TYPE
	SYNTAX     TruthValue
	MAX-ACCESS read-write
	STATUS     current
	DESCRIPTION
		"This alarm is a switching cause"
	::= { externalEntry 13 }

externalTrapHysteresis  OBJECT-TYPE
	SYNTAX     Unsigned32(0..255)
	MAX-ACCESS read-write
	STATUS     current
	DESCRIPTION
		"Hysteresis trap"
	::= { externalEntry 14 }

powerSupplyTable  OBJECT-TYPE
	SYNTAX SEQUENCE OF PowerSupplyEntry
	MAX-ACCESS not-accessible
	STATUS     current
	DESCRIPTION
		"Power supply alarm table "
	::= { alarmsConfiguration 80 }

powerSupplyEntry  OBJECT-TYPE
	SYNTAX 	PowerSupplyEntry
	MAX-ACCESS not-accessible
	STATUS     current
	DESCRIPTION
		"Power supply alarm table entry"
	INDEX { powerSupplyIndex }
	::= { powerSupplyTable 1 }

PowerSupplyEntry ::= SEQUENCE {
	powerSupplyIndex
		Unsigned32,
	powerSupplyAlarmName
		DisplayString,
	powerSupplyAlarmStatus
		AlarmStatus,
	powerSupplyOn
		TruthValue,
	powerSupplyLog
		TruthValue,
	powerSupplyFault
		TruthValue,
	powerSupplyWarning
		TruthValue,
	powerSupplyLed
		TruthValue,
	powerSupply1p1
		TruthValue,
	powerSupplyExt1
		TruthValue,
	powerSupplyExt2
		TruthValue,
	powerSupplyTrap
		TruthValue,
	powerSupplyDD
		TruthValue,
	powerSupplyTrapHysteresis
		Unsigned32
}

powerSupplyIndex  OBJECT-TYPE
	SYNTAX     Unsigned32 (1..3)
	MAX-ACCESS not-accessible
	STATUS     current
	DESCRIPTION
		"Popwer Supply Alarm Index"
	::= { powerSupplyEntry 1 }

powerSupplyAlarmName  OBJECT-TYPE
	SYNTAX     DisplayString
	MAX-ACCESS read-only
	STATUS     current
	DESCRIPTION
		"Power supply alarm name "
	::= { powerSupplyEntry 2 }

powerSupplyAlarmStatus  OBJECT-TYPE
	SYNTAX     AlarmStatus
	MAX-ACCESS read-only
	STATUS     current
	DESCRIPTION
		"Alarm"
	::= { powerSupplyEntry 3 }

powerSupplyOn  OBJECT-TYPE
	SYNTAX     TruthValue
	MAX-ACCESS read-write
	STATUS     current
	DESCRIPTION
		"On/Off alarm viwer.

		When you set off this amlarm, it will be on 3th status, so alarm will be on unknown status."
	::= { powerSupplyEntry 4 }

powerSupplyLog  OBJECT-TYPE
	SYNTAX     TruthValue
	MAX-ACCESS read-write
	STATUS     current
	DESCRIPTION
		"This alarm is logged "
	::= { powerSupplyEntry 5 }

powerSupplyFault  OBJECT-TYPE
	SYNTAX     TruthValue
	MAX-ACCESS read-write
	STATUS     current
	DESCRIPTION
		"This alarm sum to Fault alarm "
	::= { powerSupplyEntry 6 }

powerSupplyWarning  OBJECT-TYPE
	SYNTAX     TruthValue
	MAX-ACCESS read-write
	STATUS     current
	DESCRIPTION
		"This alarm sum to Warning alarm "
	::= { powerSupplyEntry 7 }

powerSupplyLed  OBJECT-TYPE
	SYNTAX     TruthValue
	MAX-ACCESS read-write
	STATUS     current
	DESCRIPTION
		"This alarm modify LED status "
	::= { powerSupplyEntry 8 }

powerSupply1p1  OBJECT-TYPE
	SYNTAX     TruthValue
	MAX-ACCESS read-write
	STATUS     current
	DESCRIPTION
		"This alarm is a switching cause"
	::= { powerSupplyEntry 9 }

powerSupplyExt1  OBJECT-TYPE
	SYNTAX     TruthValue
	MAX-ACCESS read-write
	STATUS     current
	DESCRIPTION
		"This alarm sum to External relay 1 "
	::= { powerSupplyEntry 10 }

powerSupplyExt2  OBJECT-TYPE
	SYNTAX     TruthValue
	MAX-ACCESS read-write
	STATUS     current
	DESCRIPTION
		"This alarm sum to External delay 2 "
	::= { powerSupplyEntry 11 }

powerSupplyTrap  OBJECT-TYPE
	SYNTAX     TruthValue
	MAX-ACCESS read-write
	STATUS     current
	DESCRIPTION
		"This alarm generates SNMP trap "
	::= { powerSupplyEntry 12 }

powerSupplyDD  OBJECT-TYPE
	SYNTAX     TruthValue
	MAX-ACCESS read-write
	STATUS     current
	DESCRIPTION
		"This alarm is a switching cause"
	::= { powerSupplyEntry 13 }

powerSupplyTrapHysteresis  OBJECT-TYPE
	SYNTAX     Unsigned32(0..255)
	MAX-ACCESS read-write
	STATUS     current
	DESCRIPTION
		"Hysteresis trap"
	::= { powerSupplyEntry 14 }

dcInputTable  OBJECT-TYPE
	SYNTAX SEQUENCE OF DcInputEntry
	MAX-ACCESS not-accessible
	STATUS     current
	DESCRIPTION
		"Power supply alarm table "
	::= { alarmsConfiguration 85 }

dcInputEntry  OBJECT-TYPE
	SYNTAX 	DcInputEntry
	MAX-ACCESS not-accessible
	STATUS     current
	DESCRIPTION
		"DC Input alarm table entry"
	INDEX { dcInputIndex }
	::= { dcInputTable 1 }

DcInputEntry ::= SEQUENCE {
	dcInputIndex
		Unsigned32,
	dcInputAlarmName
		DisplayString,
	dcInputAlarmStatus
		AlarmStatus,
	dcInputOn
		TruthValue,
	dcInputLog
		TruthValue,
	dcInputFault
		TruthValue,
	dcInputWarning
		TruthValue,
	dcInputLed
		TruthValue,
	dcInput1p1
		TruthValue,
	dcInputExt1
		TruthValue,
	dcInputExt2
		TruthValue,
	dcInputTrap
		TruthValue,
	dcInputDD
		TruthValue,
	dcInputTrapHysteresis
		Unsigned32
}

dcInputIndex  OBJECT-TYPE
	SYNTAX     Unsigned32 (1..3)
	MAX-ACCESS not-accessible
	STATUS     current
	DESCRIPTION
		"DC Input Alarm Index"
	::= { dcInputEntry 1 }

dcInputAlarmName  OBJECT-TYPE
	SYNTAX     DisplayString
	MAX-ACCESS read-only
	STATUS     current
	DESCRIPTION
		"DC Input alarm name "
	::= { dcInputEntry 2 }

dcInputAlarmStatus  OBJECT-TYPE
	SYNTAX     AlarmStatus
	MAX-ACCESS read-only
	STATUS     current
	DESCRIPTION
		"Alarm"
	::= { dcInputEntry 3 }

dcInputOn  OBJECT-TYPE
	SYNTAX     TruthValue
	MAX-ACCESS read-write
	STATUS     current
	DESCRIPTION
		"On/Off alarm viwer.

		When you set off this amlarm, it will be on 3th status, so alarm will be on unknown status."
	::= { dcInputEntry 4 }

dcInputLog  OBJECT-TYPE
	SYNTAX     TruthValue
	MAX-ACCESS read-write
	STATUS     current
	DESCRIPTION
		"This alarm is logged "
	::= { dcInputEntry 5 }

dcInputFault  OBJECT-TYPE
	SYNTAX     TruthValue
	MAX-ACCESS read-write
	STATUS     current
	DESCRIPTION
		"This alarm sum to Fault alarm "
	::= { dcInputEntry 6 }

dcInputWarning  OBJECT-TYPE
	SYNTAX     TruthValue
	MAX-ACCESS read-write
	STATUS     current
	DESCRIPTION
		"This alarm sum to Warning alarm "
	::= { dcInputEntry 7 }

dcInputLed  OBJECT-TYPE
	SYNTAX     TruthValue
	MAX-ACCESS read-write
	STATUS     current
	DESCRIPTION
		"This alarm modify LED status "
	::= { dcInputEntry 8 }

dcInput1p1  OBJECT-TYPE
	SYNTAX     TruthValue
	MAX-ACCESS read-write
	STATUS     current
	DESCRIPTION
		"This alarm is a switching cause"
	::= { dcInputEntry 9 }

dcInputExt1  OBJECT-TYPE
	SYNTAX     TruthValue
	MAX-ACCESS read-write
	STATUS     current
	DESCRIPTION
		"This alarm sum to External relay 1 "
	::= { dcInputEntry 10 }

dcInputExt2  OBJECT-TYPE
	SYNTAX     TruthValue
	MAX-ACCESS read-write
	STATUS     current
	DESCRIPTION
		"This alarm sum to External delay 2 "
	::= { dcInputEntry 11 }

dcInputTrap  OBJECT-TYPE
	SYNTAX     TruthValue
	MAX-ACCESS read-write
	STATUS     current
	DESCRIPTION
		"This alarm generates SNMP trap "
	::= { dcInputEntry 12 }

dcInputDD  OBJECT-TYPE
	SYNTAX     TruthValue
	MAX-ACCESS read-write
	STATUS     current
	DESCRIPTION
		"This alarm is a switching cause"
	::= { dcInputEntry 13 }

dcInputTrapHysteresis  OBJECT-TYPE
	SYNTAX     Unsigned32(0..255)
	MAX-ACCESS read-write
	STATUS     current
	DESCRIPTION
		"Hysteresis trap"
	::= { dcInputEntry 14 }

redundancySysTable  OBJECT-TYPE
	SYNTAX SEQUENCE OF RedundancySysEntry
	MAX-ACCESS not-accessible
	STATUS     current
	DESCRIPTION
		"Redundancy System alarm table "
	::= { alarmsConfiguration 90 }

redundancySysEntry  OBJECT-TYPE
	SYNTAX 	RedundancySysEntry
	MAX-ACCESS not-accessible
	STATUS     current
	DESCRIPTION
		"Redundancy System alarm table entry"
	INDEX { redundancySysIndex }
	::= { redundancySysTable 1 }

RedundancySysEntry ::= SEQUENCE {
	redundancySysIndex
		Unsigned32,
	redundancySysAlarmName
		DisplayString,
	redundancySysAlarmStatus
		AlarmStatus,
	redundancySysOn
		TruthValue,
	redundancySysLog
		TruthValue,
	redundancySysFault
		TruthValue,
	redundancySysWarning
		TruthValue,
	redundancySysLed
		TruthValue,
	redundancySys1p1
		TruthValue,
	redundancySysExt1
		TruthValue,
	redundancySysExt2
		TruthValue,
	redundancySysTrap
		TruthValue,
	redundancySysDD
		TruthValue,
	redundancySysTrapHysteresis
		Unsigned32
}

redundancySysIndex  OBJECT-TYPE
	SYNTAX     Unsigned32 (1..3)
	MAX-ACCESS not-accessible
	STATUS     current
	DESCRIPTION
		"Redundancy System Alarm Index"
	::= { redundancySysEntry 1 }

redundancySysAlarmName  OBJECT-TYPE
	SYNTAX     DisplayString
	MAX-ACCESS read-only
	STATUS     current
	DESCRIPTION
		"Redundancy System alarm name"
	::= { redundancySysEntry 2 }

redundancySysAlarmStatus  OBJECT-TYPE
	SYNTAX     AlarmStatus
	MAX-ACCESS read-only
	STATUS     current
	DESCRIPTION
		"Alarm"
	::= { redundancySysEntry 3 }

redundancySysOn  OBJECT-TYPE
	SYNTAX     TruthValue
	MAX-ACCESS read-write
	STATUS     current
	DESCRIPTION
		"On/Off alarm viwer.

		When you set off this amlarm, it will be on 3th status, so alarm will be on unknown status."
	::= { redundancySysEntry 4 }

redundancySysLog  OBJECT-TYPE
	SYNTAX     TruthValue
	MAX-ACCESS read-write
	STATUS     current
	DESCRIPTION
		"This alarm is logged "
	::= { redundancySysEntry 5 }

redundancySysFault  OBJECT-TYPE
	SYNTAX     TruthValue
	MAX-ACCESS read-write
	STATUS     current
	DESCRIPTION
		"This alarm sum to Fault alarm "
	::= { redundancySysEntry 6 }

redundancySysWarning  OBJECT-TYPE
	SYNTAX     TruthValue
	MAX-ACCESS read-write
	STATUS     current
	DESCRIPTION
		"This alarm sum to Warning alarm "
	::= { redundancySysEntry 7 }

redundancySysLed  OBJECT-TYPE
	SYNTAX     TruthValue
	MAX-ACCESS read-write
	STATUS     current
	DESCRIPTION
		"This alarm modify LED status "
	::= { redundancySysEntry 8 }

redundancySys1p1  OBJECT-TYPE
	SYNTAX     TruthValue
	MAX-ACCESS read-write
	STATUS     current
	DESCRIPTION
		"This alarm is a switching cause"
	::= { redundancySysEntry 9 }

redundancySysExt1  OBJECT-TYPE
	SYNTAX     TruthValue
	MAX-ACCESS read-write
	STATUS     current
	DESCRIPTION
		"This alarm sum to External relay 1 "
	::= { redundancySysEntry 10 }

redundancySysExt2  OBJECT-TYPE
	SYNTAX     TruthValue
	MAX-ACCESS read-write
	STATUS     current
	DESCRIPTION
		"This alarm sum to External delay 2 "
	::= { redundancySysEntry 11 }

redundancySysTrap  OBJECT-TYPE
	SYNTAX     TruthValue
	MAX-ACCESS read-write
	STATUS     current
	DESCRIPTION
		"This alarm generates SNMP trap "
	::= { redundancySysEntry 12 }

redundancySysDD  OBJECT-TYPE
	SYNTAX     TruthValue
	MAX-ACCESS read-write
	STATUS     current
	DESCRIPTION
		"This alarm is a switching cause"
	::= { redundancySysEntry 13 }

redundancySysTrapHysteresis  OBJECT-TYPE
	SYNTAX     Unsigned32(0..255)
	MAX-ACCESS read-write
	STATUS     current
	DESCRIPTION
		"Hysteresis trap"
	::= { redundancySysEntry 14 }

eventsTable  OBJECT-TYPE
	SYNTAX SEQUENCE OF EventsEntry
	MAX-ACCESS not-accessible
	STATUS     current
	DESCRIPTION
		"Events table "
	::= { eventsConfiguration 1 }

eventsEntry  OBJECT-TYPE
	SYNTAX 	EventsEntry
	MAX-ACCESS not-accessible
	STATUS     current
	DESCRIPTION
		"Events entry "
	INDEX { eventsIndex }
	::= { eventsTable 1 }

EventsEntry ::= SEQUENCE {
	eventsIndex
		Unsigned32,
	eventName
		DisplayString,
	eventOn
		TruthValue,
	eventLog
		TruthValue,
	eventTrap
		TruthValue
}

eventsIndex  OBJECT-TYPE
	SYNTAX     Unsigned32 (1..2)
	MAX-ACCESS not-accessible
	STATUS     current
	DESCRIPTION
		"Event Index"
	::= { eventsEntry 1 }

eventName  OBJECT-TYPE
	SYNTAX     DisplayString
	MAX-ACCESS read-only
	STATUS     current
	DESCRIPTION
		"Event Name"
	::= { eventsEntry 2 }

eventOn  OBJECT-TYPE
	SYNTAX     TruthValue
	MAX-ACCESS read-write
	STATUS     current
	DESCRIPTION
		"Event On/Off viwer.

		"
	::= { eventsEntry 3 }

eventLog  OBJECT-TYPE
	SYNTAX     TruthValue
	MAX-ACCESS read-write
	STATUS     current
	DESCRIPTION
		"Logging event"
	::= { eventsEntry 4 }

eventTrap  OBJECT-TYPE
	SYNTAX     TruthValue
	MAX-ACCESS read-write
	STATUS     current
	DESCRIPTION
		"Trap event"
	::= { eventsEntry 5 }

input01Status  OBJECT-TYPE
	SYNTAX     INTEGER {
		open (0),
		closed (1),
		redundancy (2)
	}
	MAX-ACCESS read-only
	STATUS     current
	DESCRIPTION
		"Input #1 status

		close/opened/redundancy-use"
	::= { input01 1 }

input01Description  OBJECT-TYPE
	SYNTAX     OCTET STRING (SIZE(0..16))
	MAX-ACCESS read-write
	STATUS     current
	DESCRIPTION
		"Input #1 Description for tagging changes"
	::= { input01 2 }

input01StandByStatus  OBJECT-TYPE
	SYNTAX     INTEGER {
		open (0),
		closed (1)
	}
	MAX-ACCESS read-write
	STATUS     current
	DESCRIPTION
		"Input #1 Stand-by status"
	::= { input01 3 }

input01Mode  OBJECT-TYPE
	SYNTAX     INTEGER {
		level (0),
		pulse (1),
		interlock (2),
		systemReset (3),
		minimumPower (4)
	}
	MAX-ACCESS read-write
	STATUS     current
	DESCRIPTION
		"Input #1 Mode

		Level / Pulse / Interlock"
	::= { input01 4 }

input01Duration  OBJECT-TYPE
	SYNTAX     Unsigned32 (1..99)
	UNITS 	"s"
	MAX-ACCESS read-write
	STATUS     current
	DESCRIPTION
		"Input #1 Duration for pulse detection"
	::= { input01 5 }

input02Status  OBJECT-TYPE
	SYNTAX     INTEGER {
		open (0),
		closed (1),
		redundancy (2)
	}
	MAX-ACCESS read-only
	STATUS     current
	DESCRIPTION
		"Input #2 status

		close/opened/redundancy-use"
	::= { input02 1 }

input02Description  OBJECT-TYPE
	SYNTAX     OCTET STRING (SIZE(0..16))
	MAX-ACCESS read-write
	STATUS     current
	DESCRIPTION
		"Input #2 Description for tagging changes"
	::= { input02 2 }

input02StandByStatus  OBJECT-TYPE
	SYNTAX     INTEGER {
		open (0),
		closed (1)
	}
	MAX-ACCESS read-write
	STATUS     current
	DESCRIPTION
		"Input #2 Stand-by status"
	::= { input02 3 }

input02Mode  OBJECT-TYPE
	SYNTAX     INTEGER {
		level (0),
		pulse (1),
		interlock (2),
		systemReset (3),
		minimumPower (4)
	}
	MAX-ACCESS read-write
	STATUS     current
	DESCRIPTION
		"Input #2 Mode

		Level / Pulse / Interlock"
	::= { input02 4 }

input02Duration  OBJECT-TYPE
	SYNTAX     Unsigned32 (1..99)
	UNITS 	"s"
	MAX-ACCESS read-write
	STATUS     current
	DESCRIPTION
		"Input #2 Duration for pulse detection"
	::= { input02 5 }

output01Status  OBJECT-TYPE
	SYNTAX     INTEGER {
		open (0),
		closed (1),
		redundancy (2)
	}
	MAX-ACCESS read-only
	STATUS     current
	DESCRIPTION
		"Output #1 status

		close/opened/redundancy-use"
	::= { output01 1 }

output01Description  OBJECT-TYPE
	SYNTAX     OCTET STRING (SIZE(0..30))
	MAX-ACCESS read-write
	STATUS     current
	DESCRIPTION
		"Output #1 Description for tagging changes"
	::= { output01 2 }

output01StandByStatus  OBJECT-TYPE
	SYNTAX     INTEGER {
		open (0),
		closed (1)
	}
	MAX-ACCESS read-write
	STATUS     current
	DESCRIPTION
		"Output #1 Stand-by status"
	::= { output01 3 }

output01Mode  OBJECT-TYPE
	SYNTAX     INTEGER {
		level (0),
		pulse (1)
	}
	MAX-ACCESS read-write
	STATUS     current
	DESCRIPTION
		"Output #1 Mode

		Level / Pulse"
	::= { output01 4 }

output01Duration  OBJECT-TYPE
	SYNTAX     Unsigned32 (1..99)
	UNITS 	"s"
	MAX-ACCESS read-write
	STATUS     current
	DESCRIPTION
		"Output #1 Duration for pulse detection"
	::= { output01 5 }

output02Status  OBJECT-TYPE
	SYNTAX     INTEGER {
		open (0),
		closed (1),
		redundancy (2)
	}
	MAX-ACCESS read-only
	STATUS     current
	DESCRIPTION
		"Output Input #2 status

		close/opened/redundancy-use"
	::= { output02 1 }

output02Description  OBJECT-TYPE
	SYNTAX     OCTET STRING (SIZE(0..30))
	MAX-ACCESS read-write
	STATUS     current
	DESCRIPTION
		"Output #2 Description for tagging changes"
	::= { output02 2 }

output02StandByStatus  OBJECT-TYPE
	SYNTAX     INTEGER {
		open (0),
		closed (1)
	}
	MAX-ACCESS read-write
	STATUS     current
	DESCRIPTION
		"Output #2 Stand-by status"
	::= { output02 3 }

output02Mode  OBJECT-TYPE
	SYNTAX     INTEGER {
		level (0),
		pulse (1)
	}
	MAX-ACCESS read-write
	STATUS     current
	DESCRIPTION
		"Output #2 Mode

		Level / Pulse"
	::= { output02 4 }

output02Duration  OBJECT-TYPE
	SYNTAX     Unsigned32 (1..99)
	UNITS 	"s"
	MAX-ACCESS read-write
	STATUS     current
	DESCRIPTION
		"Output #2 Duration for pulse generation"
	::= { output02 5 }

readCommunity1  OBJECT-TYPE
	SYNTAX     DisplayString
	MAX-ACCESS read-write
	STATUS     current
	DESCRIPTION
		"Read community 1"
	::= { snmp 1 }

writeCommunity1  OBJECT-TYPE
	SYNTAX     DisplayString
	MAX-ACCESS read-write
	STATUS     current
	DESCRIPTION
		"Read/Write Community 2"
	::= { snmp 2 }

fastTrapSync  OBJECT-TYPE
	SYNTAX     NullApply
	MAX-ACCESS read-write
	STATUS     current
	DESCRIPTION
		"Re-send new actived alarms (only alarms enabled for sending traps) "
	::= { snmp 4 }

enableAuthenTraps  OBJECT-TYPE
	SYNTAX     TruthValue
	MAX-ACCESS read-write
	STATUS     current
	DESCRIPTION
		"Setting this variable to 1enables generation of authentication failure traps.

		True = authentication failure traps enabled
		False = authentication failure traps disabled"
	::= { snmp 5 }

trapKeepaliveEnable  OBJECT-TYPE
	SYNTAX     TruthValue
	MAX-ACCESS read-write
	STATUS     current
	DESCRIPTION
		"Enable keepalive trap"
	::= { snmp 6 }

trapKeepalive  OBJECT-TYPE
	SYNTAX     Unsigned32 (5..43200)
	UNITS 	"seconds"
	MAX-ACCESS read-write
	STATUS     current
	DESCRIPTION
		"The agent will send one trap to all sinks after this timeout"
	::= { snmp 7 }

sendTestTrap  OBJECT-TYPE
	SYNTAX     NullApply
	MAX-ACCESS read-write
	STATUS     current
	DESCRIPTION
		"Send an trap for testing sinks"
	::= { snmp 8 }

lastUpdate  OBJECT-TYPE
	SYNTAX     DisplayString (SIZE(12))
	MAX-ACCESS read-only
	STATUS     current
	DESCRIPTION
		"LAST-UPDATE MIB value"
	::= { snmp 9 }

readCommunity2  OBJECT-TYPE
	SYNTAX     DisplayString
	MAX-ACCESS read-write
	STATUS     current
	DESCRIPTION
		"Read community 2"
	::= { snmp 10 }

writeCommunity2  OBJECT-TYPE
	SYNTAX     DisplayString
	MAX-ACCESS read-write
	STATUS     current
	DESCRIPTION
		"Read/Write community 2"
	::= { snmp 11 }

trapsLocalMode  OBJECT-TYPE
	SYNTAX     TruthValue
	MAX-ACCESS read-write
	STATUS     current
	DESCRIPTION
		"Send traps in local mode"
	::= { snmp 15 }

trapsInitialStatus  OBJECT-TYPE
	SYNTAX     TruthValue
	MAX-ACCESS read-write
	STATUS     current
	DESCRIPTION
		"Send initial traps"
	::= { snmp 16 }

sendAllTraps  OBJECT-TYPE
	SYNTAX     NullApply
	MAX-ACCESS read-write
	STATUS     current
	DESCRIPTION
		"Send all alarms status traps"
	::= { snmp 17 }


trapSinkTable  OBJECT-TYPE
	SYNTAX SEQUENCE OF TrapSinkEntry
	MAX-ACCESS not-accessible
	STATUS     current
	DESCRIPTION
		"Table for trapsinks configuration"
	::= { snmp 20 }

trapSinkEntry  OBJECT-TYPE
	SYNTAX 	TrapSinkEntry
	MAX-ACCESS not-accessible
	STATUS     current
	DESCRIPTION
		"Entry for a trapsink"
	INDEX { trapSinkIndex }
	::= { trapSinkTable 1 }

TrapSinkEntry ::= SEQUENCE {
	trapSinkIndex
		Unsigned32,
	trapSinkEnable
		TruthValue,
	trapSinkVersion
		INTEGER,
	trapSinkIpAddress
		IpAddress,
	trapSinkPort
		Unsigned32,
	trapSinkInformTimeout
		Unsigned32,
	trapSinkInformRetry
		Unsigned32,
	trapSinkCommunity
		DisplayString
}

trapSinkIndex  OBJECT-TYPE
	SYNTAX     Unsigned32 (1..4)
	MAX-ACCESS not-accessible
	STATUS     current
	DESCRIPTION
		"Index trap sink"
	::= { trapSinkEntry 1 }

trapSinkEnable  OBJECT-TYPE
	SYNTAX     TruthValue
	MAX-ACCESS read-write
	STATUS     current
	DESCRIPTION
		"Enable traps sink "
	::= { trapSinkEntry 2 }

trapSinkVersion  OBJECT-TYPE
	SYNTAX     INTEGER {
		v1Trap (1),
		v2Trap (2),
		v2Inform (3)
	}
	MAX-ACCESS read-write
	STATUS     current
	DESCRIPTION
		"SNMP version of sent trap"
	::= { trapSinkEntry 3 }

trapSinkIpAddress  OBJECT-TYPE
	SYNTAX     IpAddress
	MAX-ACCESS read-write
	STATUS     current
	DESCRIPTION
		"The IP address of SNMP Manager to send traps"
	::= { trapSinkEntry 4 }

trapSinkPort  OBJECT-TYPE
	SYNTAX     Unsigned32 (1..65535)
	MAX-ACCESS read-write
	STATUS     current
	DESCRIPTION
		"The port where the SNMP Manager are watting for traps"
	::= { trapSinkEntry 5 }

trapSinkInformTimeout  OBJECT-TYPE
	SYNTAX     Unsigned32
	MAX-ACCESS read-write
	STATUS     current
	DESCRIPTION
		"Only for informs.
		Timeout for resend the inform if ack is not received."
	::= { trapSinkEntry 6 }

trapSinkInformRetry  OBJECT-TYPE
	SYNTAX     Unsigned32
	MAX-ACCESS read-write
	STATUS     current
	DESCRIPTION
		"Only for informs.
		Number o retries for send inform while ack is not received"
	::= { trapSinkEntry 7 }

trapSinkCommunity  OBJECT-TYPE
	SYNTAX     DisplayString (SIZE(1..16))
	MAX-ACCESS read-write
	STATUS     current
	DESCRIPTION
		"Community sink traps"
	::= { trapSinkEntry 8 }

partNumber  OBJECT-TYPE
	SYNTAX     DisplayString (SIZE(12))
	MAX-ACCESS read-only
	STATUS     current
	DESCRIPTION
		"Part number"
	::= { deviceInfo 1 }

serialNumber  OBJECT-TYPE
	SYNTAX     DisplayString (SIZE(12))
	MAX-ACCESS read-only
	STATUS     current
	DESCRIPTION
		"Serial number"
	::= { deviceInfo 2 }

softwareVersion  OBJECT-TYPE
	SYNTAX     DisplayString (SIZE(16))
	MAX-ACCESS read-only
	STATUS     current
	DESCRIPTION
		"Software version"
	::= { deviceInfo 3 }

softwareId  OBJECT-TYPE
	SYNTAX     Unsigned32
	MAX-ACCESS read-only
	STATUS     current
	DESCRIPTION
		"Software ID"
	::= { deviceInfo 4 }

ctrlBoard  OBJECT-TYPE
	SYNTAX     OptionHw
	MAX-ACCESS read-only
	STATUS     current
	DESCRIPTION
		"Control Board"
	::= { hardwareBasis 1 }

ctrlCBoard  OBJECT-TYPE
	SYNTAX     OptionHw
	MAX-ACCESS read-only
	STATUS     current
	DESCRIPTION
		"Control C Board"
	::= { hardwareBasis 2 }

ctrlMBoard  OBJECT-TYPE
	SYNTAX     OptionHw
	MAX-ACCESS read-only
	STATUS     current
	DESCRIPTION
		"Control M Board"
	::= { hardwareBasis 3 }

signalBoardGf  OBJECT-TYPE
	SYNTAX     OptionHw
	MAX-ACCESS read-only
	STATUS     current
	DESCRIPTION
		"Signal Board Gap Filler"
	::= { hardwareBasis 11 }

signalBoardTx  OBJECT-TYPE
	SYNTAX     OptionHw
	MAX-ACCESS read-only
	STATUS     current
	DESCRIPTION
		"Signal Board Transmitter"
	::= { hardwareBasis 12 }

extraDigitalDacModulator  OBJECT-TYPE
	SYNTAX     OptionHw
	MAX-ACCESS read-only
	STATUS     current
	DESCRIPTION
		"Extra Digital DAC modulator"
	::= { hardwareBasis 13 }

satelliteBoard  OBJECT-TYPE
	SYNTAX     OptionHw
	MAX-ACCESS read-only
	STATUS     current
	DESCRIPTION
		"Satellite Board"
	::= { hardwareBasis 14 }

dabBoard  OBJECT-TYPE
	SYNTAX     OptionHw
	MAX-ACCESS read-only
	STATUS     current
	DESCRIPTION
		"DAB Board"
	::= { hardwareBasis 15 }

dabGfBoard  OBJECT-TYPE
	SYNTAX     OptionHw
	MAX-ACCESS read-only
	STATUS     current
	DESCRIPTION
		"DAB GF Board"
	::= { hardwareBasis 16 }

dabEti2  OBJECT-TYPE
	SYNTAX     OptionSw 
	MAX-ACCESS read-only
	STATUS     current
	DESCRIPTION
		"ETI 2 Input"
	::= { hardwareBasis 17 }

terrestialReceiver1Board  OBJECT-TYPE
	SYNTAX     OptionHw
	MAX-ACCESS read-only
	STATUS     current
	DESCRIPTION
		"Terrestial Receiver 1"
	::= { hardwareBasis 21 }

terrestialReceiver2Board  OBJECT-TYPE
	SYNTAX     OptionHw
	MAX-ACCESS read-only
	STATUS     current
	DESCRIPTION
		"Terrestial Receiver 2"
	::= { hardwareBasis 22 }

satelliteReceiver1Board  OBJECT-TYPE
	SYNTAX     OptionHw
	MAX-ACCESS read-only
	STATUS     current
	DESCRIPTION
		"Satellite Receiver 1"
	::= { hardwareBasis 23 }

satelliteReceiver2Board  OBJECT-TYPE
	SYNTAX     OptionHw
	MAX-ACCESS read-only
	STATUS     current
	DESCRIPTION
		"Satellite Receiver 2"
	::= { hardwareBasis 24 }

ctrlBusInterface  OBJECT-TYPE
	SYNTAX     OptionHw
	MAX-ACCESS read-only
	STATUS     current
	DESCRIPTION
		"Control Bus Interface"
	::= { hardwareBasis 25 }

onePlusOneRedundancy  OBJECT-TYPE
	SYNTAX     OptionHw
	MAX-ACCESS read-only
	STATUS     current
	DESCRIPTION
		"1+1 Redundancy system"
	::= { hardwareBasis 31 }

--coaxialRelay  OBJECT-TYPE
--	SYNTAX     INTEGER {
--		interlock (0),
--		noInterlock (1)
--	}
--	MAX-ACCESS read-write
--	STATUS     current
--	DESCRIPTION
--		"Coaxial relay"
--	::= { serviceInstallHwSw 35 }

externalFeedback  OBJECT-TYPE
	SYNTAX     OptionHw
	MAX-ACCESS read-only
	STATUS     current
	DESCRIPTION
		"External feedback"
	::= { hardwareBasis 41 }

relay1p1Interface  OBJECT-TYPE
	SYNTAX     INTEGER {
		db9 (25),
		db25 (26),
		notConfigured (254),
		error (255)
	}
	MAX-ACCESS read-only
	STATUS     current
	DESCRIPTION
		"1+1 relay inteface"
	::= { hardwareBasis 42 }

i2o8Interface  OBJECT-TYPE
	SYNTAX     OptionHw
	MAX-ACCESS read-only
	STATUS     current
	DESCRIPTION
		"I/O 2/8 interface"
	::= { hardwareBasis 43 }

externalInterlock  OBJECT-TYPE
	SYNTAX     OptionHw
	MAX-ACCESS read-only
	STATUS     current
	DESCRIPTION
		"External interlock"
	::= { hardwareBasis 44 }

i4o10Interface  OBJECT-TYPE
	SYNTAX     OptionHw
	MAX-ACCESS read-only
	STATUS     current
	DESCRIPTION
		"I/O 4/10 interface"
	::= { hardwareBasis 45 }

dcConnector  OBJECT-TYPE
	SYNTAX     OptionHw
	MAX-ACCESS read-only
	STATUS     current
	DESCRIPTION
		"DC Connector"
	::= { hardwareBasis 46 }

rfBooster  OBJECT-TYPE
	SYNTAX     OptionHw
	MAX-ACCESS read-only
	STATUS     current
	DESCRIPTION
		"RF booster"
	::= { hardwareBasis 47 }

amplifierHw  OBJECT-TYPE
	SYNTAX     INTEGER {
		pw1A (0),
		pw1B (1),
		pw1C (2),
		pw1D (3),
		pw1E (4),
		pw2A (5),
		pw2B (6),
		pw2C (7),
		pw2D (8),
		pw2E (9),
		pw3A (10),
		pw3B (11),
		pw3C (12),
		pw3D (13),
		pw3E (14),
		pwEXT (15),
		pwNONE (16),
		pw1F (17),
		pw1G (18),
		pw1H (19),
		pw21 (20),
		pw22 (21),
		pw23 (22),
		pw24 (23),
		pw25 (24),
		pw26 (25),
		pw27 (26),
		pw28 (27),
		pw29 (28),
		pw30 (29),
		pw31 (30),
		pw32 (31),
		error (32)
	}
	MAX-ACCESS read-only
	STATUS     current
	DESCRIPTION
		"Power Amplifier Board"
	::= { hardwareBasis 50 }

amplifierHwRevision  OBJECT-TYPE
	SYNTAX     INTEGER {
		ref0 (0),
		ref1 (1)
	}
	MAX-ACCESS read-only
	STATUS     current
	DESCRIPTION
		"Amplifier HW Rev."
	::= { hardwareBasis 52 }

amplifierStageInfoTable  OBJECT-TYPE
	SYNTAX SEQUENCE OF AmplifierStageInfoEntry
	MAX-ACCESS not-accessible
	STATUS     current
	DESCRIPTION
		"Table for amplifier stages information"
	::= { hardwareBasis 60 }

amplifierStageInfoEntry  OBJECT-TYPE
	SYNTAX 	AmplifierStageInfoEntry
	MAX-ACCESS not-accessible
	STATUS     current
	DESCRIPTION
		"Entry for an amplifier stage information"
	INDEX { amplifierStageInfoIndex }
	::= { amplifierStageInfoTable   1 }

AmplifierStageInfoEntry ::= SEQUENCE {
	amplifierStageInfoIndex 
		Unsigned32,
	amplifierStageType
		INTEGER,
	amplifierStageSN
		OCTET STRING
}

amplifierStageInfoIndex   OBJECT-TYPE
	SYNTAX     Unsigned32 (1..4)
	MAX-ACCESS not-accessible
	STATUS     current
	DESCRIPTION
		"Index amplifier stage"
	::= { amplifierStageInfoEntry  1 }

amplifierStageType  OBJECT-TYPE
	SYNTAX     INTEGER {
		null (0),
		pw4A (1),
		pw4B (2),
		pw4C (3),
		pw4D (4),
		pw4E (5),
		pw4F (6)
	}
	MAX-ACCESS read-only
	STATUS     current
	DESCRIPTION
		"Amplifier Stage info"
	::= { amplifierStageInfoEntry 2 }

amplifierStageSN  OBJECT-TYPE
	SYNTAX    OCTET STRING 
	MAX-ACCESS read-only
	STATUS     current
	DESCRIPTION
		"Amplifier Stage Serial Number"
	::= { amplifierStageInfoEntry 3 }

gnssReceiverHw  OBJECT-TYPE
	SYNTAX     OptionHw
	MAX-ACCESS read-only
	STATUS     current
	DESCRIPTION
		"GNSS Board"
	::= { hardwareOptions 1 }

externalReferenceHw  OBJECT-TYPE
	SYNTAX     OptionHw
	MAX-ACCESS read-only
	STATUS     current
	DESCRIPTION
		"External reference Board"
	::= { hardwareOptions 2 }

redundantPsuHw  OBJECT-TYPE
	SYNTAX     OptionSw
	MAX-ACCESS read-only
	STATUS     current
	DESCRIPTION
		"Redundant PSU installation"
	::= { hardwareOptions 3 }

ocxoReferenceHw  OBJECT-TYPE
	SYNTAX     OptionHw
	MAX-ACCESS read-only
	STATUS     current
	DESCRIPTION
		"OCXO reference Board"
	::= { hardwareOptions 4 }

referenceHwSerialNumber  OBJECT-TYPE
	SYNTAX     DisplayString (SIZE(14))
	MAX-ACCESS read-only
	STATUS     current
	DESCRIPTION
		"Serial number"
	::= { hardwareOptions 7 }

rackCooling1Hw  OBJECT-TYPE
	SYNTAX     OptionHw
	MAX-ACCESS read-only
	STATUS     current
	DESCRIPTION
		"Rack cooling 1 Board"
	::= { hardwareOptions 10 }

rackCooling2Hw  OBJECT-TYPE
	SYNTAX     OptionHw
	MAX-ACCESS read-only
	STATUS     current
	DESCRIPTION
		"Rack cooling 2 Board"
	::= { hardwareOptions 11 }

rackCooling3Hw  OBJECT-TYPE
	SYNTAX     OptionHw
	MAX-ACCESS read-only
	STATUS     current
	DESCRIPTION
		"Rack cooling 3 Board"
	::= { hardwareOptions 12 }

rackCooling4Hw  OBJECT-TYPE
	SYNTAX     OptionHw
	MAX-ACCESS read-only
	STATUS     current
	DESCRIPTION
		"Rack cooling 4 Board"
	::= { hardwareOptions 13 }

asi1Matrix1Hw  OBJECT-TYPE
	SYNTAX     OptionHw
	MAX-ACCESS read-only
	STATUS     current
	DESCRIPTION
		"ASI 1 matrix 1 Board"
	::= { hardwareOptions 15 }

asi1Matrix2Hw  OBJECT-TYPE
	SYNTAX     OptionHw
	MAX-ACCESS read-only
	STATUS     current
	DESCRIPTION
		"ASI 1 matrix 2 Board"
	::= { hardwareOptions 16 }

asi2Matrix1Hw  OBJECT-TYPE
	SYNTAX     OptionHw
	MAX-ACCESS read-only
	STATUS     current
	DESCRIPTION
		"ASI 2 matrix 1 Board"
	::= { hardwareOptions 17 }

asi2Matrix2Hw  OBJECT-TYPE
	SYNTAX     OptionHw
	MAX-ACCESS read-only
	STATUS     current
	DESCRIPTION
		"ASI 2 matrix 2 Board"
	::= { hardwareOptions 18 }

rackCooling5Hw  OBJECT-TYPE
	SYNTAX     OptionHw
	MAX-ACCESS read-only
	STATUS     current
	DESCRIPTION
		"Rack cooling 5 Board"
	::= { hardwareOptions 20 }

rackCooling6Hw  OBJECT-TYPE
	SYNTAX     OptionHw
	MAX-ACCESS read-only
	STATUS     current
	DESCRIPTION
		"Rack cooling 6 Board"
	::= { hardwareOptions 21 }

rfMatrix1Hw  OBJECT-TYPE
	SYNTAX     OptionHw
	MAX-ACCESS read-only
	STATUS     current
	DESCRIPTION
		"RF matrix 1 Board"
	::= { hardwareOptions 22 }

rfMatrix2Hw  OBJECT-TYPE
	SYNTAX     OptionHw
	MAX-ACCESS read-only
	STATUS     current
	DESCRIPTION
		"RF matrix 2 Board"
	::= { hardwareOptions 23 }

rackCooling7Hw  OBJECT-TYPE
	SYNTAX     OptionHw
	MAX-ACCESS read-only
	STATUS     current
	DESCRIPTION
		"Rack cooling 7 Board"
	::= { hardwareOptions 24 }

eti1Matrix1Hw  OBJECT-TYPE
	SYNTAX     OptionHw
	MAX-ACCESS read-only
	STATUS     current
	DESCRIPTION
		"ETI 1 matrix 1 Board"
	::= { hardwareOptions 25 }

eti1Matrix2Hw  OBJECT-TYPE
	SYNTAX     OptionHw
	MAX-ACCESS read-only
	STATUS     current
	DESCRIPTION
		"ETI 1 matrix 2 Board"
	::= { hardwareOptions 26 }

eti2Matrix1Hw  OBJECT-TYPE
	SYNTAX     OptionHw
	MAX-ACCESS read-only
	STATUS     current
	DESCRIPTION
		"ETI 2 matrix 1 Board"
	::= { hardwareOptions 27 }

eti2Matrix2Hw  OBJECT-TYPE
	SYNTAX     OptionHw
	MAX-ACCESS read-only
	STATUS     current
	DESCRIPTION
		"ETI 2 matrix 2 Board"
	::= { hardwareOptions 28 }

snmpSw  OBJECT-TYPE
	SYNTAX     OptionSw
	MAX-ACCESS read-only
	STATUS     current
	DESCRIPTION
		"SNMP Software"
	::= { softwareOptions 1 }

dvbtSw  OBJECT-TYPE
	SYNTAX     OptionSw
	MAX-ACCESS read-only
	STATUS     current
	DESCRIPTION
		"DVB-T Software"
	::= { softwareOptions 2 }

dvbt2Sw  OBJECT-TYPE
	SYNTAX     OptionSw
	MAX-ACCESS read-only
	STATUS     current
	DESCRIPTION
		"DVB-T2 Software"
	::= { softwareOptions 3 }

isdbtSw  OBJECT-TYPE
	SYNTAX     OptionSw
	MAX-ACCESS read-only
	STATUS     current
	DESCRIPTION
		"ISDB-T Software"
	::= { softwareOptions 4 }

deecSw  OBJECT-TYPE
	SYNTAX     OptionSw
	MAX-ACCESS read-only
	STATUS     current
	DESCRIPTION
		"DEEC Software"
	::= { softwareOptions 5 }

isdbtRemuxSw  OBJECT-TYPE
	SYNTAX     OptionSw
	MAX-ACCESS read-only
	STATUS     current
	DESCRIPTION
		"REMUX Software"
	::= { softwareOptions 6 }

onePlusOneSw  OBJECT-TYPE
	SYNTAX     OptionSw
	MAX-ACCESS read-only
	STATUS     current
	DESCRIPTION
		"1+1 Software"
	::= { softwareOptions 7 }

dualDriveSw  OBJECT-TYPE
	SYNTAX     OptionSw
	MAX-ACCESS read-only
	STATUS     current
	DESCRIPTION
		"Dual Drive Software"
	::= { softwareOptions 8 }

atsc1Sw  OBJECT-TYPE
	SYNTAX     OptionSw
	MAX-ACCESS read-only
	STATUS     current
	DESCRIPTION
		"ATCS1"
	::= { softwareOptions 9 }

dabSw  OBJECT-TYPE
	SYNTAX     OptionSw
	MAX-ACCESS read-only
	STATUS     current
	DESCRIPTION
		"DAB"
	::= { softwareOptions 10 }

unlimitedPowerSw  OBJECT-TYPE
	SYNTAX     OptionSw
	MAX-ACCESS read-only
	STATUS     current
	DESCRIPTION
		"Unlimited Power"
	::= { softwareOptions 11 }

monitoringSw  OBJECT-TYPE
	SYNTAX     OptionSw
	MAX-ACCESS read-only
	STATUS     current
	DESCRIPTION
		"Monitoring"
	::= { softwareOptions 12 }

np1Sw  OBJECT-TYPE
	SYNTAX     OptionSw
	MAX-ACCESS read-only
	STATUS     current
	DESCRIPTION
		"N+1"
	::= { softwareOptions 13 }

bissDecription  OBJECT-TYPE
	SYNTAX     OptionSw
	MAX-ACCESS read-only
	STATUS     current
	DESCRIPTION
		"BISS Decription"
	::= { softwareOptions 14 }

btsDecompressionRma  OBJECT-TYPE
	SYNTAX     OptionSw
	MAX-ACCESS read-only
	STATUS     current
	DESCRIPTION
		"BTS decompression RMA"
	::= { softwareOptions 15 }

systemReset  OBJECT-TYPE
	SYNTAX     NullApply
	MAX-ACCESS read-write
	STATUS     current
	DESCRIPTION
		"To perform a reinitialization of all memories/FPGAs and a reboot of
		operating system/application"
	::= { serviceReset 1 }

rfReset  OBJECT-TYPE
	SYNTAX     NullApply
	MAX-ACCESS read-write
	STATUS     current
	DESCRIPTION
		"To perfom a RF output restart in order to restore the device from an
		automatic self-protection"
	::= { serviceReset 2 }

inputStatusCalibration  OBJECT-TYPE
	SYNTAX     INTEGER {
		noCalibrated (0),
		recalibratedChannel (1)
	}
	MAX-ACCESS read-only
	STATUS     current
	DESCRIPTION
		"Input calibration status"
	::= { inputCalibration 1 }

cancelInputCalibration  OBJECT-TYPE
	SYNTAX     NullApply
	MAX-ACCESS read-write
	STATUS     obsolete
	DESCRIPTION
		"Cancel input calibration"
	::= { inputCalibration 2 }

inputLevelMeasureCalibration  OBJECT-TYPE
	SYNTAX     Integer32 (-85..-15)
	UNITS 	"dBm"
	MAX-ACCESS read-write
	STATUS     current
	DESCRIPTION
		"1.- Connect the power meter to RF output port
		2.- Set the power displayed at power meter and set that value
		 "
	::= { inputCalibration 3 }

powerStatusCalibration  OBJECT-TYPE
	SYNTAX     INTEGER {
		noCalibrated (0),
		recalibratedChannel (1)
	}
	MAX-ACCESS read-only
	STATUS     current
	DESCRIPTION
		"Power calibration status"
	::= { powerCalibration 1 }

powerLevelMeasureCalibration  OBJECT-TYPE
	SYNTAX     OCTET STRING (SIZE(1..5))
	UNITS 	"dBm"
	MAX-ACCESS read-write
	STATUS     current
	DESCRIPTION
		"1.- Connect the power meter to RF output port
		2.- Set the power displayed at power meter and set that value

		The value must be 0..350 in 0.5 step"
	::= { powerCalibration 3 }

automaticRfPhaseAdjustment  OBJECT-TYPE
	SYNTAX     NullApply
	MAX-ACCESS read-write
	STATUS     current
	DESCRIPTION
		"To perform an automatic RF phase adjustment of amplifier stages"
	::= { phaseRf 5 }

linearStatusPrecorrection  OBJECT-TYPE
	SYNTAX     INTEGER {
		noCalibrated (0),
		calibratedBeforeBPF (1),
		calibratedAfterBPF (2)
	}
	MAX-ACCESS read-only
	STATUS     current
	DESCRIPTION
		"Linear precorrection status"
	::= { linearPrecorrection 1 }

startLinearPrecorrectionBBPF  OBJECT-TYPE
	SYNTAX     NullApply
	MAX-ACCESS read-write
	STATUS     current
	DESCRIPTION
		"Start a linear precorrection. Before Bypass Filter"
	::= { linearPrecorrection 2 }

startLinearPrecorrectionABPF  OBJECT-TYPE
	SYNTAX     NullApply
	MAX-ACCESS read-write
	STATUS     current
	DESCRIPTION
		"Start a linear precorrection. After Bypass Filter"
	::= { linearPrecorrection 3 }

nonLinearStatusPrecorrection  OBJECT-TYPE
	SYNTAX     INTEGER {
		noCalibrated (0),
		recalibratedChannel (1)
	}
	MAX-ACCESS read-only
	STATUS     current
	DESCRIPTION
		"Non-linear precorrection status"
	::= { nonLinearPrecorrection 1 }

cancelNonLinearPrecorrection  OBJECT-TYPE
	SYNTAX     NullApply
	MAX-ACCESS read-write
	STATUS     current
	DESCRIPTION
		"Remove non linear optimization"
	::= { nonLinearPrecorrection 2 }

startNonLinearPrecorrection  OBJECT-TYPE
	SYNTAX     NullApply
	MAX-ACCESS read-write
	STATUS     current
	DESCRIPTION
		"Start a new non-linear precorrection"
	::= { nonLinearPrecorrection 3 }

acApparentPower  OBJECT-TYPE
	SYNTAX     DisplayString
	UNITS	"VA"
	MAX-ACCESS read-only
	STATUS     current
	DESCRIPTION
		"AC Apparent power"
	::= { efficiencyCalibration 5 }

acEfficiency  OBJECT-TYPE
	SYNTAX     DisplayString
	UNITS	"%"
	MAX-ACCESS read-only
	STATUS     current
	DESCRIPTION
		"AC Efficiency"
	::= { efficiencyCalibration 6 }

efficiencyStatusCalibration  OBJECT-TYPE
	SYNTAX     INTEGER {
		noCalibrated (0),
		recalibratedChannel (1)
	}
	MAX-ACCESS read-only
	STATUS     current
	DESCRIPTION
		"Efficiency calibration status"
	::= { efficiencyImprovement 1 }

cancelEfficiencyCalibration  OBJECT-TYPE
	SYNTAX     NullApply
	MAX-ACCESS read-write
	STATUS     current
	DESCRIPTION
		"Cancel efficienty calibration"
	::= { efficiencyImprovement 2 }

--efficiencyShoulderCalibration  OBJECT-TYPE
--    SYNTAX     NullApply
--    MAX-ACCESS read-write
--    STATUS     current
--    DESCRIPTION
--        "1.- Connect the power meter to RF output port
--        2.- Set the power displayed at power meter and set that value
--
--        The value must be 30..60 in 0.1 step"
--    ::= { efficiencyImprovement 3 }


efficiencyShoulderMeasure  OBJECT-TYPE
	SYNTAX     OCTET STRING (SIZE(1..4))
	UNITS 	"dB"
	MAX-ACCESS read-only
	STATUS     current
	DESCRIPTION
		"Measure shoulders"
	::= { efficiencyImprovement 4 }

efficiencyShoulderTarget  OBJECT-TYPE
	SYNTAX     OCTET STRING (SIZE(1..4))
	UNITS 	"dB"
	MAX-ACCESS read-write
	STATUS     current
	DESCRIPTION
		"Shoulder Target and start efficiency improvement."
	::= { efficiencyImprovement 5 }

efficiencyMerMeasure  OBJECT-TYPE
	SYNTAX     OCTET STRING (SIZE(1..4))
	UNITS 	"dB"
	MAX-ACCESS read-only
	STATUS     current
	DESCRIPTION
		"MER Measure"
	::= { efficiencyImprovement 7 }

efficiencyMerTarget  OBJECT-TYPE
	SYNTAX     OCTET STRING (SIZE(1..4))
	UNITS 	"dB"
	MAX-ACCESS read-write
	STATUS     current
	DESCRIPTION
		"MER Target (30.0 .. 60.0) and start efficiency improvement."
	::= { efficiencyImprovement 8 }

fan01Status  OBJECT-TYPE
	SYNTAX     INTEGER {
		standBy (0),
		running (1),
		failed (2)
	}
	MAX-ACCESS read-only
	STATUS     current
	DESCRIPTION
		"Current status fan:
		- Stand-by
		- Runing
		- Failed"
	::= { fan01 1 }

fan01OperatingTime  OBJECT-TYPE
	SYNTAX     Unsigned32
	UNITS 	"Hours"
	MAX-ACCESS read-only
	STATUS     current
	DESCRIPTION
		"Total operating time of this fan (hours)"
	::= { fan01 2 }

fan01Reset  OBJECT-TYPE
	SYNTAX     NullApply
	MAX-ACCESS read-write
	STATUS     current
	DESCRIPTION
		"Reset operating time for this fan"
	::= { fan01 3 }

fan02Status  OBJECT-TYPE
	SYNTAX     INTEGER {
		standBy (0),
		running (1),
		failed (2)
	}
	MAX-ACCESS read-only
	STATUS     current
	DESCRIPTION
		"Current status fan:
		- Stand-by
		- Runing
		- Failed"
	::= { fan02 1 }

fan02OperatingTime  OBJECT-TYPE
	SYNTAX     Unsigned32
	UNITS 	"Hours"
	MAX-ACCESS read-only
	STATUS     current
	DESCRIPTION
		"Total operating time of this fan (hours)"
	::= { fan02 2 }

fan02Reset  OBJECT-TYPE
	SYNTAX     NullApply
	MAX-ACCESS read-write
	STATUS     current
	DESCRIPTION
		"Reset operating time for this fan"
	::= { fan02 3 }

fan03Status  OBJECT-TYPE
	SYNTAX     INTEGER {
		standBy (0),
		running (1),
		failed (2)
	}
	MAX-ACCESS read-only
	STATUS     current
	DESCRIPTION
		"Current status fan:
		- Stand-by
		- Runing
		- Failed"
	::= { fan03 1 }

fan03OperatingTime  OBJECT-TYPE
	SYNTAX     Unsigned32
	UNITS 	"Hours"
	MAX-ACCESS read-only
	STATUS     current
	DESCRIPTION
		"Total operating time of this fan (hours)"
	::= { fan03 2 }

fan03Reset  OBJECT-TYPE
	SYNTAX     NullApply
	MAX-ACCESS read-write
	STATUS     current
	DESCRIPTION
		"Reset operating time for this fan"
	::= { fan03 3 }

fanSpeed  OBJECT-TYPE
	SYNTAX     DisplayString
	UNITS 	"% percent"
	MAX-ACCESS read-only
	STATUS     current
	DESCRIPTION
		"Fan speed"
	::= { serviceCooling 10 }

externalAmplifierCoolingTable  OBJECT-TYPE
	SYNTAX SEQUENCE OF ExternalAmplifierCoolingEntry
	MAX-ACCESS not-accessible
	STATUS     current
	DESCRIPTION
		"Table for cooling in amplifier stages"
	::= { externalAmplifierCooling 1 }

externalAmplifierCoolingEntry  OBJECT-TYPE
	SYNTAX 	ExternalAmplifierCoolingEntry
	MAX-ACCESS not-accessible
	STATUS     current
	DESCRIPTION
		"Entry for an external amplifier cooling service"
	INDEX { externalAmplifierCoolingIndex }
	::= { externalAmplifierCoolingTable 1 }

ExternalAmplifierCoolingEntry ::= SEQUENCE {
	externalAmplifierCoolingIndex
		Unsigned32,
	amStFanSpeed
		DisplayString,
	amStFan1OperatingTime
		Unsigned32,
	amStFan2OperatingTime
		Unsigned32,
	amStFan1rpm
		Unsigned32,
	amStFan2rpm
		Unsigned32
}

externalAmplifierCoolingIndex  OBJECT-TYPE
	SYNTAX     Unsigned32 (1..4)
	MAX-ACCESS not-accessible
	STATUS     current
	DESCRIPTION
		"Index amplifier stage"
	::= { externalAmplifierCoolingEntry 1 }

amStFanSpeed  OBJECT-TYPE
	SYNTAX     DisplayString
	MAX-ACCESS read-only
	STATUS     current
	DESCRIPTION
		"Amplifier Stage: Fan 1 speed"
	::= { externalAmplifierCoolingEntry 2 }

amStFan1OperatingTime  OBJECT-TYPE
	SYNTAX     Unsigned32
	UNITS	"hours"
	MAX-ACCESS read-only
	STATUS     current
	DESCRIPTION
		"Amplifier Stage: Fan 1 operating time"
	::= { externalAmplifierCoolingEntry 3 }

amStFan2OperatingTime  OBJECT-TYPE
	SYNTAX     Unsigned32
	UNITS	"hours"
	MAX-ACCESS read-only
	STATUS     current
	DESCRIPTION
		"Amplifier Stage: Fan 2 operating time"
	::= { externalAmplifierCoolingEntry 4 }

amStFan1rpm  OBJECT-TYPE
	SYNTAX     Unsigned32
	UNITS	"rpm"
	MAX-ACCESS read-only
	STATUS     current
	DESCRIPTION
		"Amplifier Stage: Fan 1 rpm"
	::= { externalAmplifierCoolingEntry 5 }

amStFan2rpm  OBJECT-TYPE
	SYNTAX     Unsigned32
	UNITS	"rpm"
	MAX-ACCESS read-only
	STATUS     current
	DESCRIPTION
		"Amplifier Stage: Fan 2 rpm"
	::= { externalAmplifierCoolingEntry 6 }

rackCoolingTable  OBJECT-TYPE
	SYNTAX SEQUENCE OF RackCoolingEntry
	MAX-ACCESS not-accessible
	STATUS     current
	DESCRIPTION
		"Table for rack cooling boards"
	::= { rackCooling 1 }

rackCoolingEntry  OBJECT-TYPE
	SYNTAX 	RackCoolingEntry
	MAX-ACCESS not-accessible
	STATUS     current
	DESCRIPTION
		"Entry for an rack cooling board"
	INDEX { rcIndex }
	::= { rackCoolingTable 1 }

RackCoolingEntry ::= SEQUENCE {
	rcIndex
		Unsigned32,
	rcTag
		DisplayString,
	rcControlStatus
		INTEGER,
	rcHwStatus
		DisplayString,
	rcCoolingMode
		INTEGER,
	rcFan1
		DisabledEnabled,
	rcFan2
		DisabledEnabled,
	rcTemperature
		FloatingPoint,
	rcTemperatureTarget  
		Unsigned32,
---	rcPressureDifference
---		FloatingPoint,
	rcFan1SpeedManual
		FloatingPoint,
	rcFan2SpeedManual
		FloatingPoint,
	rcFan1Speed
		FloatingPoint,
	rcFan1Tachometer
		Unsigned32,
	rcFan1OperatingTime
		Unsigned32,
	rcFan1Reset
		NullApply,
	rcFan2Speed
		FloatingPoint,
	rcFan2Tachometer
		Unsigned32,
	rcFan2OperatingTime
		Unsigned32,
	rcFan2Reset
		NullApply,
	rcIdentifyBoard
		NullApply,
	rcExternalSensor1
		OpenClose,
	rcExternalSensor2
		OpenClose
}

rcIndex  OBJECT-TYPE
	SYNTAX     Unsigned32 (1..7)
	MAX-ACCESS not-accessible
	STATUS     current
	DESCRIPTION
		"Index Rack Cooling Board"
	::= { rackCoolingEntry 1 }

rcTag  OBJECT-TYPE
	SYNTAX     DisplayString (SIZE(1..31))
	MAX-ACCESS read-write
	STATUS     current
	DESCRIPTION
		"Rack Cooling: Tag"
	::= { rackCoolingEntry 2 }

rcControlStatus  OBJECT-TYPE
	SYNTAX     INTEGER {
		communicationError (0),
		ok (1),
		errorSwVersion (2),
		errorNoSwVersion (3),
		errorNoAddress (4),
		errorCollision (5)
	}
	MAX-ACCESS read-only
	STATUS     current
	DESCRIPTION
		"Rack Cooling: Control Status"
	::= { rackCoolingEntry 3 }

rcHwStatus  OBJECT-TYPE
	SYNTAX     DisplayString
	MAX-ACCESS read-only
	STATUS     current
	DESCRIPTION
		"Rack Cooling: HW Status"
	::= { rackCoolingEntry 4 }

rcCoolingMode  OBJECT-TYPE
	SYNTAX     INTEGER {
		temperatue (0),
		pressure (1),
		manual (2)
	}
	MAX-ACCESS read-write
	STATUS     current
	DESCRIPTION
		"Rack Cooling: Cooling mode"
	::= { rackCoolingEntry 5 }

rcFan1  OBJECT-TYPE
	SYNTAX     DisabledEnabled
	MAX-ACCESS read-write
	STATUS     current
	DESCRIPTION
		"Rack Cooling: Fan 1"
	::= { rackCoolingEntry 6 }

rcFan2  OBJECT-TYPE
	SYNTAX     DisabledEnabled
	MAX-ACCESS read-write
	STATUS     current
	DESCRIPTION
		"Rack Cooling: Fan 2"
	::= { rackCoolingEntry 7 }

rcTemperature  OBJECT-TYPE
	SYNTAX     FloatingPoint
	MAX-ACCESS read-only
	STATUS     current
	DESCRIPTION
		"Rack Cooling: Temperature"
	::= { rackCoolingEntry 8 }

rcTemperatureTarget  OBJECT-TYPE
	SYNTAX     Unsigned32 (0..100)
	MAX-ACCESS read-write
	STATUS     current
	DESCRIPTION
		"Rack Cooling: Temperature target"
	::= { rackCoolingEntry 9 }

---rcPressureDifference  OBJECT-TYPE
---	SYNTAX     FloatingPoint
---	UNITS	"Pa"
---	MAX-ACCESS read-only
---	STATUS     current
---	DESCRIPTION
---		"Rack Cooling: Pressure difference"
---	::= { rackCoolingEntry 10 }

rcFan1SpeedManual  OBJECT-TYPE
	SYNTAX     FloatingPoint
	UNITS	"%"
	MAX-ACCESS read-write
	STATUS     current
	DESCRIPTION
		"Rack Cooling: Manual fan 1 speed"
	::= { rackCoolingEntry 10 }

rcFan2SpeedManual  OBJECT-TYPE
	SYNTAX     FloatingPoint
	UNITS	"%"
	MAX-ACCESS read-write
	STATUS     current
	DESCRIPTION
		"Rack Cooling: Manual fan 2 speed"
	::= { rackCoolingEntry 11 }

rcFan1Speed  OBJECT-TYPE
	SYNTAX     FloatingPoint
	UNITS	"%"
	MAX-ACCESS read-only
	STATUS     current
	DESCRIPTION
		"Rack Cooling: Fan 1 speed"
	::= { rackCoolingEntry 12 }

rcFan1Tachometer  OBJECT-TYPE
	SYNTAX     Unsigned32
	UNITS	"rpm"
	MAX-ACCESS read-only
	STATUS     current
	DESCRIPTION
		"Rack Cooling: Fan 1 tachometer"
	::= { rackCoolingEntry 13 }

rcFan1OperatingTime  OBJECT-TYPE
	SYNTAX     Unsigned32
	UNITS	"h"
	MAX-ACCESS read-only
	STATUS     current
	DESCRIPTION
		"Rack Cooling: Fan 1 operating time"
	::= { rackCoolingEntry 14 }

rcFan1Reset  OBJECT-TYPE
	SYNTAX     NullApply
	MAX-ACCESS read-write
	STATUS     current
	DESCRIPTION
		"Rack Cooling: Fan 1 reset"
	::= { rackCoolingEntry 15 }

rcFan2Speed  OBJECT-TYPE
	SYNTAX     FloatingPoint
	UNITS	"%"
	MAX-ACCESS read-only
	STATUS     current
	DESCRIPTION
		"Rack Cooling: Fan 2 speed"
	::= { rackCoolingEntry 16 }

rcFan2Tachometer  OBJECT-TYPE
	SYNTAX     Unsigned32
	UNITS	"rpm"
	MAX-ACCESS read-only
	STATUS     current
	DESCRIPTION
		"Rack Cooling: Fan 2 tachometer"
	::= { rackCoolingEntry 17 }

rcFan2OperatingTime  OBJECT-TYPE
	SYNTAX     Unsigned32
	UNITS	"h"
	MAX-ACCESS read-only
	STATUS     current
	DESCRIPTION
		"Rack Cooling: Fan 2 operating time"
	::= { rackCoolingEntry 18 }

rcFan2Reset  OBJECT-TYPE
	SYNTAX     NullApply
	MAX-ACCESS read-write
	STATUS     current
	DESCRIPTION
		"Rack Cooling: Fan 2 reset"
	::= { rackCoolingEntry 19 }

rcIdentifyBoard  OBJECT-TYPE
	SYNTAX     NullApply
	MAX-ACCESS read-write
	STATUS     current
	DESCRIPTION
		"Rack Cooling: Identify rack cooling board (blink LEDs)"
	::= { rackCoolingEntry 20 }

rcExternalSensor1  OBJECT-TYPE
	SYNTAX     OpenClose
	MAX-ACCESS read-only
	STATUS     current
	DESCRIPTION
		"Rack Cooling: Sensor 1 status"
	::= { rackCoolingEntry 21 }

rcExternalSensor2  OBJECT-TYPE
	SYNTAX     OpenClose
	MAX-ACCESS read-only
	STATUS     current
	DESCRIPTION
		"Rack Cooling: Sensor 2 status"
	::= { rackCoolingEntry 22 }

dcLine1Voltage  OBJECT-TYPE
	SYNTAX     DisplayString
	UNITS	"V"
	MAX-ACCESS read-only
	STATUS     current
	DESCRIPTION
		"DC line 1 voltage"
	::= { servicePowerSupply 1 }

dcLine2Voltage  OBJECT-TYPE
	SYNTAX     DisplayString
	UNITS	"V"
	MAX-ACCESS read-only
	STATUS     current
	DESCRIPTION
		"DC line 2 voltage"
	::= { servicePowerSupply 2 }

dcLine3Voltage  OBJECT-TYPE
	SYNTAX     DisplayString
	UNITS	"V"
	MAX-ACCESS read-only
	STATUS     current
	DESCRIPTION
		"DC line 3 voltage"
	::= { servicePowerSupply 3 }

dcLine4Voltage  OBJECT-TYPE
	SYNTAX     DisplayString
	UNITS	"V"
	MAX-ACCESS read-only
	STATUS     current
	DESCRIPTION
		"DC line 4 voltage"
	::= { servicePowerSupply 4 }

dcInVoltage  OBJECT-TYPE
	SYNTAX     DisplayString
	UNITS	"V"
	MAX-ACCESS read-only
	STATUS     current
	DESCRIPTION
		"DC input voltage"
	::= { servicePowerSupply 7 }

psuAstatus  OBJECT-TYPE
	SYNTAX     DisplayString
	MAX-ACCESS read-only
	STATUS     current
	DESCRIPTION
		"PSU-A Status"
	::= { psuA 1 }

psuAacInputVoltage  OBJECT-TYPE
	SYNTAX     DisplayString
	UNITS	"V"
	MAX-ACCESS read-only
	STATUS     current
	DESCRIPTION
		"PSU-A: AC input voltage"
	::= { psuA 2 }

psuAdcOutputVoltage  OBJECT-TYPE
	SYNTAX     DisplayString
	UNITS	"V"
	MAX-ACCESS read-only
	STATUS     current
	DESCRIPTION
		"PSU-A: DC output voltage"
	::= { psuA 3 }

psuAtemperature  OBJECT-TYPE
	SYNTAX     DisplayString
	UNITS	"Celsius"
	MAX-ACCESS read-only
	STATUS     current
	DESCRIPTION
		"PSU-A: Temperature"
	::= { psuA 4 }

psuBstatus  OBJECT-TYPE
	SYNTAX     DisplayString
	MAX-ACCESS read-only
	STATUS     current
	DESCRIPTION
		"PSU-B Status"
	::= { psuB 1 }

psuBacInputVoltage  OBJECT-TYPE
	SYNTAX     DisplayString
	UNITS	"V"
	MAX-ACCESS read-only
	STATUS     current
	DESCRIPTION
		"PSU-B: AC input voltage"
	::= { psuB 2 }

psuBdcOutputVoltage  OBJECT-TYPE
	SYNTAX     DisplayString
	UNITS	"V"
	MAX-ACCESS read-only
	STATUS     current
	DESCRIPTION
		"PSU-B: DC output voltage"
	::= { psuB 3 }

psuBtemperature  OBJECT-TYPE
	SYNTAX     DisplayString
	UNITS	"Celsius"
	MAX-ACCESS read-only
	STATUS     current
	DESCRIPTION
		"PSU-B: Temperature"
	::= { psuB 4 }

externalAmplifierPSTable  OBJECT-TYPE
	SYNTAX SEQUENCE OF ExternalAmplifierPSEntry
	MAX-ACCESS not-accessible
	STATUS     current
	DESCRIPTION
		"Table for amplifier stages"
	::= { externalAmplifierPS 1 }

externalAmplifierPSEntry  OBJECT-TYPE
	SYNTAX 	ExternalAmplifierPSEntry
	MAX-ACCESS not-accessible
	STATUS     current
	DESCRIPTION
		"Entry for an external amplifier power supply service"
	INDEX { externalAmplifierPSIndex }
	::= { externalAmplifierPSTable 1 }

ExternalAmplifierPSEntry ::= SEQUENCE {
	externalAmplifierPSIndex
		Unsigned32,
	amStDcLineVoltage1
		DisplayString,
	amStDcLineVoltage2
		DisplayString,
	amStPsuAStatus
		DisplayString,
	amStPsuBStatus
		DisplayString,
	amStPsuCStatus
		DisplayString
}

externalAmplifierPSIndex  OBJECT-TYPE
	SYNTAX     Unsigned32 (1..4)
	MAX-ACCESS not-accessible
	STATUS     current
	DESCRIPTION
		"Index amplifier stage"
	::= { externalAmplifierPSEntry 1 }

amStDcLineVoltage1  OBJECT-TYPE
	SYNTAX     DisplayString
	MAX-ACCESS read-only
	STATUS     current
	DESCRIPTION
		"DC line 1 voltage"
	::= { externalAmplifierPSEntry 2 }

amStDcLineVoltage2  OBJECT-TYPE
	SYNTAX     DisplayString
	MAX-ACCESS read-only
	STATUS     current
	DESCRIPTION
		"DC line 2 voltage"
	::= { externalAmplifierPSEntry 3 }

amStPsuAStatus  OBJECT-TYPE
	SYNTAX     DisplayString
	MAX-ACCESS read-only
	STATUS     current
	DESCRIPTION
		"PSU-A Status"
	::= { externalAmplifierPSEntry 4 }

amStPsuBStatus  OBJECT-TYPE
	SYNTAX     DisplayString
	MAX-ACCESS read-only
	STATUS     current
	DESCRIPTION
		"PSU-B Status"
	::= { externalAmplifierPSEntry 5 }

amStPsuCStatus  OBJECT-TYPE
	SYNTAX     DisplayString
	MAX-ACCESS read-only
	STATUS     current
	DESCRIPTION
		"PSU-C Status"
	::= { externalAmplifierPSEntry 6 }


serviceSwUpgradeMode  OBJECT-TYPE
	SYNTAX     INTEGER {
		manual (0),
		autoCheck (1),
		autoDownload (2),
		autoUpgrade (3)
	}
	MAX-ACCESS read-write
	STATUS     current
	DESCRIPTION
		"Upgrade system"
	::= { serviceSwUpgrade 5 }

serviceSwUpgradeServer  OBJECT-TYPE
	SYNTAX     DisplayString (SIZE(1..32))
	MAX-ACCESS read-write
	STATUS     current
	DESCRIPTION
		"Upgrade server"
	::= { serviceSwUpgrade 10 }

serviceSwUpgradeUser  OBJECT-TYPE
	SYNTAX     DisplayString (SIZE(1..8))
	MAX-ACCESS read-write
	STATUS     current
	DESCRIPTION
		"Server user"
	::= { serviceSwUpgrade 12 }

serviceSwUpgradePassword  OBJECT-TYPE
	SYNTAX     DisplayString (SIZE(1..8))
	MAX-ACCESS read-write
	STATUS     current
	DESCRIPTION
		"Server password"
	::= { serviceSwUpgrade 13 }

serviceSwDaily  OBJECT-TYPE
	SYNTAX     DisplayString (SIZE(5))
	MAX-ACCESS read-write
	STATUS     current
	DESCRIPTION
		"Daily verification"
	::= { serviceSwUpgrade 15 }

-- serviceSwPeriodic  OBJECT-TYPE
-- 	SYNTAX     Unsigned32 (3..1440)
-- 	UNITS      "minutes"
-- 	MAX-ACCESS read-write
-- 	STATUS     current
-- 	DESCRIPTION
-- 		"Periodic verification"
-- 	::= { serviceSwUpgrade 20 }

serviceSwUpgradingFile  OBJECT-TYPE
	SYNTAX     DisplayString (SIZE(1..32))
	MAX-ACCESS read-write
	STATUS     current
	DESCRIPTION
		"Upgrading file"
	::= { serviceSwUpgrade 25 }

serviceSwVersionFile  OBJECT-TYPE
	SYNTAX     DisplayString (SIZE(1..32))
	MAX-ACCESS read-only
	STATUS     current
	DESCRIPTION
		"Version file"
	::= { serviceSwUpgrade 27 }

serviceSwStatus  OBJECT-TYPE
	SYNTAX     INTEGER {
		notUpdateAvailable (0),
		errorWrongRequest (1),
		errorLocalFileRemovingError (2),
		errorServerNotAchievable (3),
		errorManifestFileNotFound (4),
		errorLocalFileAlreadyExists (5),
		errorRemoteFileForbiden (6),
		errorNetworkIsUnreachable (7),
		errorAccessUnauthorized (8),
		errorConnectRefused (9),
		errorLoginIncorrect (10),
		errorNotHttpFtpServer (11),
		errorUpgradeFileNotFound (12),
		processNoExecuted (80),
		validatingNewVersion (90),
		downloadingFile (91),
		errorWrongFilename (92),
		fileDownloadedUpgradeAvailable (93),
		errorWrongUrlServer (94),
		upgradeFileAvailable (95),
		errorWrongUpgradeFile (96),
		errorInternalError (97),
		inProgress (98),
		errorUnknownError (100),
		downloadProcessFailed (101),
		errorCorruptedFile (102),
		errorBadUpgradeFileContent (103),
		errorPreparingUpgrade (104),
		errorExtractingUpgradeFile (105)
	}
	MAX-ACCESS read-only
	STATUS     current
	DESCRIPTION
		"Upgrade system status"
	::= { serviceSwUpgrade 30 }

serviceSwDownload  OBJECT-TYPE
	SYNTAX     Unsigned32
	MAX-ACCESS read-only
	STATUS     current
	DESCRIPTION
		"Download"
	::= { serviceSwUpgrade 35 }

serviceSwCheckNow  OBJECT-TYPE
	SYNTAX     NullApply
	MAX-ACCESS read-write
	STATUS     current
	DESCRIPTION
		"Check now"
	::= { serviceSwUpgrade 40 }

serviceSwDownloadNow  OBJECT-TYPE
	SYNTAX     NullApply
	MAX-ACCESS read-write
	STATUS     current
	DESCRIPTION
		"Download now"
	::= { serviceSwUpgrade 41 }

serviceSwUpgradeNow  OBJECT-TYPE
	SYNTAX     NullApply
	MAX-ACCESS read-write
	STATUS     current
	DESCRIPTION
		"Upgrade now"
	::= { serviceSwUpgrade 42 }

serviceInstallSyncBoard  OBJECT-TYPE
	SYNTAX     INTEGER {
		externalReference (0),
		gnssReceiver (1),
		ocxo (2),
		null (3)
	}
	MAX-ACCESS read-write
	STATUS     current
	DESCRIPTION
		"Synchronization board"
	::= { serviceInstallHwSw 5 }

serviceRedundantPsu  OBJECT-TYPE
	SYNTAX     INTEGER {
		redundantPsuDisabled (0),
		redundantPsuEnabled (1)
	}
	MAX-ACCESS read-write
	STATUS     current
	DESCRIPTION
		"Redundant PSU"
	::= { serviceInstallHwSw 10 }

serviceInput2  OBJECT-TYPE
	SYNTAX     INTEGER {
		socketIp2 (0),
		asi2 (1)
	}
	MAX-ACCESS read-write
	STATUS     current
	DESCRIPTION
		"Input 2"
	::= { serviceInstallHwSw 13 }

serviceTypeOfRedundancy  OBJECT-TYPE
	SYNTAX     INTEGER {
		singleDrive (0),
		onePlusOneA (1),
		onePlusOneB (2),
		dualDriveA (3),
		dualDriveB (4),
		nPlusOneB (5),
		nPlusOneA1 (6),
		nPlusOneA2 (7),
		nPlusOneA3 (8),
		nPlusOneA4 (9),
		nPlusOneA5 (10),
		nPlusOneA6 (11),
		nPlusOneA7 (12),
		nPlusOneA8 (13),
		nPlusOneA9 (14),
		nPlusOneA10 (15),
		nPlusOneA11 (16)
	}
	MAX-ACCESS read-write
	STATUS     current
	DESCRIPTION
		"Type of redundancy"
	::= { serviceInstallHwSw 15 }

serviceCanBusIdentifier  OBJECT-TYPE
	SYNTAX     Unsigned32 (0..12)
	MAX-ACCESS read-write
	STATUS     current
	DESCRIPTION
		"CAN bus identifier"
	::= { serviceInstallHwSw 17 }

serviceDualDriveRelay  OBJECT-TYPE
	SYNTAX     INTEGER {
		v1 (0),
		v2 (1)
	}
	MAX-ACCESS read-write
	STATUS     current
	DESCRIPTION
		"DD relay"
	::= { serviceInstallHwSw 18 }

-- serviceInstallUnitType TDF

serviceNumberOfAmplifierStages  OBJECT-TYPE
	SYNTAX     INTEGER {
		zeroAmplifier (0),
		oneAmplifier (1),
		twoAmplifiers (2),
		threeAmplifiers (3),
		fourAmplifiers (4),
		fiveAmplifiers (5),
		sixAmplifiers (6),
		sevenAmplifiers (7),
		eigthAmplifiers (8)
	}
	MAX-ACCESS read-write
	STATUS     current
	DESCRIPTION
		"Number of amplifier stages"
	::= { serviceInstallHwSw 25 }

rfPowerSample  OBJECT-TYPE
	SYNTAX     INTEGER {
		internal (0),
		external (1)
	}
	MAX-ACCESS read-write
	STATUS     current
	DESCRIPTION
		"RF power sample"
	::= { serviceInstallHwSw 26 }

servicePsuAmplifierStageTable  OBJECT-TYPE
	SYNTAX SEQUENCE OF ServicePsuAmplifierStageEntry
	MAX-ACCESS not-accessible
	STATUS     current
	DESCRIPTION
		"Table of PSU amplifier stage"
	::= { serviceInstallHwSw 30 }

servicePsuAmplifierStageEntry  OBJECT-TYPE
	SYNTAX ServicePsuAmplifierStageEntry
	MAX-ACCESS not-accessible
	STATUS     current
	DESCRIPTION
		"Entry for an amplifier stage"
	INDEX { servicePsuAmplifierStageIndex }
	::= { servicePsuAmplifierStageTable 1 }

ServicePsuAmplifierStageEntry ::= SEQUENCE {
	servicePsuAmplifierStageIndex
		Unsigned32,
	servicePsuAAmplifierStage
		OptionSw,
	servicePsuBAmplifierStage
		OptionSw,
	servicePsuCAmplifierStage
		OptionSw
}

servicePsuAmplifierStageIndex  OBJECT-TYPE
	SYNTAX     Unsigned32 (1..8)
	MAX-ACCESS not-accessible
	STATUS     current
	DESCRIPTION
		"Index trap sink"
	::= { servicePsuAmplifierStageEntry 1 }

servicePsuAAmplifierStage  OBJECT-TYPE
	SYNTAX     OptionSw
	MAX-ACCESS read-write
	STATUS     current
	DESCRIPTION
		"PSU A"
	::= { servicePsuAmplifierStageEntry 2 }

servicePsuBAmplifierStage  OBJECT-TYPE
	SYNTAX     OptionSw
	MAX-ACCESS read-write
	STATUS     current
	DESCRIPTION
		"PSU B"
	::= { servicePsuAmplifierStageEntry 3 }

servicePsuCAmplifierStage  OBJECT-TYPE
	SYNTAX     OptionSw
	MAX-ACCESS read-write
	STATUS     current
	DESCRIPTION
		"PSU C"
	::= { servicePsuAmplifierStageEntry 4 }

serviceDetectedCoolingBoard  OBJECT-TYPE
	SYNTAX     DisplayString
	MAX-ACCESS read-only
	STATUS     current
	DESCRIPTION
		"Detected devices"
	::= { serviceRackCooling 3 }

serviceAssignAddressCoolingBoard  OBJECT-TYPE
	SYNTAX     INTEGER {
		null (0),
		rackCooling1 (1),
		rackCooling2 (2),
		rackCooling3 (3),
		rackCooling4 (4),
		rackCooling5 (5),
		rackCooling6 (6),
		rackCooling7 (7)
	}
	MAX-ACCESS read-write
	STATUS     current
	DESCRIPTION
		"Assign address to Cooling board"
	::= { serviceRackCooling 5 }

serviceDeleteAddressCoolingBoard  OBJECT-TYPE
	SYNTAX     INTEGER {
		null (0),
		rackCooling1 (1),
		rackCooling2 (2),
		rackCooling3 (3),
		rackCooling4 (4),
		rackCooling5 (5),
		rackCooling6 (6),
		rackCooling7 (7)
	}
	MAX-ACCESS read-write
	STATUS     current
	DESCRIPTION
		"Delete address to Cooling board"
	::= { serviceRackCooling 10 }

serviceRackCooling1Board  OBJECT-TYPE
	SYNTAX     OptionSw 
	MAX-ACCESS read-write
	STATUS     current
	DESCRIPTION
		"Enable rack cooling 1"
	::= { serviceRackCooling 20 }

serviceRackCooling2Board  OBJECT-TYPE
	SYNTAX     OptionSw 
	MAX-ACCESS read-write
	STATUS     current
	DESCRIPTION
		"Enable rack cooling 2"
	::= { serviceRackCooling 25 }

serviceRackCooling3Board  OBJECT-TYPE
	SYNTAX     OptionSw 
	MAX-ACCESS read-write
	STATUS     current
	DESCRIPTION
		"Enable rack cooling 3"
	::= { serviceRackCooling 30 }

serviceRackCooling4Board  OBJECT-TYPE
	SYNTAX     OptionSw 
	MAX-ACCESS read-write
	STATUS     current
	DESCRIPTION
		"Enable rack cooling 4"
	::= { serviceRackCooling 35 }

serviceRackCooling5Board  OBJECT-TYPE
	SYNTAX     OptionSw 
	MAX-ACCESS read-write
	STATUS     current
	DESCRIPTION
		"Enable rack cooling 5"
	::= { serviceRackCooling 40 }

serviceRackCooling6Board  OBJECT-TYPE
	SYNTAX     OptionSw 
	MAX-ACCESS read-write
	STATUS     current
	DESCRIPTION
		"Enable rack cooling 6"
	::= { serviceRackCooling 45 }

serviceRackCooling7Board  OBJECT-TYPE
	SYNTAX     OptionSw 
	MAX-ACCESS read-write
	STATUS     current
	DESCRIPTION
		"Enable rack cooling 7"
	::= { serviceRackCooling 50 }

serviceDetectedAsiMatrix  OBJECT-TYPE
	SYNTAX     DisplayString
	MAX-ACCESS read-only
	STATUS     current
	DESCRIPTION
		"Detected devices"
	::= { serviceAsiMatrix 3 }

--serviceAsiInputsEnabled  OBJECT-TYPE
--	SYNTAX     INTEGER {
--		null (0),
--		one (1),
--		two (2)
--	}
--	MAX-ACCESS read-write
--	STATUS     current
--	DESCRIPTION
--		"ASI inputs enabled"
--	::= { serviceAsiMatrix 5 }

serviceAssingAddressAsiMatrix  OBJECT-TYPE
	SYNTAX     INTEGER {
		null (0),
		asi1Matrix1 (1),
		asi1Matrix2 (2),
		asi2Matrix1 (3),
		asi2Matrix2 (4)
	}
	MAX-ACCESS read-write
	STATUS     current
	DESCRIPTION
		"Assign address to ASI matrix"
	::= { serviceAsiMatrix 10 }

serviceDeleteAddressAsiMatrix  OBJECT-TYPE
	SYNTAX     INTEGER {
		null (0),
		asi1Matrix1 (1),
		asi1Matrix2 (2),
		asi2Matrix1 (3),
		asi2Matrix2 (4)
	}
	MAX-ACCESS read-write
	STATUS     current
	DESCRIPTION
		"Delete address to ASI matrix"
	::= { serviceAsiMatrix 15 }

serviceInstalledAsiMatrix1  OBJECT-TYPE
	SYNTAX		OptionHw
	MAX-ACCESS read-write
	STATUS     current
	DESCRIPTION
		"Installed ASI matrix 1"
	::= { serviceAsiMatrix 17 }

serviceInstalledAsiMatrix2  OBJECT-TYPE
	SYNTAX		OptionHw
	MAX-ACCESS read-write
	STATUS     current
	DESCRIPTION
		"Installed ASI matrix 2"
	::= { serviceAsiMatrix 18 }

--serviceIdentifyAsiMatrix  OBJECT-TYPE
--	SYNTAX     NullApply
--	MAX-ACCESS read-write
--	STATUS     current
--	DESCRIPTION
--		"Identify ASI matrix (blink LEDs)"
--	::= { serviceAsiMatrix 20 }

serviceDetectedRfMatrix  OBJECT-TYPE
	SYNTAX     DisplayString
	MAX-ACCESS read-only
	STATUS     current
	DESCRIPTION
		"Detected devices"
	::= { serviceRfMatrix 3 }

serviceAssingAddressRfMatrix  OBJECT-TYPE
	SYNTAX     INTEGER {
		null (0),
		rfMatrix1 (1),
		rfMatrix2 (2)
	}
	MAX-ACCESS read-write
	STATUS     current
	DESCRIPTION
		"Assign address to RF matrix"
	::= { serviceRfMatrix 10 }

serviceDeleteAddressRfMatrix  OBJECT-TYPE
	SYNTAX     INTEGER {
		null (0),
		rfMatrix1 (1),
		rfMatrix2 (2)
	}
	MAX-ACCESS read-write
	STATUS     current
	DESCRIPTION
		"Delete address to RF matrix"
	::= { serviceRfMatrix 15 }

serviceInstalledRfMatrix  OBJECT-TYPE
	SYNTAX		OptionHw
	MAX-ACCESS read-write
	STATUS     current
	DESCRIPTION
		"Installed RF matrix"
	::= { serviceRfMatrix 17 }

--serviceIdentifyRfMatrix  OBJECT-TYPE
--	SYNTAX     NullApply
--	MAX-ACCESS read-write
--	STATUS     current
--	DESCRIPTION
--		"Identify RF matrix (blink LEDs)"
--	::= { serviceRfMatrix 20 }

serviceDetectedEtiMatrix  OBJECT-TYPE
	SYNTAX     DisplayString
	MAX-ACCESS read-only
	STATUS     current
	DESCRIPTION
		"Detected devices"
	::= { serviceEtiMatrix 3 }

--serviceEtiInputsEnabled  OBJECT-TYPE
--	SYNTAX     INTEGER {
--		null (0),
--		one (1),
--		two (2)
--	}
--	MAX-ACCESS read-write
--	STATUS     current
--	DESCRIPTION
--		"ETI inputs enabled"
--	::= { serviceEtiMatrix 5 }

serviceAssingAddressEtiMatrix  OBJECT-TYPE
	SYNTAX     INTEGER {
		null (0),
		eti1Matrix1 (1),
		eti1Matrix2 (2),
		eti2Matrix1 (3),
		eti2Matrix2 (4)
	}
	MAX-ACCESS read-write
	STATUS     current
	DESCRIPTION
		"Assign address to ETI matrix"
	::= { serviceEtiMatrix 10 }

serviceDeleteAddressEtiMatrix  OBJECT-TYPE
	SYNTAX     INTEGER {
		null (0),
		eti1Matrix1 (1),
		eti1Matrix2 (2),
		eti2Matrix1 (3),
		eti2Matrix2 (4)
	}
	MAX-ACCESS read-write
	STATUS     current
	DESCRIPTION
		"Delete address to ETI matrix"
	::= { serviceEtiMatrix 15 }

serviceInstalledEtiMatrix1  OBJECT-TYPE
	SYNTAX		OptionHw
	MAX-ACCESS read-write
	STATUS     current
	DESCRIPTION
		"Installed ETI matrix 1"
	::= { serviceEtiMatrix 17 }

serviceInstalledEtiMatrix2  OBJECT-TYPE
	SYNTAX		OptionHw
	MAX-ACCESS read-write
	STATUS     current
	DESCRIPTION
		"Installed ETI matrix 2"
	::= { serviceEtiMatrix 18 }

--serviceIdentifyEtiMatrix  OBJECT-TYPE
--	SYNTAX     NullApply
--	MAX-ACCESS read-write
--	STATUS     current
--	DESCRIPTION
--		"Identify ETI matrix (blink LEDs)"
--	::= { serviceEtiMatrix 20 }
	
serviceInstallSwActivationCode  OBJECT-TYPE
	SYNTAX     DisplayString
	MAX-ACCESS read-write
	STATUS     current
	DESCRIPTION
		"Activation code"
	::= { serviceInstallHwSw 40 }

socket1Enable  OBJECT-TYPE
	SYNTAX     DisabledEnabled
	MAX-ACCESS read-write
	STATUS     current
	DESCRIPTION
		"IP Socket 1 enable"
	::= { socket1 1 }

socket1TransmissionMode  OBJECT-TYPE
	SYNTAX     INTEGER {
		unicast (0),
		multicast (1)
	}
	MAX-ACCESS read-write
	STATUS     current
	DESCRIPTION
		"IP Socket 1 transmission mode"
	::= { socket1 2 }

socket1UnicastIp  OBJECT-TYPE
	SYNTAX     IpAddress
	MAX-ACCESS read-write
	STATUS     current
	DESCRIPTION
		"Socket 1 unicast IP address"
	::= { socket1 3 }

socket1MulticastIp  OBJECT-TYPE
	SYNTAX     IpAddress
	MAX-ACCESS read-write
	STATUS     current
	DESCRIPTION
		"Socket 1 unicast IP address"
	::= { socket1 4 }

socket1SourceIp  OBJECT-TYPE
	SYNTAX     IpAddress
	MAX-ACCESS read-write
	STATUS     current
	DESCRIPTION
		"Socket 1 unicast IP address"
	::= { socket1 5 }

socket1VlanEnable  OBJECT-TYPE
	SYNTAX     INTEGER {
		disable (0),
		enable (1)
	}
	MAX-ACCESS read-write
	STATUS     current
	DESCRIPTION
		"IP socket 1 VLAN enable"
	::= { socket1 6 }

socket1VlanId  OBJECT-TYPE
	SYNTAX     Unsigned32 (1..4094)
	MAX-ACCESS read-write
	STATUS     current
	DESCRIPTION
		"IP Socket 1 VLAN ID"
	::= { socket1 7 }

socket1Port  OBJECT-TYPE
	SYNTAX     Unsigned32 (0..65535)
	MAX-ACCESS read-write
	STATUS     current
	DESCRIPTION
		"IP Socket 1 port"
	::= { socket1 8 }

socket1Protocol  OBJECT-TYPE
	SYNTAX     INTEGER {
		udp (0),
		rtp (1)
	}
	MAX-ACCESS read-write
	STATUS     current
	DESCRIPTION
		"IP Socket 1 protocol"
	::= { socket1 9 }

-- socket1MaximumBuffer  OBJECT-TYPE
-- 	SYNTAX     DisplayString
-- 	UNITS 	"ms"
-- 	MAX-ACCESS read-only
-- 	STATUS     current
-- 	DESCRIPTION
-- 		"IP socket 2 maximum buffer"
-- 	::= { socket1 10 }

socket1BufferDuration  OBJECT-TYPE
	SYNTAX     Unsigned32 (0..1000)
	UNITS 	"ms"
	MAX-ACCESS read-write
	STATUS     current
	DESCRIPTION
		"IP Socket 1 buffer duration"
	::= { socket1 11 }

socket1Fec  OBJECT-TYPE
	SYNTAX     DisplayString
	MAX-ACCESS read-only
	STATUS     current
	DESCRIPTION
		"IP socket 1 FEC (RTP)"
	::= { socket1 12 }

socket1InputBitrate  OBJECT-TYPE
	SYNTAX     DisplayString
	UNITS 	"bps"
	MAX-ACCESS read-only
	STATUS     current
	DESCRIPTION
		"IP Socket 1 input bitrate"
	::= { socket1 13 }

socket1Latency  OBJECT-TYPE
	SYNTAX     DisplayString
	UNITS 	"ms"
	MAX-ACCESS read-only
	STATUS     current
	DESCRIPTION
		"IP Socket 1 Latency"
	::= { socket1 14 }

socket1Content  OBJECT-TYPE
	SYNTAX     INTEGER {
		differentThanSocket2 (0),
		sameThantSocket2 (1)
	}
	MAX-ACCESS read-write
	STATUS     current
	DESCRIPTION
		"IP Socket 1 content"
	::= { socket1 15 }

socket1Jitter  OBJECT-TYPE
	SYNTAX     Unsigned32 (1..500)
	UNITS 	"ms"
	MAX-ACCESS read-write
	STATUS     current
	DESCRIPTION
		"IP Socket 1 Jitter"
	::= { socket1 16 }

socket1DabFec  OBJECT-TYPE
	SYNTAX     NoYes 
	MAX-ACCESS read-only
	STATUS     current
	DESCRIPTION
		"IP Socket 1 DAB FEC"
	::= { socket1 17 }

socket1RxPackets  OBJECT-TYPE
	SYNTAX    Unsigned32
	MAX-ACCESS read-only
	STATUS     current
	DESCRIPTION
		"RX Packets"
	::= { socket1Statistics 1 }

socket1RxDisorderedPkts  OBJECT-TYPE
	SYNTAX    Unsigned32
	MAX-ACCESS read-only
	STATUS     current
	DESCRIPTION
		"Disordered packets"
	::= { socket1Statistics 5 }

socket1RxDuplicatedPkts  OBJECT-TYPE
	SYNTAX    Unsigned32
	MAX-ACCESS read-only
	STATUS     current
	DESCRIPTION
		"Duplicated packets"
	::= { socket1Statistics 10 }

socket1RxReorderedPkts  OBJECT-TYPE
	SYNTAX    Unsigned32
	MAX-ACCESS read-only
	STATUS     current
	DESCRIPTION
		"Reordered packets"
	::= { socket1Statistics 15 }

socket1RxLostPkts  OBJECT-TYPE
	SYNTAX    Unsigned32
	MAX-ACCESS read-only
	STATUS     current
	DESCRIPTION
		"Lost packets"
	::= { socket1Statistics 20 }

socket1RxOutOfRangePackets  OBJECT-TYPE
	SYNTAX    Unsigned32
	MAX-ACCESS read-only
	STATUS     current
	DESCRIPTION
		"Out of range packets"
	::= { socket1Statistics 22 }

socket1RxFixedPackets  OBJECT-TYPE
	SYNTAX    Unsigned32
	MAX-ACCESS read-only
	STATUS     current
	DESCRIPTION
		"Fixed packets"
	::= { socket1Statistics 23 }

socket1CorrectedRSCodewords  OBJECT-TYPE
	SYNTAX    Unsigned32
	MAX-ACCESS read-only
	STATUS     current
	DESCRIPTION
		"Corrected RS codewords"
	::= { socket1Statistics 25 }

socket1NotCorrectedRSCodewords  OBJECT-TYPE
	SYNTAX    Unsigned32
	MAX-ACCESS read-only
	STATUS     current
	DESCRIPTION
		"Not corrected RS codewords"
	::= { socket1Statistics 30 }

socket1TimeWithoutService  OBJECT-TYPE
	SYNTAX     FloatingPoint
	MAX-ACCESS read-only
	STATUS     current
	DESCRIPTION
		"Time without service"
	::= { socket1Statistics 32 }

socket1RxStatisticsReset  OBJECT-TYPE
	SYNTAX    NullApply
	MAX-ACCESS read-write
	STATUS     current
	DESCRIPTION
		"Reset Rx 1 counters"
	::= { socket1Statistics 35 }

socket1UnicastNetmask  OBJECT-TYPE
	SYNTAX     IpAddress
	MAX-ACCESS read-write
	STATUS     current
	DESCRIPTION
		"Socket 1 Unicast Netmask"
	::= { socket1 30 }

socket1MacAddr  OBJECT-TYPE
	SYNTAX     MacAddress
	MAX-ACCESS read-only
	STATUS     current
	DESCRIPTION
		"Socket 1 MAC interfaz address"
	::= { socket1 33 }

socket2Enable  OBJECT-TYPE
	SYNTAX     DisabledEnabled
	MAX-ACCESS read-write
	STATUS     current
	DESCRIPTION
		"IP Socket 2 enable"
	::= { socket2 1 }

socket2TransmissionMode  OBJECT-TYPE
	SYNTAX     INTEGER {
		unicast (0),
		multicast (1)
	}
	MAX-ACCESS read-write
	STATUS     current
	DESCRIPTION
		"IP Socket 2 transmission mode"
	::= { socket2 2 }

socket2UnicastIp  OBJECT-TYPE
	SYNTAX     IpAddress
	MAX-ACCESS read-write
	STATUS     current
	DESCRIPTION
		"Socket 2 unicast IP address"
	::= { socket2 3 }

socket2MulticastIp  OBJECT-TYPE
	SYNTAX     IpAddress
	MAX-ACCESS read-write
	STATUS     current
	DESCRIPTION
		"Socket 2 unicast IP address"
	::= { socket2 4 }

socket2SourceIp  OBJECT-TYPE
	SYNTAX     IpAddress
	MAX-ACCESS read-write
	STATUS     current
	DESCRIPTION
		"Socket 2 unicast IP address"
	::= { socket2 5 }

socket2VlanEnable  OBJECT-TYPE
	SYNTAX     INTEGER {
		disable (0),
		enable (1)
	}
	MAX-ACCESS read-write
	STATUS     current
	DESCRIPTION
		"IP socket 2 VLAN enable"
	::= { socket2 6 }

socket2VlanId  OBJECT-TYPE
	SYNTAX     Unsigned32 (1..4094)
	MAX-ACCESS read-write
	STATUS     current
	DESCRIPTION
		"IP Socket 2 VLAN ID"
	::= { socket2 7 }

socket2Port  OBJECT-TYPE
	SYNTAX     Unsigned32 (0..65535)
	MAX-ACCESS read-write
	STATUS     current
	DESCRIPTION
		"IP Socket 2 port"
	::= { socket2 8 }

socket2Protocol  OBJECT-TYPE
	SYNTAX     INTEGER {
		udp (0),
		rtp (1)
	}
	MAX-ACCESS read-write
	STATUS     current
	DESCRIPTION
		"IP Socket 2 protocol"
	::= { socket2 9 }

-- socket2MaximumBuffer  OBJECT-TYPE
-- 	SYNTAX     DisplayString
-- 	UNITS 	"ms"
-- 	MAX-ACCESS read-only
-- 	STATUS     current
-- 	DESCRIPTION
-- 		"IP socket 2 maximum buffer"
-- 	::= { socket2 10 }

socket2BufferDuration  OBJECT-TYPE
	SYNTAX     Unsigned32 (0..1000)
	UNITS 	"ms"
	MAX-ACCESS read-write
	STATUS     current
	DESCRIPTION
		"IP Socket 1 buffer duration"
	::= { socket2 11 }

socket2Fec  OBJECT-TYPE
	SYNTAX     DisplayString
	MAX-ACCESS read-only
	STATUS     current
	DESCRIPTION
		"IP socket 2 FEC (RTP)"
	::= { socket2 12 }

socket2InputBitrate  OBJECT-TYPE
	SYNTAX     DisplayString
	UNITS 	"bps"
	MAX-ACCESS read-only
	STATUS     current
	DESCRIPTION
		"IP Socket 2 input bitrate"
	::= { socket2 13 }

socket2Latency  OBJECT-TYPE
	SYNTAX     DisplayString
	UNITS 	"ms"
	MAX-ACCESS read-only
	STATUS     current
	DESCRIPTION
		"IP Socket 2 Latency"
	::= { socket2 14 }

socket2Content  OBJECT-TYPE
	SYNTAX     INTEGER {
		differentThanSocket1 (0),
		sameThantSocket1 (1)
	}
	MAX-ACCESS read-write
	STATUS     current
	DESCRIPTION
		"IP Socket 2 content"
	::= { socket2 15 }

socket2Jitter  OBJECT-TYPE
	SYNTAX     Unsigned32 (1..500)
	UNITS 	"ms"
	MAX-ACCESS read-write
	STATUS     current
	DESCRIPTION
		"IP Socket 2 Jitter"
	::= { socket2 16 }

socket2DabFec  OBJECT-TYPE
	SYNTAX     NoYes 
	MAX-ACCESS read-only
	STATUS     current
	DESCRIPTION
		"IP Socket 2 DAB FEC"
	::= { socket2 17 }

socket2RxPackets  OBJECT-TYPE
	SYNTAX    Unsigned32
	MAX-ACCESS read-only
	STATUS     current
	DESCRIPTION
		"RX Packets"
	::= { socket2Statistics 1 }

socket2RxDisorderedPkts  OBJECT-TYPE
	SYNTAX    Unsigned32
	MAX-ACCESS read-only
	STATUS     current
	DESCRIPTION
		"Disordered packets"
	::= { socket2Statistics 5 }

socket2RxDuplicatedPkts  OBJECT-TYPE
	SYNTAX    Unsigned32
	MAX-ACCESS read-only
	STATUS     current
	DESCRIPTION
		"Duplicated packets"
	::= { socket2Statistics 10 }

socket2RxReorderedPkts  OBJECT-TYPE
	SYNTAX    Unsigned32
	MAX-ACCESS read-only
	STATUS     current
	DESCRIPTION
		"Reordered packets"
	::= { socket2Statistics 15 }

socket2RxLostPkts  OBJECT-TYPE
	SYNTAX    Unsigned32
	MAX-ACCESS read-only
	STATUS     current
	DESCRIPTION
		"Lost packets"
	::= { socket2Statistics 20 }

socket2RxOutOfRangePackets  OBJECT-TYPE
	SYNTAX    Unsigned32
	MAX-ACCESS read-only
	STATUS     current
	DESCRIPTION
		"Out of range packets"
	::= { socket2Statistics 22 }

socket2RxFixedPackets  OBJECT-TYPE
	SYNTAX    Unsigned32
	MAX-ACCESS read-only
	STATUS     current
	DESCRIPTION
		"Fixed packets"
	::= { socket2Statistics 23 }

socket2CorrectedRSCodewords  OBJECT-TYPE
	SYNTAX    Unsigned32
	MAX-ACCESS read-only
	STATUS     current
	DESCRIPTION
		"Corrected RS codewords"
	::= { socket2Statistics 25 }

socket2NotCorrectedRSCodewords  OBJECT-TYPE
	SYNTAX    Unsigned32
	MAX-ACCESS read-only
	STATUS     current
	DESCRIPTION
		"Not corrected RS codewords"
	::= { socket2Statistics 30 }

socket2TimeWithoutService  OBJECT-TYPE
	SYNTAX     FloatingPoint
	MAX-ACCESS read-only
	STATUS     current
	DESCRIPTION
		"Time without service"
	::= { socket2Statistics 32 }


socket2RxStatisticsReset  OBJECT-TYPE
	SYNTAX    NullApply
	MAX-ACCESS read-write
	STATUS     current
	DESCRIPTION
		"Reset Rx 2 counters"
	::= { socket2Statistics 35 }

socket2UnicastNetmask  OBJECT-TYPE
	SYNTAX     IpAddress
	MAX-ACCESS read-write
	STATUS     current
	DESCRIPTION
		"Socket 2 Unicast Netmask"
	::= { socket2 30 }

socket2MacAddr  OBJECT-TYPE
	SYNTAX     MacAddress
	MAX-ACCESS read-only
	STATUS     current
	DESCRIPTION
		"Socket 2 MAC interfaz address"
	::= { socket2 33 }

sourceSelected  OBJECT-TYPE
	SYNTAX     INTEGER {
		null (0),
		source1 (1),
		source2 (2),
		source3 (3),
		source4 (4)
	}
	MAX-ACCESS read-only
	STATUS     current
	DESCRIPTION
		"Selected input"
	::= { inputSwitching 1 }

switchingMode  OBJECT-TYPE
	SYNTAX     INTEGER {
		null (0),
		automatic (1),
		source1 (2),
		source2 (3),
		source3 (4),
		source4 (5)
	}
	MAX-ACCESS read-write
	STATUS     current
	DESCRIPTION
		"Selected input"
	::= { inputSwitching 2 }

monitorOutput  OBJECT-TYPE
	SYNTAX     INTEGER {
		null (0),
		automatic (1),
		source1 (2),
		source2 (3),
		source3 (4),
		source4 (5)
	}
	MAX-ACCESS read-write
	STATUS     current
	DESCRIPTION
		"Monitor output"
	::= { inputSwitching 3 }


-- maximumLatency  OBJECT-TYPE
-- 	SYNTAX     Unsigned32 (0..999)
-- 	UNITS 	"milliseconds"
-- 	MAX-ACCESS read-write
-- 	STATUS     current
-- 	DESCRIPTION
-- 		"Maximum Latency buffer in milliseconds"
-- 	::= { inputSwitching 3 }

asiBypassEqualizers  OBJECT-TYPE
	SYNTAX     DisabledEnabled
	MAX-ACCESS read-write
	STATUS     current
	DESCRIPTION
		"ASI equalizers bypass"
	::= { inputSwitching 5 }

nonSeamlessHysteresis  OBJECT-TYPE
	SYNTAX     Unsigned32 (0..10)
	UNITS 	"seconds"
	MAX-ACCESS read-write
	STATUS     current
	DESCRIPTION
		"Non-seamless hysteresis"
	::= { inputSwitchingHysteresis 1 }

higherPriorityHysteresis  OBJECT-TYPE
	SYNTAX     Unsigned32 (0..600)
	UNITS 	"seconds"
	MAX-ACCESS read-write
	STATUS     current
	DESCRIPTION
		"Higher priority hysteresis"
	::= { inputSwitchingHysteresis 2 }

input1Priority  OBJECT-TYPE
	SYNTAX     INTEGER {
		inputDisabled (0),
		p1Highest (1),
		p2 (2),
		p3 (3),
		p4Lowest (4)
	}
	MAX-ACCESS read-write
	STATUS     current
	DESCRIPTION
		"Input priority
		1 - Highest
		4 - Lowest"
	::= { input1 1 }

input1Status  OBJECT-TYPE
	SYNTAX     DisplayString
	MAX-ACCESS read-only
	STATUS     current
	DESCRIPTION
		"Assignment / Status / Bitrate / Latency"
	::= { input1 2 }

input1Pat  OBJECT-TYPE
	SYNTAX     DisplayString
	MAX-ACCESS read-only
	STATUS     current
	DESCRIPTION
		"Program / Name / PIDs / Bitrate [bps]"
	::= { input1 3 }

input2Priority  OBJECT-TYPE
	SYNTAX     INTEGER {
		inputDisabled (0),
		p1Highest (1),
		p2 (2),
		p3 (3),
		p4Lowest (4)
	}
	MAX-ACCESS read-write
	STATUS     current
	DESCRIPTION
		"Input priority
		1 - Highest
		4 - Lowest"
	::= { input2 1 }

input2Status  OBJECT-TYPE
	SYNTAX     DisplayString
	MAX-ACCESS read-only
	STATUS     current
	DESCRIPTION
		"Assignment / Status / Bitrate / Latency"
	::= { input2 2 }

input2Pat  OBJECT-TYPE
	SYNTAX     DisplayString
	MAX-ACCESS read-only
	STATUS     current
	DESCRIPTION
		"Program / Name / PIDs / Bitrate [bps]"
	::= { input2 3 }

input3Priority  OBJECT-TYPE
	SYNTAX     INTEGER {
		inputDisabled (0),
		p1Highest (1),
		p2 (2),
		p3 (3),
		p4Lowest (4)
	}
	MAX-ACCESS read-write
	STATUS     current
	DESCRIPTION
		"Input priority
		1 - Highest
		4 - Lowest"
	::= { input3 1 }

input3Status  OBJECT-TYPE
	SYNTAX     DisplayString
	MAX-ACCESS read-only
	STATUS     current
	DESCRIPTION
		"Assignment / Status / Bitrate / Latency"
	::= { input3 2 }

input3Pat  OBJECT-TYPE
	SYNTAX     DisplayString
	MAX-ACCESS read-only
	STATUS     current
	DESCRIPTION
		"Program / Name / PIDs / Bitrate [bps]"
	::= { input3 3 }

input4Priority  OBJECT-TYPE
	SYNTAX     INTEGER {
		inputDisabled (0),
		p1Highest (1),
		p2 (2),
		p3 (3),
		p4Lowest (4)
	}
	MAX-ACCESS read-write
	STATUS     current
	DESCRIPTION
		"Input priority
		1 - Highest
		4 - Lowest"
	::= { input4 1 }

input4Status  OBJECT-TYPE
	SYNTAX     DisplayString
	MAX-ACCESS read-only
	STATUS     current
	DESCRIPTION
		"Assignment / Status / Bitrate / Latency"
	::= { input4 2 }

input4Pat  OBJECT-TYPE
	SYNTAX     DisplayString
	MAX-ACCESS read-only
	STATUS     current
	DESCRIPTION
		"Program / Name / PIDs / Bitrate [bps]"
	::= { input4 3 }

asi1Enable  OBJECT-TYPE
	SYNTAX     DisabledEnabled
	MAX-ACCESS read-write
	STATUS     current
	DESCRIPTION
		"Enable/Disable ASI 1 input"
	::= { asi1 1 }

asi2Enable  OBJECT-TYPE
	SYNTAX     DisabledEnabled
	MAX-ACCESS read-write
	STATUS     current
	DESCRIPTION
		"Enable/Disable ASI 2 input"
	::= { asi2 1 }

-- ETI 1 --

eti1Enable  OBJECT-TYPE
	SYNTAX     DisabledEnabled
	MAX-ACCESS read-write
	STATUS     current
	DESCRIPTION
		"Enable/Disable ETI 1 input"
	::= { eti1 1 }

eti1DetectedLayer  OBJECT-TYPE
	SYNTAX     INTEGER {
		none (0),
		etiNi (1),
		etiNa5592 (2),
		etiNa5376 (3)
	}
	MAX-ACCESS read-only
	STATUS     current
	DESCRIPTION
		"ETI 1 Detected Layer"
	::= { eti1 10 }

eti1InputBitrate  OBJECT-TYPE
	SYNTAX     FloatingPoint
	UNITS			"bps"
	MAX-ACCESS read-only
	STATUS     current
	DESCRIPTION
		"ETI 1 Input bitrate"
	::= { eti1 15 }

eti1CorrectedRSCodewords  OBJECT-TYPE
	SYNTAX    Unsigned32
	MAX-ACCESS read-only
	STATUS     current
	DESCRIPTION
		"ETI 1 Corrected RS codewords"
	::= { eti1Statistics 1 }

eti1NotCorrectedRSCodewords  OBJECT-TYPE
	SYNTAX    Unsigned32
	MAX-ACCESS read-only
	STATUS     current
	DESCRIPTION
		"Not corrected RS codewords"
	::= { eti1Statistics 5 }

eti1TimeWithoutService  OBJECT-TYPE
	SYNTAX     FloatingPoint
	MAX-ACCESS read-only
	STATUS     current
	DESCRIPTION
		"Time without service"
	::= { eti1Statistics 7 }

eti1RxStatisticsReset  OBJECT-TYPE
	SYNTAX    NullApply
	MAX-ACCESS read-write
	STATUS     current
	DESCRIPTION
		"Reset Rx 1 counters"
	::= { eti1Statistics 10 }

-- ETI 2 --

eti2Enable  OBJECT-TYPE
	SYNTAX     DisabledEnabled
	MAX-ACCESS read-write
	STATUS     current
	DESCRIPTION
		"Enable/Disable ETI 2 input"
	::= { eti2 1 }

eti2DetectedLayer  OBJECT-TYPE
	SYNTAX     INTEGER {
		none (0),
		etiNi (1),
		etiNa5592 (2),
		etiNa5376 (3)
	}
	MAX-ACCESS read-only
	STATUS     current
	DESCRIPTION
		"ETI 2 Detected Layer"
	::= { eti2 10 }

eti2InputBitrate  OBJECT-TYPE
	SYNTAX     FloatingPoint
	UNITS			"bps"
	MAX-ACCESS read-only
	STATUS     current
	DESCRIPTION
		"ETI 2 Input bitrate"
	::= { eti2 15 }

eti2CorrectedRSCodewords  OBJECT-TYPE
	SYNTAX    Unsigned32
	MAX-ACCESS read-only
	STATUS     current
	DESCRIPTION
		"ETI 2 Corrected RS codewords"
	::= { eti2Statistics 1 }

eti2NotCorrectedRSCodewords  OBJECT-TYPE
	SYNTAX    Unsigned32
	MAX-ACCESS read-only
	STATUS     current
	DESCRIPTION
		"Not corrected RS codewords"
	::= { eti2Statistics 5 }

eti2TimeWithoutService  OBJECT-TYPE
	SYNTAX     FloatingPoint
	MAX-ACCESS read-only
	STATUS     current
	DESCRIPTION
		"Time without service"
	::= { eti2Statistics 7 }

eti2RxStatisticsReset  OBJECT-TYPE
	SYNTAX    NullApply
	MAX-ACCESS read-write
	STATUS     current
	DESCRIPTION
		"Reset Rx 2 counters"
	::= { eti2Statistics 10 }

--- Receiver 1

dttReceiver1Enable  OBJECT-TYPE
	SYNTAX     DisabledEnabled
	MAX-ACCESS read-write
	STATUS     current
	DESCRIPTION
		"Enable/Disable DTT receiver 1"
	::= { dttReceiver1 5 }

dttReceiver1Standard  OBJECT-TYPE
	SYNTAX     INTEGER {
		dvbt (0),
		dvbt2 (1),
		isdbt (2)
	}
	MAX-ACCESS read-write
	STATUS     current
	DESCRIPTION
		"Standard"
	::= { dttReceiver1 10 }

dttReceiver1Bandwidth  OBJECT-TYPE
	SYNTAX     INTEGER {
		bw6Mhz (6),
		bw7Mhz (7),
		bw8Mhz (8)
	}
	MAX-ACCESS read-write
	STATUS     current
	DESCRIPTION
		"Bandwidth"
	::= { dttReceiver1 15 }

dttReceiver1InputFrequencyMode  OBJECT-TYPE
	SYNTAX     INTEGER {
		channel (0),
		frequency (1)
	}
	MAX-ACCESS read-write
	STATUS     current
	DESCRIPTION
		"Input Frequency Mode"
	::= { dttReceiver1 20 }

dttReceiver1PlpId  OBJECT-TYPE
	SYNTAX     Unsigned32 (0..255)
	MAX-ACCESS read-write
	STATUS     current
	DESCRIPTION
		"PLP ID [Only for DVB-T2]"
	::= { dttReceiver1 25 }

dttReceiver1BerMute  OBJECT-TYPE
	SYNTAX     DisabledEnabled
	MAX-ACCESS read-write
	STATUS     current
	DESCRIPTION
		"BER Mute"
	::= { dttReceiver1 30 }

--- Receiver 1 Channel

dttReceiver1Channel  OBJECT-TYPE
	SYNTAX     Unsigned32 (14..78)
	MAX-ACCESS read-write
	STATUS     current
	DESCRIPTION
		"Channel"
	::= { dttReceiver1ChannelMode 5 }

dttReceiver1ChannelOffset  OBJECT-TYPE
	SYNTAX     Integer32 (-4..4)
	MAX-ACCESS read-write
	STATUS     current
	DESCRIPTION
		"Frequency offset"
	::= { dttReceiver1ChannelMode 10 }

dttReceiver1ChannelResolution  OBJECT-TYPE
	SYNTAX     INTEGER {
		resolution1div6 (0),
		resolution1div7 (1),
		resolution1div8 (2)
	}
	UNITS 	"MHz"
	MAX-ACCESS read-write
	STATUS     current
	DESCRIPTION
		"Channel resolution"
	::= { dttReceiver1ChannelMode 15 }

--- Receiver 1 Frequency

dttReceiver1Frequency  OBJECT-TYPE
	SYNTAX     Unsigned32 (42000000..862000000)
	UNITS 	"Hz"
	MAX-ACCESS read-write
	STATUS     current
	DESCRIPTION
		"Frequency"
	::= { dttReceiver1CentralFrequencyMode 5 }

--- Receiver 1 Status

dttReceiver1StatusReceiver  OBJECT-TYPE
	SYNTAX     INTEGER {
		unlocked (0),
		locked (1),
		disabled (2)
	}
	MAX-ACCESS read-only
	STATUS     current
	DESCRIPTION
		"Status"
	::= { dttReceiver1Status 5 }

dttReceiver1InputFrequency  OBJECT-TYPE
	SYNTAX     DisplayString
	UNITS 	"Hz"
	MAX-ACCESS read-only
	STATUS     current
	DESCRIPTION
		"Input frequency"
	::= { dttReceiver1Status 10 }

--- Receiver 1 DVB-T Modulation

dttReceiver1Constellation  OBJECT-TYPE
	SYNTAX     INTEGER {
		null (0),
		qpsk (1),
		qam16 (2),
		qam64 (3),
		reserved (4)
	}
	MAX-ACCESS read-only
	STATUS     current
	DESCRIPTION
		"Constellation"
	::= { dttReceiver1TModulation 5 }

dttReceiver1Fec  OBJECT-TYPE
	SYNTAX     INTEGER {
		null (0),
		fec1div2 (1),
		fec2div3 (2),
		fec3div4 (3),
		fec5div6 (4),
		fec7div8 (5),
		reserved6 (6),
		reserved7 (7),
		reserved8 (8)
	}
	MAX-ACCESS read-only
	STATUS     current
	DESCRIPTION
		"FEC"
	::= { dttReceiver1TModulation 10 }

dttReceiver1GuardInterval  OBJECT-TYPE
	SYNTAX     INTEGER {
		null8 (0),
		guardInterval1div32 (1),
		guardInterval1div16 (2),
		guardInterval1div8 (3),
		guardInterval1div4 (4)
	}
	MAX-ACCESS read-only
	STATUS     current
	DESCRIPTION
		"Guard Interval"
	::= { dttReceiver1TModulation 15 }

dttReceiver1Fft  OBJECT-TYPE
	SYNTAX     INTEGER {
		null (0),
		fft2K (1),
		fft8K (2),
		reserved1 (3),
		reserved2 (4)
	}
	MAX-ACCESS read-only
	STATUS     current
	DESCRIPTION
		"FFT"
	::= { dttReceiver1TModulation 20 }

dttReceiver1CellId  OBJECT-TYPE
	SYNTAX     Unsigned32 (0..65535)
	MAX-ACCESS read-only
	STATUS     current
	DESCRIPTION
		"Cell ID"
	::= { dttReceiver1TModulation 25 }

--- Receiver 1 DVB-T Measurements

dttReceiver1Cber  OBJECT-TYPE
	SYNTAX     DisplayString
	MAX-ACCESS read-only
	STATUS     current
	DESCRIPTION
		"CBER"
	::= { dttReceiver1TMeasures 5 }

dttReceiver1Vber  OBJECT-TYPE
	SYNTAX     DisplayString
	MAX-ACCESS read-only
	STATUS     current
	DESCRIPTION
		"CBER"
	::= { dttReceiver1TMeasures 10 }

--- Receiver 1 DVB-T2 System

dttReceiver1T2Profile  OBJECT-TYPE
	SYNTAX     INTEGER {
		null (0),
		base (1),
		lite (2),
		baseLite (3)
	}
	MAX-ACCESS read-only
	STATUS     current
	DESCRIPTION
		"DVB-T2 profile"
	::= { dttReceiver1T2System 5 }

dttReceiver1T2Version  OBJECT-TYPE
	SYNTAX     INTEGER {
		null (0),
		v1p1p1 (1),
		v1p2p1 (2),
		v1p3p1 (3)
	}
	MAX-ACCESS read-only
	STATUS     current
	DESCRIPTION
		"T2 Version"
	::= { dttReceiver1T2System 10 }

dttReceiver1T2CellId  OBJECT-TYPE
	SYNTAX     Unsigned32 (0..65535)
	MAX-ACCESS read-only
	STATUS     current
	DESCRIPTION
		"Cell ID"
	::= { dttReceiver1T2System 15 }

dttReceiver1T2NetworkId  OBJECT-TYPE
	SYNTAX     Unsigned32 (0..65535)
	MAX-ACCESS read-only
	STATUS     current
	DESCRIPTION
		"Network ID"
	::= { dttReceiver1T2System 20 }

dttReceiver1T2SystemId  OBJECT-TYPE
	SYNTAX     Unsigned32 (0..65535)
	MAX-ACCESS read-only
	STATUS     current
	DESCRIPTION
		"T2 system ID"
	::= { dttReceiver1T2System 25 }

--- Receiver 1 DVB-T2 Frame

dttRx1T2L1SignallingModulation  OBJECT-TYPE
	SYNTAX     INTEGER {
		null (0),
		bpsk (1),
		qpsk (2),
		qam16 (3),
		qam64 (4)
	}
	MAX-ACCESS read-only
	STATUS     current
	DESCRIPTION
		"L1-post signalling constellation"
	::= { dttReceiver1T2Frame 5 }

dttRx1T2L1PostScrambling  OBJECT-TYPE
	SYNTAX     INTEGER {
		null(0),
		off (1),
		on (2)
	}
	MAX-ACCESS read-only
	STATUS     current
	DESCRIPTION
		"L1-post scrambling"
	::= { dttReceiver1T2Frame 10 }

dttRx1T2PreambleFormat  OBJECT-TYPE
	SYNTAX     INTEGER {
		null (0),
		siso (1),
		miso (2)
	}
	MAX-ACCESS read-only
	STATUS     current
	DESCRIPTION
		"Preamble format"
	::= { dttReceiver1T2Frame 15 }

dttRx1T2ExtendedCarrierMode  OBJECT-TYPE
	SYNTAX     INTEGER {
		null (0),
		disable (1),
		enable (2)
	}
	MAX-ACCESS read-only
	STATUS     current
	DESCRIPTION
		"Extended carrier mode"
	::= { dttReceiver1T2Frame 20 }

dttRx1T2FftSize  OBJECT-TYPE
	SYNTAX     INTEGER {
		null (0),
		fft2K (1),
		fft8K (2),
		fft4K (3),
		fft1K (4),
		fft16K (5),
		fft32K (6)
	}
	MAX-ACCESS read-only
	STATUS     current
	DESCRIPTION
		"FFT size"
	::= { dttReceiver1T2Frame 25 }

dttRx1T2GuardInterval  OBJECT-TYPE
	SYNTAX     INTEGER {
		null (0),
		interval1div32 (1),
		interval1div16 (2),
		interval1div8 (3),
		interval1div4 (4),
		interval1div128 (5),
		interval19div128 (6),
		interval19div256 (7)
	}
	MAX-ACCESS read-only
	STATUS     current
	DESCRIPTION
		"Guard interval"
	::= { dttReceiver1T2Frame 30 }

dttRx1T2PaprReduction  OBJECT-TYPE
	SYNTAX     INTEGER {
		null (0),
		nullTrP2 (1),
		ace (2),
		tr (3),
		aceTr (4)
	}
	MAX-ACCESS read-only
	STATUS     current
	DESCRIPTION
		"PAPR reduction"
	::= { dttReceiver1T2Frame 35 }

dttRx1T2PilotPattern  OBJECT-TYPE
	SYNTAX     INTEGER {
		null (0),
		pp1 (1),
		pp2 (2),
		pp3 (3),
		pp4 (4),
		pp5 (5),
		pp6 (6),
		pp7 (7),
		pp8 (8)
	}
	MAX-ACCESS read-only
	STATUS     current
	DESCRIPTION
		"Pilot pattern"
	::= { dttReceiver1T2Frame 40 }

dttRx1T2FramesPerSuperframe  OBJECT-TYPE
	SYNTAX     Unsigned32 (2..256)
	MAX-ACCESS read-only
	STATUS     current
	DESCRIPTION
		"Number of T2 frames per superframe"
	::= { dttReceiver1T2Frame 45 }

dttRx1T2OfdmSymbolsPerSuperframe  OBJECT-TYPE
	SYNTAX     Unsigned32 (0..4095)
	MAX-ACCESS read-only
	STATUS     current
	DESCRIPTION
		"Number of OFDM symbols per T2 frame"
	::= { dttReceiver1T2Frame 50 }

--- Receiver DVB-T2 PLP

dttRx1NumberOfPlps  OBJECT-TYPE
	SYNTAX     Unsigned32 (0..255)
	MAX-ACCESS read-only
	STATUS     current
	DESCRIPTION
		"Total number of PLPs"
	::= { dttReceiver1T2PLP 5 }

dttRx1PlpId  OBJECT-TYPE
	SYNTAX     Unsigned32 (0..255)
	MAX-ACCESS read-only
	STATUS     current
	DESCRIPTION
		"Selected PLP ID"
	::= { dttReceiver1T2PLP 10 }

dttRx1T2PlpType  OBJECT-TYPE
	SYNTAX     INTEGER {
		null (0),
		common (1),
		data1 (2),
		data2 (3)
	}
	MAX-ACCESS read-only
	STATUS     current
	DESCRIPTION
		"PLP type"
	::= { dttReceiver1T2PLP 15 }

dttRx1T2PlpMode  OBJECT-TYPE
	SYNTAX     INTEGER {
		null (0),
		nm (1),
		hem (2)
	}
	MAX-ACCESS read-only
	STATUS     current
	DESCRIPTION
		"PLP mode"
	::= { dttReceiver1T2PLP 20 }

dttRx1T2PlpGroupId  OBJECT-TYPE
	SYNTAX     Unsigned32 (0..255)
	MAX-ACCESS read-only
	STATUS     current
	DESCRIPTION
		"PLP Group ID"
	::= { dttReceiver1T2PLP 25 }

dttRx1T2PlpConstellation  OBJECT-TYPE
	SYNTAX     INTEGER {
		null (0),
		qpsk (1),
		qam16 (2),
		qam64 (3),
		qam256 (4)
	}
	MAX-ACCESS read-only
	STATUS     current
	DESCRIPTION
		"PLP Constellation"
	::= { dttReceiver1T2PLP 30 }

dttRx1T2PlpRotatedConstellation  OBJECT-TYPE
	SYNTAX     INTEGER {
		null (0),
		disable (1),
		enable (2)
	}
	MAX-ACCESS read-only
	STATUS     current
	DESCRIPTION
		"Roted Constellation"
	::= { dttReceiver1T2PLP 35 }

dttRx1T2FecType  OBJECT-TYPE
	SYNTAX     INTEGER {
		null (0),
		ldpc16k (1),
		ldpc64k (2)
	}
	MAX-ACCESS read-only
	STATUS     current
	DESCRIPTION
		"FEC type"
	::= { dttReceiver1T2PLP 40 }

dttRx1T2CodeRate  OBJECT-TYPE
	SYNTAX     INTEGER {
		null (0),
		rate1div2 (1),
		rate3div5 (2),
		rate2div3 (3),
		rate3div4 (4),
		rate4div5 (5),
		rate5div6 (6),
		rate1div3 (7),
		rate2div5 (8)
	}
	MAX-ACCESS read-only
	STATUS     current
	DESCRIPTION
		"Code Rate"
	::= { dttReceiver1T2PLP 45 }

dttRx1T2NumberOfFecBlocks  OBJECT-TYPE
	SYNTAX     Unsigned32 (0..65535)
	MAX-ACCESS read-only
	STATUS     current
	DESCRIPTION
		"Number of FEC blocks"
	::= { dttReceiver1T2PLP 50 }

dttRx1T2TypeOfTimeInvervaling  OBJECT-TYPE
	SYNTAX     INTEGER {
		null (0),
		simple (1),
		multiple (2)
	}
	MAX-ACCESS read-only
	STATUS     current
	DESCRIPTION
		"Type of time-interleaving"
	::= { dttReceiver1T2PLP 55 }

dttRx1T2LengthOfTimeInvervaling  OBJECT-TYPE
	SYNTAX     Unsigned32 (0..255)
	MAX-ACCESS read-only
	STATUS     current
	DESCRIPTION
		"Length of time-interleaving"
	::= { dttReceiver1T2PLP 60 }

dttRx1T2InBandSignalling  OBJECT-TYPE
	SYNTAX     INTEGER {
		null (0),
		b (1),
		a (2),
		ab (3)
	}
	MAX-ACCESS read-only
	STATUS     current
	DESCRIPTION
		"In-band signalling"
	::= { dttReceiver1T2PLP 65 }

--- Receiver 1 DVB-T2 Measure

dttRx1T2BerBeforeLdpc  OBJECT-TYPE
	SYNTAX     DisplayString
	MAX-ACCESS read-only
	STATUS     current
	DESCRIPTION
		"BER Before LDPC"
	::= { dttReceiver1T2Measures 5 }

dttRx1T2BerBeforeBch  OBJECT-TYPE
	SYNTAX     DisplayString
	MAX-ACCESS read-only
	STATUS     current
	DESCRIPTION
		"BER Before BCH"
	::= { dttReceiver1T2Measures 10 }

dttRx1T2BbframeErrorRatio  OBJECT-TYPE
	SYNTAX     DisplayString
	MAX-ACCESS read-only
	STATUS     current
	DESCRIPTION
		"BBFRAME Error Ratio"
	::= { dttReceiver1T2Measures 15 }

-- Receiver ISDBT
-- Receiver ISDBT System

dttRx1IsdbtSystem  OBJECT-TYPE
	SYNTAX     INTEGER {
		null (0),
		isdb (1),
		isdbTsba (2),
		reserved2 (3),
		reserved3 (4)
	}
	MAX-ACCESS read-only
	STATUS     current
	DESCRIPTION
		"System"
	::= { dttReceiver1IsdbtSystem 5 }

dttRx1IsdbtMode  OBJECT-TYPE
	SYNTAX     Unsigned32
	MAX-ACCESS read-only
	STATUS     current
	DESCRIPTION
		"Tx Mode"
	::= { dttReceiver1IsdbtSystem 10 }

dttRx1IsdbtGuard  OBJECT-TYPE
	SYNTAX     INTEGER {
		null(0),
		guard1div32(1),
		guard1div16(2),
		guard1div8(3),
		guard1div4(4),
		unknown(5)
	}
	MAX-ACCESS read-only
	STATUS     current
	DESCRIPTION
		"Guard Interval"
	::= { dttReceiver1IsdbtSystem 15 }

dttRx1IsdbtEws  OBJECT-TYPE
	SYNTAX     INTEGER {
		null(0),
		off(1),
		on(2)
	}
	MAX-ACCESS read-only
	STATUS     current
	DESCRIPTION
		"EWS"
	::= { dttReceiver1IsdbtSystem 20 }

dttRx1IsdbtPartialRx  OBJECT-TYPE
	SYNTAX     INTEGER {
		null(0),
		off(1),
		on(2)
	}
	MAX-ACCESS read-only
	STATUS     current
	DESCRIPTION
		"Partial Rx"
	::= { dttReceiver1IsdbtSystem 25 }

-- Receiver ISDBT Layer A

dttRx1IsdbtLASegments  OBJECT-TYPE
	SYNTAX     Unsigned32
	MAX-ACCESS read-only
	STATUS     current
	DESCRIPTION
		"Segments"
	::= { dttReceiver1IsdbtLayerA 5 }

dttRx1IsdbtLAInterleaveLength  OBJECT-TYPE
	SYNTAX     Unsigned32
	MAX-ACCESS read-only
	STATUS     current
	DESCRIPTION
		"Interleave Length"
	::= { dttReceiver1IsdbtLayerA 10 }

dttRx1IsdbtLAConstellation  OBJECT-TYPE
	SYNTAX     IsdbtLayerConstellation 
	MAX-ACCESS read-only
	STATUS     current
	DESCRIPTION
		"Constellation"
	::= { dttReceiver1IsdbtLayerA 15 }

dttRx1IsdbtLACodeRate  OBJECT-TYPE
	SYNTAX     IsdbtLayerCodeRate
	MAX-ACCESS read-only
	STATUS     current
	DESCRIPTION
		"Code Rate"
	::= { dttReceiver1IsdbtLayerA 20 }

dttRx1IsdbtLACber  OBJECT-TYPE
	SYNTAX     DisplayString
	MAX-ACCESS read-only
	STATUS     current
	DESCRIPTION
		"CBER"
	::= { dttReceiver1IsdbtLayerA 23 }

dttRx1IsdbtLABERbeforeRS  OBJECT-TYPE
	SYNTAX     DisplayString
	MAX-ACCESS read-only
	STATUS     current
	DESCRIPTION
		"BER before RS"
	::= { dttReceiver1IsdbtLayerA 25 }

-- Receiver ISDBT Layer B

dttRx1IsdbtLBSegments  OBJECT-TYPE
	SYNTAX     Unsigned32
	MAX-ACCESS read-only
	STATUS     current
	DESCRIPTION
		"Segments"
	::= { dttReceiver1IsdbtLayerB 5 }

dttRx1IsdbtLBInterleaveLength  OBJECT-TYPE
	SYNTAX     Unsigned32
	MAX-ACCESS read-only
	STATUS     current
	DESCRIPTION
		"Interleave Length"
	::= { dttReceiver1IsdbtLayerB 10 }

dttRx1IsdbtLBConstellation  OBJECT-TYPE
	SYNTAX     IsdbtLayerConstellation 
	MAX-ACCESS read-only
	STATUS     current
	DESCRIPTION
		"Constellation"
	::= { dttReceiver1IsdbtLayerB 15 }

dttRx1IsdbtLBCodeRate  OBJECT-TYPE
	SYNTAX     IsdbtLayerCodeRate
	MAX-ACCESS read-only
	STATUS     current
	DESCRIPTION
		"Code Rate"
	::= { dttReceiver1IsdbtLayerB 20 }

dttRx1IsdbtLBCber  OBJECT-TYPE
	SYNTAX     DisplayString
	MAX-ACCESS read-only
	STATUS     current
	DESCRIPTION
		"CBER"
	::= { dttReceiver1IsdbtLayerB 23 }

dttRx1IsdbtLBBERbeforeRS  OBJECT-TYPE
	SYNTAX     DisplayString
	MAX-ACCESS read-only
	STATUS     current
	DESCRIPTION
		"BER before RS"
	::= { dttReceiver1IsdbtLayerB 25 }

-- Receiver ISDBT Layer C

dttRx1IsdbtLCSegments  OBJECT-TYPE
	SYNTAX     Unsigned32
	MAX-ACCESS read-only
	STATUS     current
	DESCRIPTION
		"Segments"
	::= { dttReceiver1IsdbtLayerC 5 }

dttRx1IsdbtLCInterleaveLength  OBJECT-TYPE
	SYNTAX     Unsigned32
	MAX-ACCESS read-only
	STATUS     current
	DESCRIPTION
		"Interleave Length"
	::= { dttReceiver1IsdbtLayerC 10 }

dttRx1IsdbtLCConstellation  OBJECT-TYPE
	SYNTAX     IsdbtLayerConstellation 
	MAX-ACCESS read-only
	STATUS     current
	DESCRIPTION
		"Constellation"
	::= { dttReceiver1IsdbtLayerC 15 }

dttRx1IsdbtLCCodeRate  OBJECT-TYPE
	SYNTAX     IsdbtLayerCodeRate
	MAX-ACCESS read-only
	STATUS     current
	DESCRIPTION
		"Code Rate"
	::= { dttReceiver1IsdbtLayerC 20 }

dttRx1IsdbtLCCber  OBJECT-TYPE
	SYNTAX     DisplayString
	MAX-ACCESS read-only
	STATUS     current
	DESCRIPTION
		"CBER"
	::= { dttReceiver1IsdbtLayerC 23 }

dttRx1IsdbtLCBERbeforeRS  OBJECT-TYPE
	SYNTAX     DisplayString
	MAX-ACCESS read-only
	STATUS     current
	DESCRIPTION
		"BER before RS"
	::= { dttReceiver1IsdbtLayerC 25 }


-- Receiver Common Measures

dttRx1Mer  OBJECT-TYPE
	SYNTAX     DisplayString
	UNITS	"dB"
	MAX-ACCESS read-only
	STATUS     current
	DESCRIPTION
		"MER"
	::= { dttReceiver1CommonMeasures 5 }

dttRx1Snr  OBJECT-TYPE
	SYNTAX     DisplayString
	UNITS	"dB"
	MAX-ACCESS read-only
	STATUS     current
	DESCRIPTION
		"SNR"
	::= { dttReceiver1CommonMeasures 10 }

dttRx1Level  OBJECT-TYPE
	SYNTAX     DisplayString
	UNITS	"dBm"
	MAX-ACCESS read-only
	STATUS     current
	DESCRIPTION
		"Level"
	::= { dttReceiver1CommonMeasures 15 }

-- Receiver Sat 1
-- Demodulador. 

dstReceiver1Enable  OBJECT-TYPE
	SYNTAX     DisabledEnabled
	MAX-ACCESS read-write
	STATUS     current
	DESCRIPTION
		"Enable/Disable DST receiver 1"
	::= { dstReceiver1Demodulator 5 }

dstReceiver1Status  OBJECT-TYPE
	SYNTAX     INTEGER {
		unlocked (0),
		locked (1),
		disabled (2)
	}
	MAX-ACCESS read-only
	STATUS     current
	DESCRIPTION
		"Status"
	::= { dstReceiver1Demodulator 10 }

dstReceiver1Temperature  OBJECT-TYPE
	SYNTAX     FloatingPoint
	UNITS	"Celsius"
	MAX-ACCESS read-only
	STATUS     current
	DESCRIPTION
		"Status"
	::= { dstReceiver1Demodulator 15 }

dstReceiver1Band  OBJECT-TYPE
	SYNTAX     INTEGER {
		ku(0),
		c(1)
	}
	MAX-ACCESS read-write
	STATUS     current
	DESCRIPTION
		"Band"
	::= { dstReceiver1DemFrequency 3 }

dstReceiver1Frequency  OBJECT-TYPE
	SYNTAX     FloatingPoint
	UNITS 	"MHz"
	MAX-ACCESS read-write
	STATUS     current
	DESCRIPTION
		"Frequency"
	::= { dstReceiver1DemFrequency 5 }

dstReceiver1Polarization  OBJECT-TYPE
	SYNTAX     INTEGER {
		vertical (0),
		horizontal (1)
	}
	MAX-ACCESS read-write
	STATUS     current
	DESCRIPTION
		"Polarization"
	::= { dstReceiver1DemFrequency 10 }

dstReceiver1Satellite  OBJECT-TYPE
	SYNTAX     INTEGER {
		satelliteA (0),
		satelliteB (1),
		satelliteC (2),
		satelliteD (3)
	}
	MAX-ACCESS read-write
	STATUS     current
	DESCRIPTION
		"Satellite"
	::= { dstReceiver1DemFrequency 15 }

dstReceiver1DvbMode  OBJECT-TYPE
	SYNTAX     INTEGER {
		dvbS (1),
		dvbS2 (2)
	}
	MAX-ACCESS read-write
	STATUS     current
	DESCRIPTION
		"DVB mode"
	::= { dstReceiver1DemModulation 5 }

dstReceiver1SymbolRateMode  OBJECT-TYPE
	SYNTAX     INTEGER {
		manual (0),
		auto (1)
	}
	MAX-ACCESS read-write
	STATUS     current
	DESCRIPTION
		"Symbol rate mode"
	::= { dstReceiver1DemModulation 10 }

dstReceiver1ConfiguredSymbolRate  OBJECT-TYPE
	SYNTAX     Unsigned32 (1000..45000)
	UNITS "KS/s"
	MAX-ACCESS read-write
	STATUS     current
	DESCRIPTION
		"Configured symbol rate"
	::= { dstReceiver1DemModulation 15 }

dstReceiver1MeasuredSymbolRate  OBJECT-TYPE
	SYNTAX     Unsigned32
	UNITS "KS/s"
	MAX-ACCESS read-only
	STATUS     current
	DESCRIPTION
		"Measured symbol rate"
	::= { dstReceiver1DemModulation 20 }
	
dstReceiver1Rolloff  OBJECT-TYPE
	SYNTAX     INTEGER{
		rollOff035 (0),
		rollOff025 (1),
		rollOff020 (2)
	}
	MAX-ACCESS read-only
	STATUS     current
	DESCRIPTION
		"Roll-off"
	::= { dstReceiver1DemModulation 25 }
	
dstReceiver1Pilots  OBJECT-TYPE
	SYNTAX     NoYes
	MAX-ACCESS read-only
	STATUS     current
	DESCRIPTION
		"Pilots"
	::= { dstReceiver1DemModulation 30 }
	
dstReceiver1FrameLength  OBJECT-TYPE
	SYNTAX     INTEGER {
		long(0),
		short(1)
	}
	MAX-ACCESS read-only
	STATUS     current
	DESCRIPTION
		"Frame length"
	::= { dstReceiver1DemModulation 35 }
	
dstReceiver1Modulation  OBJECT-TYPE
	SYNTAX     INTEGER {
		modQPSK (0),
		mod8PSK (1),
		mod16APSK (2),
		mod32APSK (3),
		modNull (4)
	}
	MAX-ACCESS read-only
	STATUS     current
	DESCRIPTION
		"Modulation"
	::= { dstReceiver1DemModulation 40 }
	
dstReceiver1Fec  OBJECT-TYPE
	SYNTAX     INTEGER {
		fec1d2 (0),
		fec2d3 (1),
		fec3d4 (2),
		fec4d5 (3),
		fec5d6 (4),
		fec6d7 (5),
		fec7d8 (6),
		fec8d9 (7),
		fecNull (8),
		fec1d4 (9),
		fec1d3 (10),
		fec2d5 (11),
		fec3d5 (12),
		fec9d10 (13)
	}
	MAX-ACCESS read-only
	STATUS     current
	DESCRIPTION
		"FEC"
	::= { dstReceiver1DemModulation 45 }

dstReceiver1PlsMode  OBJECT-TYPE
	SYNTAX     INTEGER {
		gols (0),
		root (1)
	}
	MAX-ACCESS read-write
	STATUS     current
	DESCRIPTION
		"PLS Mode"
	::= { dstReceiver1DemScrambling 5 }

dstReceiver1Pls  OBJECT-TYPE
	SYNTAX     Unsigned32(0..262143)
	MAX-ACCESS read-write
	STATUS     current
	DESCRIPTION
		"PLS"
	::= { dstReceiver1DemScrambling 10 }

-- Demodulador. Quality DVB-S 

dstReceiver1Cber  OBJECT-TYPE
	SYNTAX     FloatingPoint
	MAX-ACCESS read-only
	STATUS     current
	DESCRIPTION
		"CBER (only DVB-S)"
	::= { dstReceiver1DemQuality 5 }

dstReceiver1Vber  OBJECT-TYPE
	SYNTAX     FloatingPoint
	MAX-ACCESS read-only
	STATUS     current
	DESCRIPTION
		"VBER (only DVB-S)"
	::= { dstReceiver1DemQuality 10 }

-- Demodulador. Quality DVB-S 2

dstReceiver1Ldpc  OBJECT-TYPE
	SYNTAX     FloatingPoint
	MAX-ACCESS read-only
	STATUS     current
	DESCRIPTION
		"LDPC (only DVB-S2)"
	::= { dstReceiver1DemQuality 15 }

dstReceiver1Per  OBJECT-TYPE
	SYNTAX     FloatingPoint
	MAX-ACCESS read-only
	STATUS     current
	DESCRIPTION
		"PER (only DVB-S2)"
	::= { dstReceiver1DemQuality 20 }

-- Demodulador. Quality CN (Common)

dstReceiver1CN  OBJECT-TYPE
	SYNTAX     FloatingPoint
	MAX-ACCESS read-only
	STATUS     current
	DESCRIPTION
		"CN (DVB-S and DVB-S2)"
	::= { dstReceiver1DemQuality 25 }

-- Demodulador. Quality DVB-S 2

-- dstReceiver1Bch  OBJECT-TYPE
-- 	SYNTAX     FloatingPoint
-- 	MAX-ACCESS read-only
-- 	STATUS     current
-- 	DESCRIPTION
-- 		"BCH (only DVB-S2)"
-- 	::= { dstReceiver1DemQuality 30 }

dstReceiver1LinkMarginThreshold  OBJECT-TYPE
	SYNTAX     Unsigned32(0..15)
	UNITS "dB"
	MAX-ACCESS read-write
	STATUS     current
	DESCRIPTION
		"Link margin threshold (only DVB-S2)"
	::= { dstReceiver1DemQuality 35 }

dstReceiver1LinkMargin  OBJECT-TYPE
	SYNTAX     Unsigned32(0..15)
	UNITS "dB"
	MAX-ACCESS read-write
	STATUS     current
	DESCRIPTION
		"Link margin (only DVB-S2)"
	::= { dstReceiver1DemQuality 40 }

dstReceiver1Attenuation  OBJECT-TYPE
	SYNTAX     Unsigned32(0..15)
	UNITS "dB"
	MAX-ACCESS read-write
	STATUS     current
	DESCRIPTION
		"Attenuation"
	::= { dstReceiver1DemQuality 42 }

-- Demodulador. Level common

dstReceiver1Level  OBJECT-TYPE
	SYNTAX     FloatingPoint
	UNITS "dBm"
	MAX-ACCESS read-only
	STATUS     current
	DESCRIPTION
		"Level (DVB-S and DVB-S2)"
	::= { dstReceiver1DemQuality 45 }

-- LNB

dstReceiver1Mode  OBJECT-TYPE
	SYNTAX     INTEGER {
		single (0),
		dual (1),
		manual (2)
	}
	MAX-ACCESS read-write
	STATUS     current
	DESCRIPTION
		"Mode"
	::= { dstReceiver1Lnb 5 }

dstReceiver1LnbStatus  OBJECT-TYPE
	SYNTAX     DisplayString
	MAX-ACCESS read-only
	STATUS     current
	DESCRIPTION
		"Status"
	::= { dstReceiver1Lnb 10 }

dstReceiver1LnbOlLow  OBJECT-TYPE
	SYNTAX     Unsigned32 (0..65535)
	MAX-ACCESS read-only
	STATUS     current
	DESCRIPTION
		"OL (Single/Dual low band)"
	::= { dstReceiver1LnbSingleDualMode 5 }

dstReceiver1LnbBandSwitchingFreq  OBJECT-TYPE
	SYNTAX     Unsigned32 (0..65535)
	MAX-ACCESS read-only
	STATUS     current
	DESCRIPTION
		"Band switching frequency"
	::= { dstReceiver1LnbSingleDualMode 10 }

dstReceiver1LnbOlHigh  OBJECT-TYPE
	SYNTAX     Unsigned32 (0..65535)
	MAX-ACCESS read-only
	STATUS     current
	DESCRIPTION
		"OL (Dual high band)"
	::= { dstReceiver1LnbSingleDualMode 15 }

dstReceiver1Voltage  OBJECT-TYPE
	SYNTAX     INTEGER {
		lnbVoltageOff (0),
		lnbVoltage13V (1),
		lnbVoltage18V (2)
	}
	MAX-ACCESS read-write
	STATUS     current
	DESCRIPTION
		"Voltage"
	::= { dstReceiver1LnbManualMode 5 }

dstReceiver1Tone22kHz  OBJECT-TYPE
	SYNTAX     INTEGER {
		off (0),
		on (1)
	}
	MAX-ACCESS read-write
	STATUS     current
	DESCRIPTION
		"22kHz tone"
	::= { dstReceiver1LnbManualMode 10 }

dstReceiver1OlManual  OBJECT-TYPE
	SYNTAX     Unsigned32 (0..65535)
	MAX-ACCESS read-write
	STATUS     current
	DESCRIPTION
		"OL (Manual)"
	::= { dstReceiver1LnbManualMode 15 }

-- TS

dstReceiver1TsAvailableIsis  OBJECT-TYPE
	SYNTAX     DisplayString
	MAX-ACCESS read-only
	STATUS     current
	DESCRIPTION
		"Available ISIs (only DVB-S2)"
	::= { dstReceiver1Ts 5 }

dstReceiver1TsIsi  OBJECT-TYPE
	SYNTAX     Unsigned32 (0..255)
	MAX-ACCESS read-write
	STATUS     current
	DESCRIPTION
		"ISI (only DVB-S2)"
	::= { dstReceiver1Ts 10 }

dstReceiver1TsRate  OBJECT-TYPE
	SYNTAX     Unsigned32
	UNITS "bps"
	MAX-ACCESS read-write
	STATUS     current
	DESCRIPTION
		"Rate"
	::= { dstReceiver1TsAsiOutput 5 }

dstReceiver1TsMode  OBJECT-TYPE
	SYNTAX     INTEGER {
		byte (0),
		burst (1)
	}
	MAX-ACCESS read-write
	STATUS     current
	DESCRIPTION
		"Mode"
	::= { dstReceiver1TsAsiOutput 10 }

dstReceiver1TsBissEnable  OBJECT-TYPE
	SYNTAX     DisabledEnabled
	MAX-ACCESS read-write
	STATUS     current
	DESCRIPTION
		"BISS"
	::= { dstReceiver1TsBiss 5 }

dstReceiver1TsBissMode  OBJECT-TYPE
	SYNTAX     INTEGER {
		mode1 (0),
		modeE (1)
	}
	MAX-ACCESS read-write
	STATUS     current
	DESCRIPTION
		"Mode"
	::= { dstReceiver1TsBiss 10 }

dstReceiver1TsBissPass  OBJECT-TYPE
	SYNTAX     OCTET STRING (SIZE(1..16))
	MAX-ACCESS read-write
	STATUS     current
	DESCRIPTION
		"Pass"
	::= { dstReceiver1TsBiss 15 }

dstReceiver1TsBissInjectId  OBJECT-TYPE
	SYNTAX     OCTET STRING (SIZE(1..14))
	MAX-ACCESS read-write
	STATUS     current
	DESCRIPTION
		"Inject ID"
	::= { dstReceiver1TsBiss 20 }

dstReceiver1TsCamEnable  OBJECT-TYPE
	SYNTAX     DisabledEnabled
	MAX-ACCESS read-write
	STATUS     current
	DESCRIPTION
		"CAM"
	::= { dstReceiver1TsCam 5 }

dstReceiver1TsCamStatus  OBJECT-TYPE
	SYNTAX     INTEGER {
		disabled (0),
		notInserted (1),
		inserted (2),
		waiting (3),
		readingCis (4),
		ready (5),
		wrongSmartCard (6),
		noSmartCard (7),
		notReady (8)
	}
	MAX-ACCESS read-only
	STATUS     current
	DESCRIPTION
		"Status"
	::= { dstReceiver1TsCam 10 }

dstReceiver1TsCamReset  OBJECT-TYPE
	SYNTAX     NullApply 
	MAX-ACCESS read-write
	STATUS     current
	DESCRIPTION
		"CAM Reset"
	::= { dstReceiver1TsCam 25 }

dstServicesTable  OBJECT-TYPE
	SYNTAX SEQUENCE OF DstServicesEntry
	MAX-ACCESS not-accessible
	STATUS     current
	DESCRIPTION
		"Table for trapsinks configuration"
	::= { dstReceiver1Ts 25 }

dstServicesEntry  OBJECT-TYPE
	SYNTAX 	DstServicesEntry
	MAX-ACCESS not-accessible
	STATUS     current
	DESCRIPTION
		"Entry for a trapsink"
	INDEX { dstServiceIndex }
	::= { dstServicesTable 1 }

DstServicesEntry ::= SEQUENCE {
	dstServiceIndex
		Unsigned32,
	dstDecryptEnable
		DisabledEnabled,
	dstProgramId
		Unsigned32,
	dstServiceName
		OCTET STRING,
	dstServiceStatus
		INTEGER
}

dstServiceIndex  OBJECT-TYPE
	SYNTAX     Unsigned32 (1..9)
	MAX-ACCESS not-accessible
	STATUS     current
	DESCRIPTION
		"DST Service sink"
	::= { dstServicesEntry 1 }

dstDecryptEnable  OBJECT-TYPE
	SYNTAX     DisabledEnabled
	MAX-ACCESS read-write
	STATUS     current
	DESCRIPTION
		"DST decrypt enable"
	::= { dstServicesEntry 2 }

dstProgramId  OBJECT-TYPE
	SYNTAX     Unsigned32
	MAX-ACCESS read-only
	STATUS     current
	DESCRIPTION
		"DST Program"
	::= { dstServicesEntry 3 }

dstServiceName  OBJECT-TYPE
	SYNTAX     OCTET STRING
	MAX-ACCESS read-write
	STATUS     current
	DESCRIPTION
		"Name"
	::= { dstServicesEntry 4 }

dstServiceStatus  OBJECT-TYPE
	SYNTAX     INTEGER {
		null (0),
		decryptingId (1),
		decryptingErr (2)
	}
	MAX-ACCESS read-write
	STATUS     current
	DESCRIPTION
		"Status"
	::= { dstServicesEntry 5 }

--- dstReceiver1TsEtiOutput

dstR1TsEtiOutputPid  OBJECT-TYPE
	SYNTAX     Unsigned32 (0..8191)
	MAX-ACCESS read-write
	STATUS     current
	DESCRIPTION
		"PID"
	::= { dstReceiver1TsEtiOutput 5 }

dstR1TsEtiOutputType  OBJECT-TYPE
	SYNTAX     INTEGER {
		etiNa (0),
		tsEtiV11 (1),
		edi (2)
	}
	MAX-ACCESS read-write
	STATUS     current
	DESCRIPTION
		"Type"
	::= { dstReceiver1TsEtiOutput 10 }

dstR1TsEtiOutputStreamTo  OBJECT-TYPE
	SYNTAX     INTEGER {
		null (0),
		socket1 (1),
		socket2 (2),
		socket1and2 (3)
	}
	MAX-ACCESS read-write
	STATUS     current
	DESCRIPTION
		"Satellite EDI stream to..."
	::= { dstReceiver1TsEtiOutput 12 }

dstR1TsEtiOutputLayer  OBJECT-TYPE
	SYNTAX     INTEGER {
		null (0),
		etiNi (1),
		etiNa5592 (2),
		etiNa5376 (3)
	}
	MAX-ACCESS read-only
	STATUS     current
	DESCRIPTION
		"Layer"
	::= { dstReceiver1TsEtiOutput 15 }

dstR1TsEtiOutputInputBitrate  OBJECT-TYPE
	SYNTAX     FloatingPoint
	MAX-ACCESS read-only
	STATUS     current
	DESCRIPTION
		"Intput Bitrate"
	::= { dstReceiver1TsEtiOutput 20 }

dstR1TsEOCorrectedRsCodewords  OBJECT-TYPE
	SYNTAX     Unsigned32
	MAX-ACCESS read-only
	STATUS     current
	DESCRIPTION
		"Corrected RS codewords"
	::= { dstR1TsEtiOutputStatistics 5 }

dstR1TsEONotCorrectedRsCodewords  OBJECT-TYPE
	SYNTAX     Unsigned32
	MAX-ACCESS read-only
	STATUS     current
	DESCRIPTION
		"Not corrected RS codewords"
	::= { dstR1TsEtiOutputStatistics 10 }

dstR1TsEtiOutputWithouService  OBJECT-TYPE
	SYNTAX     FloatingPoint
	MAX-ACCESS read-only
	STATUS     current
	DESCRIPTION
		"Time without service"
	::= { dstR1TsEtiOutputStatistics 12 }

dstR1TsEOResetCounters  OBJECT-TYPE
	SYNTAX     NullApply
	MAX-ACCESS read-write
	STATUS     current
	DESCRIPTION
		"Reset statistics"
	::= { dstR1TsEtiOutputStatistics 15 }

--- Setup > Exciter > RfInput > RfInputConfiguration

inputFrequencyMode  OBJECT-TYPE
	SYNTAX     INTEGER {
		channel (0),
		centralFrequency (1)
	}
	MAX-ACCESS read-write
	STATUS     current
	DESCRIPTION
		"Input Frequency mode"
	::= { rfInputConfiguration 1 }


inputFrequency  OBJECT-TYPE
	SYNTAX     DisplayString
	MAX-ACCESS read-only
	STATUS     current
	DESCRIPTION
		"Input Frequency"
	::= { rfInputConfiguration 2 }

inputLevel  OBJECT-TYPE
	SYNTAX     DisplayString
	MAX-ACCESS read-only
	STATUS     current
	DESCRIPTION
		"Input Level"
	::= { rfInputConfiguration 3 }

inputLevelThreshold  OBJECT-TYPE
	SYNTAX     Integer32 (-85..-55)
	UNITS 	"dBm"
	MAX-ACCESS read-write
	STATUS     current
	DESCRIPTION
		"Input Level threshold"
	::= { rfInputConfiguration 4 }

inputFrequencyFlt  OBJECT-TYPE
	SYNTAX     FloatingPoint
	UNITS 	"Hz"
	MAX-ACCESS read-only
	STATUS     current
	DESCRIPTION
		"Input frequency"
	::= { rfInputConfiguration 5 }


inputChannel  OBJECT-TYPE
	SYNTAX     Unsigned32 (14..78)
	MAX-ACCESS read-write
	STATUS     current
	DESCRIPTION
		"Output channel"
	::= { inputChannelMode 1 }

inputChannelOffset  OBJECT-TYPE
	SYNTAX     Integer32 (-4..4)
	MAX-ACCESS read-write
	STATUS     current
	DESCRIPTION
		"Channel offset"
	::= { inputChannelMode 2 }

inputChannelResolution  OBJECT-TYPE
	SYNTAX     INTEGER {
		resolution1div6 (0),
		resolution1div7 (1),
		resolution1div8 (2)
	}
	UNITS 	"MHz"
	MAX-ACCESS read-write
	STATUS     current
	DESCRIPTION
		"Channel resolution"
	::= { inputChannelMode 3 }

inputChannelChannel  OBJECT-TYPE
	SYNTAX     DabOutputChannelType
	UNITS 	"MHz"
	MAX-ACCESS read-write
	STATUS     current
	DESCRIPTION
		"Channel"
	::= { inputChannelMode 4 }

inputCentralFrequency  OBJECT-TYPE
	SYNTAX     Unsigned32 (470000000..862000000)
	UNITS 	"Hz"
	MAX-ACCESS read-write
	STATUS     current
	DESCRIPTION
		"Central Frequency"
	::= { inputCentralFrequencyMode 1 }

inputCentralFrequencyMHz  OBJECT-TYPE
	SYNTAX     Unsigned32 (470000..862000)
	UNITS 	"MHz"
	MAX-ACCESS read-write
	STATUS     current
	DESCRIPTION
		"Central Frequency"
	::= { inputCentralFrequencyMode 2 }

ecTemperature  OBJECT-TYPE
	SYNTAX     DisplayString
	MAX-ACCESS read-only
	STATUS     current
	DESCRIPTION
		"Echo canceller temperature board"
	::= { ecGeneral 1 }

-- echoCancellerEnable  OBJECT-TYPE
--	SYNTAX     INTEGER {
--		off (0),
--		on (1)
--	}
--	MAX-ACCESS read-write
--	STATUS     deprecated
--	DESCRIPTION
--		" "
--	::= { ecSystem 1 }
-- echoCancellationEnable  OBJECT-TYPE
--	SYNTAX     INTEGER {
--		off (0),
--		on (1)
--	}
--	MAX-ACCESS read-write
--	STATUS     deprecated
--	DESCRIPTION
--		" "
--	::= { ecSystem 2 }

ecBandwidth  OBJECT-TYPE
	SYNTAX     INTEGER {
		bw5Mhz (0),
		bw6Mhz (1),
		bw7Mhz (2),
		bw8Mhz (3)
	}
	MAX-ACCESS read-only
	STATUS     current
	DESCRIPTION
		"Bandwidth"
	::= { ecSystem 3 }

ecBandwidthAdaptation  OBJECT-TYPE
	SYNTAX     INTEGER {
		dvbTT2 (0),
		dvbT2Ext8k (1),
		dvbT2Ext16K32K (2),
		isdbTExt (3),
		atsc3 (5)
	}
	MAX-ACCESS read-write
	STATUS     current
	DESCRIPTION
		"Bandwitdh adaptation"
	::= { ecSystem 4 }

ecAdditionDelay  OBJECT-TYPE
	SYNTAX     OCTET STRING (SIZE(1..3))
	UNITS	"us"
	MAX-ACCESS read-write
	STATUS     current
	DESCRIPTION
		"Additional delay

		The value must be 0..1 in 0.1 step (0.0 .. 1.0)"
	::= { ecSystem 5 }

ecCurrentDelay  OBJECT-TYPE
	SYNTAX     DisplayString
	UNITS 	"us"
	MAX-ACCESS read-only
	STATUS     current
	DESCRIPTION
		"Current delay"
	::= { ecSystem 6 }

-- IF processor levels

ecInputLevel  OBJECT-TYPE
	SYNTAX     DisplayString
	UNITS 	"dBFS"
	MAX-ACCESS read-only
	STATUS     current
	DESCRIPTION
		"Input"
	::= { ecLevels 1 }

ecReferenceLevel  OBJECT-TYPE
	SYNTAX     DisplayString
	UNITS 	"dBFS"
	MAX-ACCESS read-only
	STATUS     current
	DESCRIPTION
		"Reference"
	::= { ecLevels 2 }

ecCancellationLevel  OBJECT-TYPE
	SYNTAX     DisplayString
	UNITS 	"dBFS"
	MAX-ACCESS read-only
	STATUS     current
	DESCRIPTION
		"Cancellation"
	::= { ecLevels 3 }

ecOutputCancellation  OBJECT-TYPE
	SYNTAX     DisplayString
	UNITS 	"dBFS"
	MAX-ACCESS read-only
	STATUS     current
	DESCRIPTION
		"Ouput"
	::= { ecLevels 4 }

-- Echo canceller

ecEnable  OBJECT-TYPE
	SYNTAX     DisabledEnabled
	MAX-ACCESS read-write
	STATUS     current
	DESCRIPTION
		"Echo cancellation"
	::= { ecWindows 1 }

muteGainMarginThreshold  OBJECT-TYPE
	SYNTAX     Integer32 (-20..10)
	MAX-ACCESS read-write
	STATUS     current
	DESCRIPTION
		"Gain margin threshold"
	::= { ecWindows 2 }

ecGainMargin  OBJECT-TYPE
	SYNTAX     DisplayString
	UNITS 	"dB"
	MAX-ACCESS read-only
	STATUS     current
	DESCRIPTION
		"Gain margin"
	::= { ecWindows 3 }

-- ecMode  OBJECT-TYPE
-- 	SYNTAX     INTEGER {
-- 		manual (0),
-- 		automatic (1)
-- 	}
-- 	MAX-ACCESS read-write
-- 	STATUS     current
-- 	DESCRIPTION
-- 		"Mode"
-- 	::= { ecWindows 3 }

-- Window speed

ecWindow01  OBJECT-TYPE
	SYNTAX     Unsigned32 (0..7)
	MAX-ACCESS read-write
	STATUS     current
	DESCRIPTION
		"Window 1"
	::= { ecWindowSpeed 1 }

ecWindow02  OBJECT-TYPE
	SYNTAX     Unsigned32 (0..7)
	MAX-ACCESS read-write
	STATUS     current
	DESCRIPTION
		"Window 2"
	::= { ecWindowSpeed 2 }

ecWindow03  OBJECT-TYPE
	SYNTAX     Unsigned32 (0..7)
	MAX-ACCESS read-write
	STATUS     current
	DESCRIPTION
		"Window 3"
	::= { ecWindowSpeed 3 }

ecWindow04  OBJECT-TYPE
	SYNTAX     Unsigned32 (0..7)
	MAX-ACCESS read-write
	STATUS     current
	DESCRIPTION
		"Window 4"
	::= { ecWindowSpeed 4 }

ecWindow05  OBJECT-TYPE
	SYNTAX     Unsigned32 (0..7)
	MAX-ACCESS read-write
	STATUS     current
	DESCRIPTION
		"Window 5"
	::= { ecWindowSpeed 5 }

ecWindow06  OBJECT-TYPE
	SYNTAX     Unsigned32 (0..7)
	MAX-ACCESS read-write
	STATUS     current
	DESCRIPTION
		"Window 6"
	::= { ecWindowSpeed 6 }

ecWindow07  OBJECT-TYPE
	SYNTAX     Unsigned32 (0..7)
	MAX-ACCESS read-write
	STATUS     current
	DESCRIPTION
		"Window 7"
	::= { ecWindowSpeed 7 }

ecWindow08  OBJECT-TYPE
	SYNTAX     Unsigned32 (0..7)
	MAX-ACCESS read-write
	STATUS     current
	DESCRIPTION
		"Window 8"
	::= { ecWindowSpeed 8 }

ecWindow09  OBJECT-TYPE
	SYNTAX     Unsigned32 (0..7)
	MAX-ACCESS read-write
	STATUS     current
	DESCRIPTION
		"Window 9"
	::= { ecWindowSpeed 9 }

ecWindow10  OBJECT-TYPE
	SYNTAX     Unsigned32 (0..7)
	MAX-ACCESS read-write
	STATUS     current
	DESCRIPTION
		"Window 10"
	::= { ecWindowSpeed 10 }

ecWindow11  OBJECT-TYPE
	SYNTAX     Unsigned32 (0..7)
	MAX-ACCESS read-write
	STATUS     current
	DESCRIPTION
		"Window 11"
	::= { ecWindowSpeed 11 }

ecWindow12  OBJECT-TYPE
	SYNTAX     Unsigned32 (0..7)
	MAX-ACCESS read-write
	STATUS     current
	DESCRIPTION
		"Window 12"
	::= { ecWindowSpeed 12 }

ecWindow13  OBJECT-TYPE
	SYNTAX     Unsigned32 (0..7)
	MAX-ACCESS read-write
	STATUS     current
	DESCRIPTION
		"Window 13"
	::= { ecWindowSpeed 13 }

ecWindow14  OBJECT-TYPE
	SYNTAX     Unsigned32 (0..7)
	MAX-ACCESS read-write
	STATUS     current
	DESCRIPTION
		"Window 14"
	::= { ecWindowSpeed 14 }

ecWindow15  OBJECT-TYPE
	SYNTAX     Unsigned32 (0..7)
	MAX-ACCESS read-write
	STATUS     current
	DESCRIPTION
		"Window 15"
	::= { ecWindowSpeed 15 }

ecWindow16  OBJECT-TYPE
	SYNTAX     Unsigned32 (0..7)
	MAX-ACCESS read-write
	STATUS     current
	DESCRIPTION
		"Window 16"
	::= { ecWindowSpeed 16 }

ecUnmuteRetriesInterval  OBJECT-TYPE
	SYNTAX     Unsigned32 (0..9999)
	UNITS 	"min"
	MAX-ACCESS read-write
	STATUS     current
	DESCRIPTION
		"Unmute retries interval"
	::= { ecWindows 10 }

-- Precorrection

ecLinearPrecorrection  OBJECT-TYPE
	SYNTAX     INTEGER {
		off (0),
		on (1)
	}
	UNITS 	"dB"
	MAX-ACCESS read-write
	STATUS     current
	DESCRIPTION
		"Linear precorrection. Enable/Disable"
	::= { ecPrecorrector 1 }

ecNonLinearPrecorrection  OBJECT-TYPE
	SYNTAX     INTEGER {
		off (0),
		adaptative (1),
		static (2)
	}
	MAX-ACCESS read-write
	STATUS     current
	DESCRIPTION
		"Non-linear precorrection mode"
	::= { ecPrecorrector 2 }

ecSlopeCorrection  OBJECT-TYPE
	SYNTAX     Integer32 (-3..3)
	MAX-ACCESS read-write
	STATUS     current
	DESCRIPTION
		"Slope correction"
	::= { ecPrecorrector 3 }

-- Precorrector levels

ecPrecorrectorInput  OBJECT-TYPE
	SYNTAX     DisplayString
	UNITS 	"dBFS"
	MAX-ACCESS read-only
	STATUS     current
	DESCRIPTION
		"Input"
	::= { ecPrecorrectorLevels 1 }

ecPrecorrectorStatus  OBJECT-TYPE
	SYNTAX     INTEGER {
		unlocked (0),
		locked (1)
	}
	MAX-ACCESS read-only
	STATUS     current
	DESCRIPTION
		"Status"
	::= { ecPrecorrectorLevels 2 }

ecPrecorrectorFeedback  OBJECT-TYPE
	SYNTAX     DisplayString
	UNITS 	"dBFS"
	MAX-ACCESS read-only
	STATUS     current
	DESCRIPTION
		"Feedback"
	::= { ecPrecorrectorLevels 3 }

ecPrecorrectorOutput  OBJECT-TYPE
	SYNTAX     DisplayString
	UNITS 	"dBFS"
	MAX-ACCESS read-only
	STATUS     current
	DESCRIPTION
		"Output"
	::= { ecPrecorrectorLevels 4 }

-- Spectrum measures

ecShoulderAlarm  OBJECT-TYPE
	SYNTAX     Unsigned32 (30..60)
	UNITS 	"dB"
	MAX-ACCESS read-write
	STATUS     current
	DESCRIPTION
		"Shoulder alarm"
	::= { ecSpectrumMeasures 1 }

ecLowerShoulder  OBJECT-TYPE
	SYNTAX     DisplayString
	UNITS 	"dB"
	MAX-ACCESS read-only
	STATUS     current
	DESCRIPTION
		"Lower shoulder"
	::= { ecSpectrumMeasures 2 }

ecUpperShoulder  OBJECT-TYPE
	SYNTAX     DisplayString
	UNITS 	"dB"
	MAX-ACCESS read-only
	STATUS     current
	DESCRIPTION
		"Upper shoulder"
	::= { ecSpectrumMeasures 3 }

ecInBandLevelVariation  OBJECT-TYPE
	SYNTAX     DisplayString
	UNITS 	"dB"
	MAX-ACCESS read-only
	STATUS     current
	DESCRIPTION
		"In-band level variation"
	::= { ecSpectrumMeasures 4 }

ecNonLinearStoredPrecorrection  OBJECT-TYPE
	SYNTAX     DisplayString
	MAX-ACCESS read-only
	STATUS     current
	DESCRIPTION
		"Non-Linear stored precorrection"
	::= { ecPrecorrector 10 }

ecNonLinearPrecorrectorFeedback  OBJECT-TYPE
	SYNTAX     INTEGER {
		notDetected (0),
		detected (1),
		outOfRange (2)
	}
	MAX-ACCESS read-only
	STATUS     current
	DESCRIPTION
		"Non-linear precorrector feedback"
	::= { ecPrecorrector 12 }

-- Modulator

modulatorTemperature  OBJECT-TYPE
	SYNTAX     DisplayString
	MAX-ACCESS read-only
	STATUS     current
	DESCRIPTION
		"Modulator board temperature"
	::= { modulatorGeneral 1 }

modulatorStandard  OBJECT-TYPE
	SYNTAX     INTEGER {
		dvbt (0),
		dvbt2 (1),
		isdbt (2),
		atsc (3),
		dab (4)
	}
	MAX-ACCESS read-write
	STATUS     current
	DESCRIPTION
		"Modulator standard:

		DVB-T
		DVB-T2
		ISDB-T
		ATSC 1.0
		T-DAB/DAB+/DMB"
	::= { modulatorGeneral 2 }

modulatorTestMode  OBJECT-TYPE
	SYNTAX     INTEGER {
		disabled (0),
--		rfTone (1),
		prbs (2)
	}
	MAX-ACCESS read-write
	STATUS     current
	DESCRIPTION
		"Test mode"
	::= { modulatorGeneral 3 }

modulatorStandardAutoConfig  OBJECT-TYPE
	SYNTAX     DisabledEnabled
	MAX-ACCESS read-write
	STATUS     current
	DESCRIPTION
		"Standard Auto-configuration"
	::= { modulatorGeneral 6 }

-- PRBS branch only when prbs testMode selected

modulatorPrbsType  OBJECT-TYPE
	SYNTAX     INTEGER {
		ccittItuTx151n150x2e23 (1),
		ccittItuTx151x150x2e20 (2),
		ccittItuTx151x150x2e17 (3),
		ccittItuTx151x150x2e15 (4),
		ccittItuTxV29 (5),
		ccittItuTx153x150x2e20 (6)
	}
	MAX-ACCESS read-write
	STATUS     current
	DESCRIPTION
		"PRBS Type"
	::= { modulatorGeneralPrbs 1 }

modulatorPrbsPid OBJECT-TYPE
	SYNTAX     Unsigned32 (0..8191)
	MAX-ACCESS read-write
	STATUS     current
	DESCRIPTION
		"PRBS PID"
	::= { modulatorGeneralPrbs 2 }

modulatorPrbsIn OBJECT-TYPE
	SYNTAX     DisabledEnabled
	MAX-ACCESS read-write
	STATUS     current
	DESCRIPTION
		"Inverse PRBS"
	::= { modulatorGeneralPrbs 3 }

-- System DVB-T

dvbtBandwidth  OBJECT-TYPE
	SYNTAX     INTEGER {
		bw8Mhz (0),
		bw7Mhz (1),
		bw6Mhz (2)
	}
	MAX-ACCESS read-write
	STATUS     current
	DESCRIPTION
		"Bandwidth"
	::= { dvbtSystem 1 }

dvbtCellIdEnable  OBJECT-TYPE
	SYNTAX     DisabledEnabled
	MAX-ACCESS read-write
	STATUS     current
	DESCRIPTION
		"Enable Cell ID"
	::= { dvbtSystem 2 }

dvbtCellId  OBJECT-TYPE
	SYNTAX     Unsigned32 (0..65535)
	MAX-ACCESS read-write
	STATUS     current
	DESCRIPTION
		"Cell ID"
	::= { dvbtSystem 3 }

-- Network DVB-T

dvbtNetworkType  OBJECT-TYPE
	SYNTAX     INTEGER {
		sfn (0),
		mfn (1)
	}
	MAX-ACCESS read-write
	STATUS     current
	DESCRIPTION
		"Network type"
	::= { dvbtNetwork 1 }

-- dvbt1ppsActiveEdge  OBJECT-TYPE
-- 	SYNTAX     INTEGER {
-- 		rising (0),
-- 		falling (1)
-- 	}
-- 	MAX-ACCESS read-write
-- 	STATUS     current
-- 	DESCRIPTION
-- 		"1PPS active edge"
-- 	::= { dvbtNetwork 2 }

dvbtAutoconfigurationMip  OBJECT-TYPE
	SYNTAX     INTEGER {
		disable (0),
		enable (1)
	}
	MAX-ACCESS read-write
	STATUS     current
	DESCRIPTION
		"Autoconfiguration from MIP"
	::= { dvbtNetwork 3 }

dvbtLocalDelay  OBJECT-TYPE
	SYNTAX     OCTET STRING (SIZE(1..9))
	UNITS 	"us"
	MAX-ACCESS read-write
	STATUS     current
	DESCRIPTION
		"Local delay

		The value must be -500000.0..500000.0 in 0.1 step
		"
	::= { dvbtNetwork 4 }

dvbtRateAdaptation  OBJECT-TYPE
	SYNTAX     DisabledEnabled
	MAX-ACCESS read-write
	STATUS     obsolete
	DESCRIPTION
		"Rate adaptations"
	::= { dvbtNetwork 6 }

dvbtBufferDuration  OBJECT-TYPE
	SYNTAX     Unsigned32 (50..999)
	UNITS 	"ms"
	MAX-ACCESS read-write
	STATUS     current
	DESCRIPTION
		"Buffer duration"
	::= { dvbtNetwork 8 }

dvbtRetransmissionDelay  OBJECT-TYPE
	SYNTAX     FloatingPoint
	UNITS 	"us"
	MAX-ACCESS read-write
	STATUS     current
	DESCRIPTION
		"Retransmission delay

		The value must be 0 .. 1000000.0 in 0.1 step
		"
	::= { dvbtNetwork 11 }


-- MIP DVB-T

dvbtMaximumNetworkDelay  OBJECT-TYPE
	SYNTAX     DisplayString
	UNITS 	"us"
	MAX-ACCESS read-only
	STATUS     current
	DESCRIPTION
		"Maximum netowrk delay"
	::= { dvbtMip 1 }

dvbtTimeOffset  OBJECT-TYPE
	SYNTAX     DisplayString
	UNITS 	"us"
	MAX-ACCESS read-only
	STATUS     current
	DESCRIPTION
		"Time offset"
	::= { dvbtMip 2 }

dvbtTransmitterId  OBJECT-TYPE
	SYNTAX     Unsigned32 (0..65535)
	MAX-ACCESS read-write
	STATUS     current
	DESCRIPTION
		"Transmitter ID"
	::= { dvbtMip 3 }

-- Timing information DVB-T

dvbtCurrentNetworkDelay  OBJECT-TYPE
	SYNTAX     OCTET STRING (SIZE(1..255))
	UNITS 	"us"
	MAX-ACCESS read-only
	STATUS     current
	DESCRIPTION
		"Current network delay"
	::= { dvbtTimingInformation 1 }

dvbtInputBufferDelay  OBJECT-TYPE
	SYNTAX     DisplayString
	UNITS 	"us"
	MAX-ACCESS read-only
	STATUS     current
	DESCRIPTION
		"Input buffer delay"
	::= { dvbtTimingInformation 2 }

dvbtProcessingDelay  OBJECT-TYPE
	SYNTAX     DisplayString
	UNITS 	"us"
	MAX-ACCESS read-only
	STATUS     current
	DESCRIPTION
		"Processing delay"
	::= { dvbtTimingInformation 3 }

dvbtNetworkDelayMargin  OBJECT-TYPE
	SYNTAX     DisplayString
	UNITS 	"us"
	MAX-ACCESS read-only
	STATUS     current
	DESCRIPTION
		"Network delay margin"
	::= { dvbtTimingInformation 4 }

dvbtDelay  OBJECT-TYPE
	SYNTAX     OCTET STRING (SIZE(1..255))
	UNITS 	"us"
	MAX-ACCESS read-only
	STATUS     current
	DESCRIPTION
		"Modulator delay"
	::= { dvbtTimingInformation 5 }

-- Modulation DVB-T

dvbtConstellation  OBJECT-TYPE
	SYNTAX     INTEGER {
		qpsk (0),
		qam16 (1),
		qam64 (2)
	}
	MAX-ACCESS read-write
	STATUS     current
	DESCRIPTION
		"Constellation"
	::= { dvbtModulation 1 }

dvbtFec  OBJECT-TYPE
	SYNTAX     INTEGER {
		fec1div2 (0),
		fec2div3 (1),
		fec3div4 (2),
		fec5div6 (3),
		fec7div8 (4)
	}
	MAX-ACCESS read-write
	STATUS     current
	DESCRIPTION
		"FEC"
	::= { dvbtModulation 2 }

dvbtGuardInterval  OBJECT-TYPE
	SYNTAX     INTEGER {
		guardInterval1div32 (0),
		guardInterval1div16 (1),
		guardInterval1div8 (2),
		guardInterval1div4 (3)
	}
	MAX-ACCESS read-write
	STATUS     current
	DESCRIPTION
		"Guard Interval"
	::= { dvbtModulation 3 }

dvbtFft  OBJECT-TYPE
	SYNTAX     INTEGER {
		fft2K (0),
		fft8K (1)
	}
	MAX-ACCESS read-write
	STATUS     current
	DESCRIPTION
		"FFT"
	::= { dvbtModulation 4 }

dvbtAutoconfigurationFromDttRcv  OBJECT-TYPE
	SYNTAX     DisabledEnabled
	MAX-ACCESS read-write
	STATUS     current
	DESCRIPTION
		"Autoconfiguration from DTT receiver"
	::= { dvbtModulation 10 }

-- System DVB-T2

dvbt2Profile  OBJECT-TYPE
	SYNTAX     INTEGER {
		base (0),
		lite (1)
	}
	MAX-ACCESS read-write
	STATUS     current
	DESCRIPTION
		"DVB-T2 profile"
	::= { dvbt2System 1 }

dvbt2InputMode  OBJECT-TYPE
	SYNTAX     INTEGER {
		aMode (0),
		bMode (1)
	}
	MAX-ACCESS read-write
	STATUS     current
	DESCRIPTION
		"Input Mode"
	::= { dvbt2System 2 }

dvbt2T2miPid  OBJECT-TYPE
	SYNTAX     Unsigned32 (32..8910)
	MAX-ACCESS read-write
	STATUS     current
	DESCRIPTION
		"T2MI PID"
	::= { dvbt2System 3 }

dvbt2Bandwidth  OBJECT-TYPE
	SYNTAX     INTEGER {
		bw1p7Mhz (0),
		bw5Mhz (1),
		bw6Mhz (2),
		bw7Mhz (3),
		bw8Mhz (4),
		bw10Mhz (5)
	}
	MAX-ACCESS read-write
	STATUS     current
	DESCRIPTION
		"Bandwidth"
	::= { dvbt2System 4 }

dvbt2Version  OBJECT-TYPE
	SYNTAX     INTEGER {
		v1p1p1 (0),
		v1p2p1 (1),
		v1p3p1 (2)
	}
	MAX-ACCESS read-write
	STATUS     current
	DESCRIPTION
		"T2 Version"
	::= { dvbt2System 5 }

-- Cell ID

dvbt2CellIdT2mi  OBJECT-TYPE
	SYNTAX     Unsigned32 (0..65535)
	MAX-ACCESS read-only
	STATUS     current
	DESCRIPTION
		"T2MI value [Cell ID]"
	::= { dvbt2CellId 1 }

dvbt2CellIdOverwrite  OBJECT-TYPE
	SYNTAX     INTEGER {
		disable (0),
		enable (1)
	}
	MAX-ACCESS read-write
	STATUS     current
	DESCRIPTION
		"Overwrite [Cell ID]"
	::= { dvbt2CellId 2 }

dvbt2CellIdUser  OBJECT-TYPE
	SYNTAX     Unsigned32 (0..65535)
	MAX-ACCESS read-write
	STATUS     current
	DESCRIPTION
		"User value [Cell ID]"
	::= { dvbt2CellId 3 }

-- Network ID

dvbt2NetworkIdT2mi  OBJECT-TYPE
	SYNTAX     Unsigned32 (0..65535)
	MAX-ACCESS read-only
	STATUS     current
	DESCRIPTION
		"T2MI value [Network ID]"
	::= { dvbt2NetworkId 1 }

dvbt2NetworkIdOverwrite  OBJECT-TYPE
	SYNTAX     INTEGER {
		disable (0),
		enable (1)
	}
	MAX-ACCESS read-write
	STATUS     current
	DESCRIPTION
		"Overwrite [Network ID]"
	::= { dvbt2NetworkId 2 }

dvbt2NetworkIdUser  OBJECT-TYPE
	SYNTAX     Unsigned32 (0..65535)
	MAX-ACCESS read-write
	STATUS     current
	DESCRIPTION
		"User value [Network ID]"
	::= { dvbt2NetworkId 3 }

-- T2 system ID

dvbt2SystemIdT2mi  OBJECT-TYPE
	SYNTAX     Unsigned32 (0..65535)
	MAX-ACCESS read-only
	STATUS     current
	DESCRIPTION
		"T2MI value [T2 system ID]"
	::= { dvbt2SystemId 1 }

dvbt2SystemIdOverwrite  OBJECT-TYPE
	SYNTAX     INTEGER {
		disable (0),
		enable (1)
	}
	MAX-ACCESS read-write
	STATUS     current
	DESCRIPTION
		"Overwrite [T2 system ID]"
	::= { dvbt2SystemId 2 }

dvbt2SystemIdUser  OBJECT-TYPE
	SYNTAX     Unsigned32 (0..65535)
	MAX-ACCESS read-write
	STATUS     current
	DESCRIPTION
		"User value [T2 system ID]"
	::= { dvbt2SystemId 3 }

-- T2 frequency

dvbt2FrequencyT2mi  OBJECT-TYPE
	SYNTAX     Unsigned32 (0..65535)
	MAX-ACCESS read-only
	STATUS     current
	DESCRIPTION
		"T2MI value [T2 frequency]"
	::= { dvbt2Frequency 1 }

dvbt2FrequencyOverwrite  OBJECT-TYPE
	SYNTAX     INTEGER {
		disable (0),
		enable (1)
	}
	MAX-ACCESS read-write
	STATUS     current
	DESCRIPTION
		"Overwrite [T2 frequency]"
	::= { dvbt2Frequency 2 }

-- Network

dvbt2NetworkType  OBJECT-TYPE
	SYNTAX     INTEGER {
		sfn (0),
		mfn (1)
	}
	MAX-ACCESS read-write
	STATUS     current
	DESCRIPTION
		"Network type"
	::= { dvbt2Network 1 }

dvbt2SfnRelativeReference  OBJECT-TYPE
	SYNTAX     INTEGER {
		nok (0),
		ok (1)
	}
	MAX-ACCESS read-only
	STATUS     current
	DESCRIPTION
		"SFN reference (relative)"
	::= { dvbt2Network 2 }

dvbt2SfnAbsoluteReference  OBJECT-TYPE
	SYNTAX     INTEGER {
		nok (0),
		ok (1)
	}
	MAX-ACCESS read-only
	STATUS     current
	DESCRIPTION
		"SFN reference (absolute)"
	::= { dvbt2Network 3 }

dvbt2TimeStamp  OBJECT-TYPE
	SYNTAX     INTEGER {
		null (0),
		absolute (1),
		relative (2),
		null3 (3)
	}
	MAX-ACCESS read-only
	STATUS     current
	DESCRIPTION
		"T2MI timestamp"
	::= { dvbt2Network 4 }

dvbt2SuperFrameDuration  OBJECT-TYPE
	SYNTAX     DisplayString
	UNITS 	"us"
	MAX-ACCESS read-only
	STATUS     current
	DESCRIPTION
		"T2 Super Frame duration"
	::= { dvbt2Network 5 }

-- dvbt21ppsActiveEdge  OBJECT-TYPE
-- 	SYNTAX     INTEGER {
-- 		rising (0),
-- 		falling (1)
-- 	}
-- 	MAX-ACCESS read-write
-- 	STATUS     current
-- 	DESCRIPTION
-- 		"1PPS active edge"
-- 	::= { dvbt2Network 6 }

dvbt2LocalDelay  OBJECT-TYPE
	SYNTAX     OCTET STRING (SIZE(1..7))
	UNITS 	"us"
	MAX-ACCESS read-write
	STATUS     current
	DESCRIPTION
		"Local delay

		The value must be -2000.0..2000.0 in 0.1 step
		"
	::= { dvbt2Network 7 }

dvbt2BufferDuration  OBJECT-TYPE
	SYNTAX     Unsigned32 (50..999)
	UNITS 	"ms"
	MAX-ACCESS read-write
	STATUS     current
	DESCRIPTION
		"Buffer duration"
	::= { dvbt2Network 8 }

-- Individual Addressing

dvbt2TimeOffset  OBJECT-TYPE
	SYNTAX     DisplayString
	UNITS 	"us"
	MAX-ACCESS read-only
	STATUS     current
	DESCRIPTION
		"Time offset"
	::= { dvbt2IndividualAddresssing 1 }

dvbt2TransmitterId  OBJECT-TYPE
	SYNTAX     Unsigned32 (0..65535)
	MAX-ACCESS read-write
	STATUS     current
	DESCRIPTION
		"Transmitter ID"
	::= { dvbt2IndividualAddresssing 2 }

-- Timing information

dvbt2InputBufferDelay  OBJECT-TYPE
	SYNTAX     DisplayString
	UNITS 	"us"
	MAX-ACCESS read-only
	STATUS     current
	DESCRIPTION
		"Input buffer delay"
	::= { dvbt2TimingInformation 1 }

dvbt2ProcessingDelay  OBJECT-TYPE
	SYNTAX     DisplayString
	UNITS 	"us"
	MAX-ACCESS read-only
	STATUS     current
	DESCRIPTION
		"Processing delay"
	::= { dvbt2TimingInformation 2 }

dvbt2NetworkDelayMargin  OBJECT-TYPE
	SYNTAX     DisplayString
	UNITS 	"us"
	MAX-ACCESS read-only
	STATUS     current
	DESCRIPTION
		"Network delay margin"
	::= { dvbt2TimingInformation 3 }

dvbt2Delay  OBJECT-TYPE
	SYNTAX     DisplayString
	UNITS 	"us"
	MAX-ACCESS read-only
	STATUS     current
	DESCRIPTION
		"Modulator delay"
	::= { dvbt2TimingInformation 4 }

-- T2 Frame

dvbt2L1SignallingModulation  OBJECT-TYPE
	SYNTAX     INTEGER {
		bpsk (0),
		qpsk (1),
		qam16 (2),
		qam64 (3)
	}
	MAX-ACCESS read-write
	STATUS     current
	DESCRIPTION
		"L1-post signalling constellation"
	::= { dvbt2Frame 1 }

dvbt2L1PostScrambling  OBJECT-TYPE
	SYNTAX     INTEGER {
		disable (0),
		enable (1)
	}
	MAX-ACCESS read-write
	STATUS     current
	DESCRIPTION
		"L1-post scrambling"
	::= { dvbt2Frame 2 }

dvbt2LiteCompatible  OBJECT-TYPE
	SYNTAX     NoYes
	MAX-ACCESS read-only
	STATUS     current
	DESCRIPTION
		"T2-Lite compatible"
	::= { dvbt2Frame 3 }

dvbt2PreambleFormat  OBJECT-TYPE
	SYNTAX     INTEGER {
		siso (0),
		miso (1)
	}
	MAX-ACCESS read-write
	STATUS     current
	DESCRIPTION
		"Preamble format"
	::= { dvbt2Frame 4 }

dvbt2MisoGroup  OBJECT-TYPE
	SYNTAX     INTEGER {
		one (0),
		two (1)
	}
	MAX-ACCESS read-write
	STATUS     current
	DESCRIPTION
		"MISO Group"
	::= { dvbt2Frame 5 }

dvbt2ExtendedCarrierMode  OBJECT-TYPE
	SYNTAX     INTEGER {
		disable (0),
		enable (1)
	}
	MAX-ACCESS read-write
	STATUS     current
	DESCRIPTION
		"Extended carrier mode"
	::= { dvbt2Frame 6 }

dvbt2FftSize  OBJECT-TYPE
	SYNTAX     INTEGER {
		fft1K (0),
		fft2K (1),
		fft4K (2),
		fft8K (3),
		fft16K (4),
		fft32K (5)
	}
	MAX-ACCESS read-write
	STATUS     current
	DESCRIPTION
		"FFT size"
	::= { dvbt2Frame 7 }

dvbt2GuardInterval  OBJECT-TYPE
	SYNTAX     INTEGER {
		interval1div32 (0),
		interval1div16 (1),
		interval1div8 (2),
		interval1div4 (3),
		interval1div128 (4),
		interval19div128 (5),
		interval19div256 (6)
	}
	MAX-ACCESS read-write
	STATUS     current
	DESCRIPTION
		"Guard interval"
	::= { dvbt2Frame 8 }

dvbt2PaprReduction  OBJECT-TYPE
	SYNTAX     INTEGER {
		nullTrP2 (0),
		ace (1),
		tr (2),
		aceTr (3)
	}
	MAX-ACCESS read-write
	STATUS     current
	DESCRIPTION
		"PAPR reduction"
	::= { dvbt2Frame 9 }

dvbt2PilotPattern  OBJECT-TYPE
	SYNTAX     INTEGER {
		pp1 (0),
		pp2 (1),
		pp3 (2),
		pp4 (3),
		pp5 (4),
		pp6 (5),
		pp7 (6),
		pp8 (7)
	}
	MAX-ACCESS read-write
	STATUS     current
	DESCRIPTION
		"Pilot pattern"
	::= { dvbt2Frame 10 }

dvbt2FramesPerSuperframe  OBJECT-TYPE
	SYNTAX     Unsigned32 (2..256)
	MAX-ACCESS read-write
	STATUS     current
	DESCRIPTION
		"Number of T2 frames per superframe"
	::= { dvbt2Frame 11 }

dvbt2OfdmSymbolsPerSuperframe  OBJECT-TYPE
	SYNTAX     Unsigned32 (0..4095)
	MAX-ACCESS read-write
	STATUS     current
	DESCRIPTION
		"Number of OFDM symbols per T2 frame"
	::= { dvbt2Frame 12 }

-- PLP

numberOfPlps  OBJECT-TYPE
	SYNTAX     Unsigned32 (0..8)
	MAX-ACCESS read-only
	STATUS     current
	DESCRIPTION
		"Number of PLPs"
	::= { dvbt2Plp 1 }

dvbt2PlpTable  OBJECT-TYPE
	SYNTAX SEQUENCE OF Dvbt2PlpEntry
	MAX-ACCESS not-accessible
	STATUS     current
	DESCRIPTION
		"PLP Table"
	::= { dvbt2Plp 2 }

dvbt2PlpEntry  OBJECT-TYPE
	SYNTAX 	Dvbt2PlpEntry
	MAX-ACCESS not-accessible
	STATUS     current
	DESCRIPTION
		"PLP Table entry"
	INDEX { plpIndex }
	::= { dvbt2PlpTable 1 }

Dvbt2PlpEntry ::= SEQUENCE {
	plpIndex
		Unsigned32,
	plpId
		Unsigned32,
	plpType
		INTEGER,
	plpMode
		INTEGER,
	plpGroupId
		Unsigned32,
	plpConstellation
		INTEGER,
	rotatedConstellation
		DisabledEnabled,
	fecType
		INTEGER,
	codeRate
		INTEGER,
	numberOfFecBlocks
		Unsigned32,
	typeOfTimeInvervaling
		INTEGER,
	lengthOfTimeInvervaling
		Unsigned32,
	inBandSignalling
		INTEGER,
	plpBer
		FloatingPoint
}

plpIndex  OBJECT-TYPE
	SYNTAX     Unsigned32 (0..8)
	MAX-ACCESS not-accessible
	STATUS     current
	DESCRIPTION
		"PLP index"
	::= { dvbt2PlpEntry 1 }

plpId  OBJECT-TYPE
	SYNTAX     Unsigned32 (0..255)
	MAX-ACCESS read-write
	STATUS     current
	DESCRIPTION
		"PLP ID"
	::= { dvbt2PlpEntry 2 }

plpType  OBJECT-TYPE
	SYNTAX     INTEGER {
		common (0),
		data1 (1),
		data2 (2)
	}
	MAX-ACCESS read-write
	STATUS     current
	DESCRIPTION
		"PLP type"
	::= { dvbt2PlpEntry 3 }

plpMode  OBJECT-TYPE
	SYNTAX     INTEGER {
		nm (0),
		hem (1)
	}
	MAX-ACCESS read-write
	STATUS     current
	DESCRIPTION
		"PLP mode"
	::= { dvbt2PlpEntry 4 }

plpGroupId  OBJECT-TYPE
	SYNTAX     Unsigned32 (0..255)
	MAX-ACCESS read-write
	STATUS     current
	DESCRIPTION
		"PLP Group ID"
	::= { dvbt2PlpEntry 5 }

plpConstellation  OBJECT-TYPE
	SYNTAX     INTEGER {
		qpsk (0),
		qam16 (1),
		qam64 (2),
		qam256 (3)
	}
	MAX-ACCESS read-write
	STATUS     current
	DESCRIPTION
		"PLP Constellation"
	::= { dvbt2PlpEntry 6 }

rotatedConstellation  OBJECT-TYPE
	SYNTAX     DisabledEnabled
	MAX-ACCESS read-write
	STATUS     current
	DESCRIPTION
		"Roted Constellation"
	::= { dvbt2PlpEntry 7 }

fecType  OBJECT-TYPE
	SYNTAX     INTEGER {
		ldpc16k (0),
		ldpc64k (1)
	}
	MAX-ACCESS read-write
	STATUS     current
	DESCRIPTION
		"FEC type"
	::= { dvbt2PlpEntry 8 }

codeRate  OBJECT-TYPE
	SYNTAX     INTEGER {
		rate1div2 (0),
		rate3div5 (1),
		rate2div3 (2),
		rate3div4 (3),
		rate4div5 (4),
		rate5div6 (5),
		rate1div3 (6),
		rate2div5 (7)
	}
	MAX-ACCESS read-write
	STATUS     current
	DESCRIPTION
		"Code Rate"
	::= { dvbt2PlpEntry 9 }

numberOfFecBlocks  OBJECT-TYPE
	SYNTAX     Unsigned32 (0..65535)
	MAX-ACCESS read-write
	STATUS     current
	DESCRIPTION
		"Number of FEC blocks"
	::= { dvbt2PlpEntry 10 }

typeOfTimeInvervaling  OBJECT-TYPE
	SYNTAX     INTEGER {
		simple (0),
		multiple (1)
	}
	MAX-ACCESS read-write
	STATUS     current
	DESCRIPTION
		"Type of time-interleaving"
	::= { dvbt2PlpEntry 11 }

lengthOfTimeInvervaling  OBJECT-TYPE
	SYNTAX     Unsigned32 (0..255)
	MAX-ACCESS read-write
	STATUS     current
	DESCRIPTION
		"Length of time-interleaving"
	::= { dvbt2PlpEntry 12 }

inBandSignalling  OBJECT-TYPE
	SYNTAX     INTEGER {
		null (0),
		b (1),
		a (2),
		ab (3)
	}
	MAX-ACCESS read-write
	STATUS     current
	DESCRIPTION
		"In-band signalling"
	::= { dvbt2PlpEntry 13 }

plpBer  OBJECT-TYPE
	SYNTAX     FloatingPoint
	MAX-ACCESS read-only
	STATUS     current
	DESCRIPTION
		"BER"
	::= { dvbt2PlpEntry 14 }

-- System ISDB-T

isdbtBandwidth  OBJECT-TYPE
	SYNTAX     INTEGER {
		bw5Mhz (0),
		bw6Mhz (1),
		bw7Mhz (2),
		bw8Mhz (3)
	}
	MAX-ACCESS read-write
	STATUS     current
	DESCRIPTION
		"Bandwidth"
	::= { isdbtSystem 1 }

isdbtInputMode  OBJECT-TYPE
	SYNTAX     INTEGER {
		ts (0),
		bts (1)
	}
	MAX-ACCESS read-write
	STATUS     current
	DESCRIPTION
		"Input mode"
	::= { isdbtSystem 2 }

isdbtBtsRateLock  OBJECT-TYPE
	SYNTAX     DisabledEnabled
	MAX-ACCESS read-only
	STATUS     current
	DESCRIPTION
		"BTS-rate-lock"
	::= { isdbtSystem 3 }

-- ISDBT CAS

isdbtCasBiss  OBJECT-TYPE
	SYNTAX     DisabledEnabled
	MAX-ACCESS read-write
	STATUS     current
	DESCRIPTION
		"BISS"
	::= { isdbtConditionaAccessSystem 5 }

isdbtCasMode  OBJECT-TYPE
	SYNTAX     INTEGER {
		mode1(0),
		modeE(1)
	}
	MAX-ACCESS read-write
	STATUS     current
	DESCRIPTION
		"Mode"
	::= { isdbtConditionaAccessSystem 10 }

isdbtCasPass  OBJECT-TYPE
	SYNTAX     OCTET STRING (SIZE(1..16))
	MAX-ACCESS read-write
	STATUS     current
	DESCRIPTION
		"Pass"
	::= { isdbtConditionaAccessSystem 15 }

isdbtCasInjectId  OBJECT-TYPE
	SYNTAX     OCTET STRING (SIZE(1..14))
	MAX-ACCESS read-write
	STATUS     current
	DESCRIPTION
		"Inject ID"
	::= { isdbtConditionaAccessSystem 20 }

-- ISDBT BTS

isdbtBtsDecompression  OBJECT-TYPE
	SYNTAX     DisabledEnabled
	MAX-ACCESS read-write
	STATUS     current
	DESCRIPTION
		"Decompression"
	::= { isdbtBroadcastTransportStream 5 }

isdbtBtsIipPid  OBJECT-TYPE
	SYNTAX     Unsigned32 (0..8190)
	MAX-ACCESS read-write
	STATUS     current
	DESCRIPTION
		"IIP PID"
	::= { isdbtBroadcastTransportStream 10 }

isdbtBtsAuxPid  OBJECT-TYPE
	SYNTAX     Unsigned32 (32..8191)
	MAX-ACCESS read-write
	STATUS     current
	DESCRIPTION
		"Aux. PID"
	::= { isdbtBroadcastTransportStream 15 }

isdbtBtsPidRemapping  OBJECT-TYPE
	SYNTAX     DisabledEnabled
	MAX-ACCESS read-write
	STATUS     current
	DESCRIPTION
		"PID Remapping"
	::= { isdbtBroadcastTransportStream 20 }

isdbtBtsRestorePcr  OBJECT-TYPE
	SYNTAX     DisabledEnabled
	MAX-ACCESS read-write
	STATUS     current
	DESCRIPTION
		"Restore PCR"
	::= { isdbtBroadcastTransportStream 25 }

isdbtBtsBypass  OBJECT-TYPE
	SYNTAX     DisabledEnabled
	MAX-ACCESS read-write
	STATUS     current
	DESCRIPTION
		"Bypass"
	::= { isdbtBroadcastTransportStream 30 }

isdbtBtsVirtualChannel  OBJECT-TYPE
	SYNTAX     Unsigned32 (0..99)
	MAX-ACCESS read-write
	STATUS     current
	DESCRIPTION
		"Virtual Channel"
	::= { isdbtBroadcastTransportStream 35 }

isdbtBtsChannel  OBJECT-TYPE
	SYNTAX     Unsigned32 (470000000..862000000)
	MAX-ACCESS read-write
	STATUS     current
	DESCRIPTION
		"Channel"
	::= { isdbtBroadcastTransportStream 40 }

isdbtBtsAreaCode  OBJECT-TYPE
	SYNTAX     Unsigned32 (0..4095)
	MAX-ACCESS read-write
	STATUS     current
	DESCRIPTION
		"Area Code"
	::= { isdbtBroadcastTransportStream 45 }

isdbtBts188BInputLocked  OBJECT-TYPE
	SYNTAX     NokOk
	MAX-ACCESS read-only
	STATUS     current
	DESCRIPTION
		"188B Input Locked"
	::= { isdbtBroadcastTransportStream 50 }

isdbtBts204BOutputLocked  OBJECT-TYPE
	SYNTAX     NokOk
	MAX-ACCESS read-only
	STATUS     current
	DESCRIPTION
		"204B Output Locked"
	::= { isdbtBroadcastTransportStream 55 }

-- ISDBT PID List

isdbtDeletePids  OBJECT-TYPE
	SYNTAX     NullApply
	MAX-ACCESS read-write
	STATUS     current
	DESCRIPTION
		"Delete PIDs"
	::= { isdbtPidList 5 }

isdbtPidListTable  OBJECT-TYPE
	SYNTAX SEQUENCE OF IsdbtPidListEntry
	MAX-ACCESS not-accessible
	STATUS     current
	DESCRIPTION
		"Table for PID List Table"
	::= { isdbtPidList 10 }

isdbtPidListEntry  OBJECT-TYPE
	SYNTAX 	IsdbtPidListEntry
	MAX-ACCESS not-accessible
	STATUS     current
	DESCRIPTION
		"Entry for a trapsink"
	INDEX { isdbtPidIndex }
	::= { isdbtPidListTable 1 }

IsdbtPidListEntry ::= SEQUENCE {
	isdbtPidIndex
		Unsigned32,
	isdbtPidIn
		Unsigned32,
	isdbtPidOut
		Unsigned32
}

isdbtPidIndex  OBJECT-TYPE
	SYNTAX     Unsigned32 (1..99)
	MAX-ACCESS not-accessible
	STATUS     current
	DESCRIPTION
		"ISDBT PID Index"
	::= { isdbtPidListEntry 1 }

isdbtPidIn  OBJECT-TYPE
	SYNTAX     Unsigned32 (0..65535)
	MAX-ACCESS read-only
	STATUS     current
	DESCRIPTION
		"ISDBT PID In"
	::= { isdbtPidListEntry 2 }

isdbtPidOut  OBJECT-TYPE
	SYNTAX     Unsigned32 (0..65535)
	MAX-ACCESS read-only
	STATUS     current
	DESCRIPTION
		"ISDBT PID Out"
	::= { isdbtPidListEntry 3 }

-- Network ISDB-T

isdbtNetworkType  OBJECT-TYPE
	SYNTAX     INTEGER {
		sfn (0),
		mfn (1)
	}
	MAX-ACCESS read-write
	STATUS     current
	DESCRIPTION
		"Network type"
	::= { isdbtNetwork 1 }

-- isdbt1ppsActiveEdge  OBJECT-TYPE
-- 	SYNTAX     INTEGER {
-- 		rising (0),
-- 		falling (1)
-- 	}
-- 	MAX-ACCESS read-write
-- 	STATUS     current
-- 	DESCRIPTION
-- 		"1PPS active edge"
-- 	::= { isdbtNetwork 2 }

isdbtLocalDelay  OBJECT-TYPE
	SYNTAX     OCTET STRING (SIZE(1..7))
	UNITS 	"us"
	MAX-ACCESS read-write
	STATUS     current
	DESCRIPTION
		"Local Delay

		The value must be -2000.0..2000.0 in 0.1 step
		"
	::= { isdbtNetwork 3 }

isdbtBufferDuration  OBJECT-TYPE
	SYNTAX     Unsigned32 (50..999)
	UNITS 	"ms"
	MAX-ACCESS read-write
	STATUS     current
	DESCRIPTION
		"Buffer Duration"
	::= { isdbtNetwork 6 }

-- IIP Network Syncronization Information

isdbtMaximumNetworkDelay  OBJECT-TYPE
	SYNTAX     DisplayString
	UNITS 	"us"
	MAX-ACCESS read-only
	STATUS     current
	DESCRIPTION
		"Maximum network delay"
	::= { iip 1 }

isdbtTimeOffset  OBJECT-TYPE
	SYNTAX     DisplayString
	UNITS 	"us"
	MAX-ACCESS read-only
	STATUS     current
	DESCRIPTION
		"Time offset"
	::= { iip 2 }

isdbtStaticDelay  OBJECT-TYPE
	SYNTAX     DisabledEnabled
	MAX-ACCESS read-only
	STATUS     current
	DESCRIPTION
		"Static delay"
	::= { iip 3 }

isdbtTransmitterId  OBJECT-TYPE
	SYNTAX     Unsigned32 (0..65535)
	MAX-ACCESS read-write
	STATUS     current
	DESCRIPTION
		"Equipment ID"
	::= { iip 4 }

-- Timing information ISDB-T

isdbtCurrentNetworkDelay  OBJECT-TYPE
	SYNTAX     DisplayString
	UNITS 	"us"
	MAX-ACCESS read-only
	STATUS     current
	DESCRIPTION
		"Current network dealy"
	::= { isdbtTimingInformation 1 }

isdbtInputBufferDelay  OBJECT-TYPE
	SYNTAX     DisplayString
	UNITS 	"us"
	MAX-ACCESS read-only
	STATUS     current
	DESCRIPTION
		"Input buffer delay"
	::= { isdbtTimingInformation 2 }

isdbtProcessingDelay  OBJECT-TYPE
	SYNTAX     DisplayString
	UNITS 	"us"
	MAX-ACCESS read-only
	STATUS     current
	DESCRIPTION
		"Processing delay"
	::= { isdbtTimingInformation 3 }

isdbtNetworkDelayMargin  OBJECT-TYPE
	SYNTAX     DisplayString
	UNITS 	"us"
	MAX-ACCESS read-only
	STATUS     current
	DESCRIPTION
		"Network delay margin"
	::= { isdbtTimingInformation 4 }

isdbtDelay  OBJECT-TYPE
	SYNTAX     DisplayString
	UNITS 	"us"
	MAX-ACCESS read-only
	STATUS     current
	DESCRIPTION
		"Modulator delay"
	::= { isdbtTimingInformation 5 }

isdbtRfDelay  OBJECT-TYPE
	SYNTAX     OCTET STRING (SIZE(1..7))
	UNITS 	"us"
	MAX-ACCESS read-write
	STATUS     current
	DESCRIPTION
		"RF delay"
	::= { isdbtNetwork 10 }


-- Modulation ISDB-T

isdbtFft  OBJECT-TYPE
	SYNTAX     INTEGER {
		fftMode12K (1),
		fftMode24K (2),
		fftMode38K (3)
	}
	MAX-ACCESS read-write
	STATUS     current
	DESCRIPTION
		"FFT mode"
	::= { isdbtModulation 1 }

isdbtGuardInterval  OBJECT-TYPE
	SYNTAX     INTEGER {
		guardInterval1div32 (0),
		guardInterval1div16 (1),
		guardInterval1div8 (2),
		guardInterval1div4 (3)
	}
	MAX-ACCESS read-write
	STATUS     current
	DESCRIPTION
		"Guard interval"
	::= { isdbtModulation 2 }

-- isdbtFftWindowing  OBJECT-TYPE
-- 	SYNTAX     INTEGER {
-- 		disable (0),
-- 		enable (1)
-- 	}
-- 	MAX-ACCESS read-write
-- 	STATUS     current
-- 	DESCRIPTION
-- 		"FFT Windowing"
-- 	::= { isdbtModulation 3 }

-- isdbtFftWindowRate  OBJECT-TYPE
-- 	SYNTAX     Unsigned32 (16..64)
-- 	MAX-ACCESS read-write
-- 	STATUS     current
-- 	DESCRIPTION
-- 		"FFT Window Rate"
-- 	::= { isdbtModulation 4 }

isdbtPartialReception  OBJECT-TYPE
	SYNTAX     INTEGER {
		disable (0),
		enable (1)
	}
	MAX-ACCESS read-write
	STATUS     current
	DESCRIPTION
		"Partial reception"
	::= { isdbtModulation 5 }

-- Layer A ISDB-T

--isdbtPidFilteringLA  OBJECT-TYPE
--	SYNTAX     INTEGER {
--		disabled (0),
--		pids (1),
--		programs (2)
--	}
--	MAX-ACCESS read-write
--	STATUS     obsolete
--	DESCRIPTION
--		"Filtering type"
--	::= { isdbtLayerA 1 }

isdbtPidsLA  OBJECT-TYPE
	SYNTAX     DisplayString
	MAX-ACCESS read-write
	STATUS     current
	DESCRIPTION
		"Filter items"
	::= { isdbtLayerA 2 }

isdbtConstellationLA  OBJECT-TYPE
	SYNTAX     INTEGER {
		dqpsk (0),
		qpsk (1),
		qam16 (2),
		qam64 (3)
	}
	MAX-ACCESS read-write
	STATUS     current
	DESCRIPTION
		"Constellation"
	::= { isdbtLayerA 3 }

isdbtCodeRateLA  OBJECT-TYPE
	SYNTAX     INTEGER {
		rate1div2 (0),
		rate2div3 (1),
		rate3div4 (2),
		rate5div6 (3),
		rate7div8 (4)
	}
	MAX-ACCESS read-write
	STATUS     current
	DESCRIPTION
		"Code rate"
	::= { isdbtLayerA 4 }

isdbtTimeIntervalLengthLA  OBJECT-TYPE
	SYNTAX     INTEGER {
		length0 (0),
		length1 (1),
		length2 (2),
		length4 (4),
		length8 (8),
		length16 (16)
	}
	MAX-ACCESS read-write
	STATUS     current
	DESCRIPTION
		"Time interval lenght"
	::= { isdbtLayerA 5 }

isdbtNumberOfSegmentsLA  OBJECT-TYPE
	SYNTAX     Unsigned32 (0..13)
	MAX-ACCESS read-write
	STATUS     current
	DESCRIPTION
		"Number of segments"
	::= { isdbtLayerA 6 }

isdbtBitrateLA  OBJECT-TYPE
	SYNTAX     DisplayString
	UNITS 	"bps"
	MAX-ACCESS read-only
	STATUS     current
	DESCRIPTION
		"Bitrate (In / Out)"
	::= { isdbtLayerA 7 }

isdbtBerLA  OBJECT-TYPE
	SYNTAX     DisplayString
	MAX-ACCESS read-only
	STATUS     current
	DESCRIPTION
		"BER"
	::= { isdbtLayerA 8 }

isdbtServicesA  OBJECT-TYPE
	SYNTAX     DisplayString
	MAX-ACCESS read-write
	STATUS     current
	DESCRIPTION
		"Services names"
	::= { isdbtLayerA 10 }


-- Layer B ISDB-T

--isdbtPidFilteringLB  OBJECT-TYPE
--	SYNTAX     INTEGER {
--		disabled (0),
--		pids (1),
--		programs (2)
--	}
--	MAX-ACCESS read-write
--	STATUS     obsolete
--	DESCRIPTION
--		"Filtering type"
--	::= { isdbtLayerB 1 }

isdbtPidsLB  OBJECT-TYPE
	SYNTAX     DisplayString
	MAX-ACCESS read-write
	STATUS     current
	DESCRIPTION
		"Filter items"
	::= { isdbtLayerB 2 }

isdbtConstellationLB  OBJECT-TYPE
	SYNTAX     INTEGER {
		dqpsk (0),
		qpsk (1),
		qam16 (2),
		qam64 (3)
	}
	MAX-ACCESS read-write
	STATUS     current
	DESCRIPTION
		"Constellation"
	::= { isdbtLayerB 3 }

isdbtCodeRateLB  OBJECT-TYPE
	SYNTAX     INTEGER {
		rate1div2 (0),
		rate2div3 (1),
		rate3div4 (2),
		rate5div6 (3),
		rate7div8 (4)
	}
	MAX-ACCESS read-write
	STATUS     current
	DESCRIPTION
		"Code rate"
	::= { isdbtLayerB 4 }

isdbtTimeIntervalLengthLB  OBJECT-TYPE
	SYNTAX     INTEGER {
		length0 (0),
		length1 (1),
		length2 (2),
		length4 (4),
		length8 (8),
		length16 (16)
	}
	MAX-ACCESS read-write
	STATUS     current
	DESCRIPTION
		"Time interval lenght"
	::= { isdbtLayerB 5 }

isdbtNumberOfSegmentsLB  OBJECT-TYPE
	SYNTAX     Unsigned32 (0..13)
	MAX-ACCESS read-write
	STATUS     current
	DESCRIPTION
		"Number of segments"
	::= { isdbtLayerB 6 }

isdbtBitrateLB  OBJECT-TYPE
	SYNTAX     DisplayString
	UNITS 	"bps"
	MAX-ACCESS read-only
	STATUS     current
	DESCRIPTION
		"Bitrate (In / Out)"
	::= { isdbtLayerB 7 }

isdbtBerLB  OBJECT-TYPE
	SYNTAX     DisplayString
	MAX-ACCESS read-only
	STATUS     current
	DESCRIPTION
		"BER"
	::= { isdbtLayerB 8 }

isdbtServicesB  OBJECT-TYPE
	SYNTAX     DisplayString
	MAX-ACCESS read-write
	STATUS     current
	DESCRIPTION
		"Services names"
	::= { isdbtLayerB 10 }


-- Layer C ISDB-T

--isdbtPidFilteringLC  OBJECT-TYPE
--	SYNTAX     INTEGER {
--		disabled (0),
--		pids (1),
--		programs (2)
--	}
--	MAX-ACCESS read-write
--	STATUS     obsolete
--	DESCRIPTION
--		"Filtering type"
--	::= { isdbtLayerC 1 }

isdbtPidsLC  OBJECT-TYPE
	SYNTAX     DisplayString
	MAX-ACCESS read-write
	STATUS     current
	DESCRIPTION
		"Filter items"
	::= { isdbtLayerC 2 }

isdbtConstellationLC  OBJECT-TYPE
	SYNTAX     INTEGER {
		dqpsk (0),
		qpsk (1),
		qam16 (2),
		qam64 (3)
	}
	MAX-ACCESS read-write
	STATUS     current
	DESCRIPTION
		"Constellation"
	::= { isdbtLayerC 3 }

isdbtCodeRateLC  OBJECT-TYPE
	SYNTAX     INTEGER {
		rate1div2 (0),
		rate2div3 (1),
		rate3div4 (2),
		rate5div6 (3),
		rate7div8 (4)
	}
	MAX-ACCESS read-write
	STATUS     current
	DESCRIPTION
		"Code rate"
	::= { isdbtLayerC 4 }

isdbtTimeIntervalLengthLC  OBJECT-TYPE
	SYNTAX     INTEGER {
		length0 (0),
		length1 (1),
		length2 (2),
		length4 (4),
		length8 (8),
		length16 (16)
	}
	MAX-ACCESS read-write
	STATUS     current
	DESCRIPTION
		"Time interleaving lenght"
	::= { isdbtLayerC 5 }

isdbtNumberOfSegmentsLC  OBJECT-TYPE
	SYNTAX     Unsigned32 (0..13)
	MAX-ACCESS read-write
	STATUS     current
	DESCRIPTION
		"Number of segments"
	::= { isdbtLayerC 6 }

isdbtBitrateLC  OBJECT-TYPE
	SYNTAX     DisplayString
	UNITS 	"bps"
	MAX-ACCESS read-only
	STATUS     current
	DESCRIPTION
		"Bitrate (In / Out)"
	::= { isdbtLayerC 7 }

isdbtBerLC  OBJECT-TYPE
	SYNTAX     DisplayString
	MAX-ACCESS read-only
	STATUS     current
	DESCRIPTION
		"BER"
	::= { isdbtLayerC 8 }

isdbtServicesC  OBJECT-TYPE
	SYNTAX     DisplayString
	MAX-ACCESS read-write
	STATUS     current
	DESCRIPTION
		"Services names"
	::= { isdbtLayerC 10 }

isdbtPidFiltering  OBJECT-TYPE
	SYNTAX     INTEGER {
		disabled (0),
		pids (1),
		programs (2),
		advanced (3)
	}
	MAX-ACCESS read-write
	STATUS     current
	DESCRIPTION
		"Filtering type"
	::= { isdbtModulation 15 }

-- ISDBT Modulator Program Specific Information

isdbtAvailablePrograms  OBJECT-TYPE
	SYNTAX     DisplayString
	MAX-ACCESS read-only
	STATUS     current
	DESCRIPTION
		"Available programs"
	::= { isdbtPAT 5 }

isdbtAffiliationId  OBJECT-TYPE
	SYNTAX     Unsigned32 (0..255)
	MAX-ACCESS read-write
	STATUS     current
	DESCRIPTION
		"Affiliation ID"
	::= { isdbtBIT 5 }

isdbtNetworkId  OBJECT-TYPE
	SYNTAX     Unsigned32 (0..65535)
	MAX-ACCESS read-write
	STATUS     current
	DESCRIPTION
		"Affilation ID"
	::= { isdbtNIT 5 }

isdbtNetworkName  OBJECT-TYPE
	SYNTAX     DisplayString (SIZE(1..18))
	MAX-ACCESS read-write
	STATUS     current
	DESCRIPTION
		"Network name"
	::= { isdbtNIT 10 }

isdbtTransportStreamId  OBJECT-TYPE
	SYNTAX     Unsigned32 (0..65535)
	MAX-ACCESS read-write
	STATUS     current
	DESCRIPTION
		"Transport Stream ID"
	::= { isdbtNIT 15 }

isdbtOriginalNetworkId  OBJECT-TYPE
	SYNTAX     Unsigned32
	MAX-ACCESS read-only
	STATUS     current
	DESCRIPTION
		"Original Network ID"
	::= { isdbtNIT 20 }

isdbtAreaCode  OBJECT-TYPE
	SYNTAX     Unsigned32 (0..4045)
	MAX-ACCESS read-write
	STATUS     current
	DESCRIPTION
		"Area code"
	::= { isdbtNIT 25 }

isdbtOverwriteAreaCode  OBJECT-TYPE
	SYNTAX     Unsigned32 (0..4045)
	MAX-ACCESS read-write
	STATUS     current
	DESCRIPTION
		"Overwrite Area code"
	::= { isdbtNIT 30 }

isdbtFrequency  OBJECT-TYPE
	SYNTAX     Unsigned32 (470000000..862000000)
 	UNITS 	"Hz"
	MAX-ACCESS read-write
	STATUS     current
	DESCRIPTION
		"Frequency"
	::= { isdbtNIT 35 }

isdbtOverwriteFrequency  OBJECT-TYPE
	SYNTAX     Unsigned32 (470000000..862000000)
 	UNITS 	"Hz"
	MAX-ACCESS read-write
	STATUS     current
	DESCRIPTION
		"Overwrite Frequency"
	::= { isdbtNIT 40 }

isdbtRemoteControlIdKey  OBJECT-TYPE
	SYNTAX     Unsigned32 (0..99)
	MAX-ACCESS read-write
	STATUS     current
	DESCRIPTION
		"Remote Control ID Key"
	::= { isdbtNIT 45 }

isdbtVirtualChannelBypass  OBJECT-TYPE
	SYNTAX     DisabledEnabled
	MAX-ACCESS read-write
	STATUS     current
	DESCRIPTION
		"Bypass Remote Control Key ID"
	::= { isdbtNIT 47 }

isdbtOverwriteRemoteControlIdKey  OBJECT-TYPE
	SYNTAX     Unsigned32 (0..99)
	MAX-ACCESS read-write
	STATUS     current
	DESCRIPTION
		"Remote Control ID Key"
	::= { isdbtNIT 50 }

isdbtTSName  OBJECT-TYPE
	SYNTAX     DisplayString (SIZE(1..18))
	MAX-ACCESS read-write
	STATUS     current
	DESCRIPTION
		"TS Name"
	::= { isdbtNIT 55 }

-- ISDBT Modulator Program Specific Information

isdbtCountry  OBJECT-TYPE
	SYNTAX     DisplayString
	MAX-ACCESS read-write
	STATUS     current
	DESCRIPTION
		"Country code"
	::= { isdbtTOT 5 }

isdbtRegionId  OBJECT-TYPE
	SYNTAX     Unsigned32 (0..63)
	MAX-ACCESS read-write
	STATUS     current
	DESCRIPTION
		"Region ID"
	::= { isdbtTOT 10 }

-- DAB

-- DAB System

dabTransmitterId  OBJECT-TYPE
	SYNTAX     Unsigned32 (0..65535)
	MAX-ACCESS read-write
	STATUS     current
	DESCRIPTION
		"Transmitter ID"
	::= { dabSystem 1 }

dabMode  OBJECT-TYPE
	SYNTAX     INTEGER {
		modeI (1),
		modeII (2),
		modeIII (3),
		modeIV (4)
	}
	MAX-ACCESS read-only
	STATUS     current
	DESCRIPTION
		"Mode"
	::= { dabSystem 5 }

-- DAB Network

dabNetworkType  OBJECT-TYPE
	SYNTAX     INTEGER {
		sfn (0),
		mfn (1)
	}
	MAX-ACCESS read-write
	STATUS     current
	DESCRIPTION
		"Network type"
	::= { dabNetwork 1 }

dabSynchronizationType  OBJECT-TYPE
	SYNTAX     INTEGER {
		relative (0),
		absolute (1)
	}
	MAX-ACCESS read-write
	STATUS     current
	DESCRIPTION
		"Synchronization type (only if SFN)"
	::= { dabNetwork 3 }

dabRelativeSfnReference  OBJECT-TYPE
	SYNTAX     INTEGER {
		nok (0),
		ok (1)
	}
	MAX-ACCESS read-only
	STATUS     current
	DESCRIPTION
		"SFN reference (relative)"
	::= { dabNetwork 4 }

dabAbsoluteSfnReference  OBJECT-TYPE
	SYNTAX     INTEGER {
		nok (0),
		ok (1)
	}
	MAX-ACCESS read-only
	STATUS     current
	DESCRIPTION
		"SFN reference (absolute)"
	::= { dabNetwork 5 }

dabAvailableTimestampType  OBJECT-TYPE
	SYNTAX     INTEGER {
		null (0),
		relativeAndAbsolute (1),
		relative (2)
	}
	MAX-ACCESS read-only
	STATUS     current
	DESCRIPTION
		"Available timestamp type"
	::= { dabNetwork 7 }

dabProcessingDelayCfg  OBJECT-TYPE
	SYNTAX     FloatingPoint
	UNITS 	"us"
	MAX-ACCESS read-write
	STATUS     current
	DESCRIPTION
		"Processing delay

		The value must be 100000.0..1000000.0 in 0.1 step
		"
	::= { dabNetwork 8 }

dabBufferingTime  OBJECT-TYPE
	SYNTAX     Unsigned32 (0..1000)
	UNITS 	"ms"
	MAX-ACCESS read-write
	STATUS     current
	DESCRIPTION
		"Buffering time (only MFN)"
	::= { dabNetwork 9 }

dabDynamicCompensationDelay  OBJECT-TYPE
	SYNTAX     DisabledEnabled
	MAX-ACCESS read-write
	STATUS     current
	DESCRIPTION
		"Dynamic compensation delay"
	::= { dabNetwork 10 }

dabMaximumBitrateOffset  OBJECT-TYPE
	SYNTAX     FloatingPoint
	UNITS 	"ppm"
	MAX-ACCESS read-write
	STATUS     current
	DESCRIPTION
		"Maximum bitrate offset"
	::= { dabNetwork 12 }

dabBitrateOffset  OBJECT-TYPE
	SYNTAX     FloatingPoint
	UNITS 	"ppm"
	MAX-ACCESS read-only
	STATUS     current
	DESCRIPTION
		"Bitrate offset"
	::= { dabNetwork 13 }

dabTimestampLevel  OBJECT-TYPE
	SYNTAX     INTEGER {
		null (0),
		one	(1),
		two (2),
		three (3),
		four (4),
		five (5)
	}
	MAX-ACCESS read-only
	STATUS     current
	DESCRIPTION
		"Timestamp level"
	::= { dabNetwork 15 }

dabTistFct  OBJECT-TYPE
	SYNTAX     Unsigned32 (0..16383999)
	UNITS	"ns"
	MAX-ACCESS read-only
	STATUS     current
	DESCRIPTION
		"TIST FCT0"
	::= { dabNetwork 17 }

dabFct0AsReference  OBJECT-TYPE
	SYNTAX     INTEGER {
		disable (0),
		enable (1)
	}
	MAX-ACCESS read-write
	STATUS     current
	DESCRIPTION
		"Use FCT0 as reference"
	::= { dabNetwork 18 }

dabLocalDelay  OBJECT-TYPE
	SYNTAX     FloatingPoint
	UNITS 	"us"
	MAX-ACCESS read-write
	STATUS     current
	DESCRIPTION
		"Local delay

		The value must be -500000.0..500000.0 in 0.1 step

		(Only SFN)
		"
	::= { dabNetwork 20 }

dabOffsetDelayAutoconfigure  OBJECT-TYPE
	SYNTAX     DisabledEnabled
	MAX-ACCESS read-write
	STATUS     current
	DESCRIPTION
		"Offset delay autoconfigure (Only SFN)"
	::= { dabNetwork 25 }

-- DAB Network > TII Code

dabTiiCodeConfiguration  OBJECT-TYPE
	SYNTAX     INTEGER {
		none (0),
		manual	(1),
		auto (2)
	}
	MAX-ACCESS read-write
	STATUS     current
	DESCRIPTION
		"TII code configuration"
	::= { dabTiiCode 1 }

dabMainId  OBJECT-TYPE
	SYNTAX     Unsigned32 (0..69)
	MAX-ACCESS read-write
	STATUS     current
	DESCRIPTION
		"Main ID"
	::= { dabTiiCode 5 }

dabSubId  OBJECT-TYPE
	SYNTAX     Unsigned32 (0..23)
	MAX-ACCESS read-write
	STATUS     current
	DESCRIPTION
		"Sub ID"
	::= { dabTiiCode 10 }

-- DAB Network > MNSC

-- DAB Network > MNSC > Time information Group

dabReceivedInformationTime  OBJECT-TYPE
	SYNTAX     NoYes
	MAX-ACCESS read-only
	STATUS     current
	DESCRIPTION
		"Time information group: received"
	::= { dabTimeInformationGroup  1 }

dabDateAndTime  OBJECT-TYPE
	SYNTAX     OCTET STRING
	MAX-ACCESS read-only
	STATUS     current
	DESCRIPTION
		"Date and time"
	::= { dabTimeInformationGroup  5 }

dabTimeAccurary  OBJECT-TYPE
	SYNTAX     NoYes
	MAX-ACCESS read-only
	STATUS     current
	DESCRIPTION
		"Time accuracy worse than 1us"
	::= { dabTimeInformationGroup  10 }

dabSynchronizationToFrame  OBJECT-TYPE
	SYNTAX     NoYes
	MAX-ACCESS read-only
	STATUS     current
	DESCRIPTION
		"Synchronization to frame"
	::= { dabTimeInformationGroup  15 }

-- DAB Network > MNSC > TSC

dabReceivedTSC  OBJECT-TYPE
	SYNTAX     NoYes
	MAX-ACCESS read-only
	STATUS     current
	DESCRIPTION
		"Transmitter Set-up and Control Information: received"
	::= { dabTsc  1 }

dabSavedTSC  OBJECT-TYPE
	SYNTAX     NoYes
	MAX-ACCESS read-only
	STATUS     current
	DESCRIPTION
		"Transmitter Set-up and Control Information: saved"
	::= { dabTsc  5 }

dabOffsetDelayTSC  OBJECT-TYPE
	SYNTAX     Unsigned32
	MAX-ACCESS read-only
	STATUS     current
	DESCRIPTION
		"Transmitter Set-up and Control Information: Offset delay"
	::= { dabTsc  10 }

dabMainIdTSC  OBJECT-TYPE
	SYNTAX     Unsigned32
	MAX-ACCESS read-only
	STATUS     current
	DESCRIPTION
		"Transmitter Set-up and Control Information: Main ID"
	::= { dabTsc  15 }

dabSubIdTSC  OBJECT-TYPE
	SYNTAX     Unsigned32
	MAX-ACCESS read-only
	STATUS     current
	DESCRIPTION
		"Transmitter Set-up and Control Information: Sub ID"
	::= { dabTsc  20 }

dabControlFlagsTSC  OBJECT-TYPE
	SYNTAX     Unsigned32
	MAX-ACCESS read-only
	STATUS     current
	DESCRIPTION
		"Transmitter Set-up and Control Information: Control Flags"
	::= { dabTsc  25 }

-- DAB Network > Timing

dabProcessingDelay  OBJECT-TYPE
	SYNTAX     FloatingPoint
	UNITS 	"us"
	MAX-ACCESS read-only
	STATUS     current
	DESCRIPTION
		"Processing delay"
	::= { dabTimmingInformation 1 }

dabMinimumProcessingDelay  OBJECT-TYPE
	SYNTAX     FloatingPoint
	UNITS 	"us"
	MAX-ACCESS read-only
	STATUS     current
	DESCRIPTION
		"Minimum processing delay"
	::= { dabTimmingInformation 2 }

--dabAdditionalProcessingDelay  OBJECT-TYPE
--	SYNTAX     FloatingPoint
--	UNITS 	"us"
--	MAX-ACCESS read-only
--	STATUS     current
--	DESCRIPTION
--		"Additional processing delay"
--	::= { dabTimmingInformation 3 }
    
dabCompensationDelay  OBJECT-TYPE
	SYNTAX     FloatingPoint
	UNITS 	"us"
	MAX-ACCESS read-only
	STATUS     current
	DESCRIPTION
		"Compensation delay"
	::= { dabTimmingInformation 5 }
    
dabMargin  OBJECT-TYPE
	SYNTAX     FloatingPoint
	UNITS 	"us"
	MAX-ACCESS read-only
	STATUS     current
	DESCRIPTION
		"Margin"
	::= { dabTimmingInformation 7 }
    
--dabTotalDelay  OBJECT-TYPE
--	SYNTAX     FloatingPoint
--	UNITS 	"us"
--	MAX-ACCESS read-only
--	STATUS     current
--	DESCRIPTION
--		"Total delay"
--	::= { dabTimmingInformation 10 }

-- DAB STC

dabStcNumberOfServices  OBJECT-TYPE
	SYNTAX     Unsigned32
	MAX-ACCESS read-only
	STATUS     current
	DESCRIPTION
		"Number of services"
	::= { dabStc 1 }

dabStreamCharacterizationTable  OBJECT-TYPE
	SYNTAX SEQUENCE OF DabStreamCharacterizationEntry
	MAX-ACCESS not-accessible
	STATUS     current
	DESCRIPTION
		"Table of Stream Characterization"
	::= { dabStc 2 }

dabStreamCharacterizationEntry  OBJECT-TYPE
	SYNTAX 	DabStreamCharacterizationEntry
	MAX-ACCESS not-accessible
	STATUS     current
	DESCRIPTION
		"Entry for a Stream Characterization"
	INDEX { dabStcIndex }
	::= { dabStreamCharacterizationTable 1 }

DabStreamCharacterizationEntry ::= SEQUENCE {
	dabStcIndex
		Unsigned32,
	dabStcSubChId
		Unsigned32,
	dabStcSubChSa
		Unsigned32,
	dabStcTpl
		OCTET STRING,
	dabStcBitrate
		FloatingPoint
}

dabStcIndex  OBJECT-TYPE
	SYNTAX     Unsigned32 (1..40)
	MAX-ACCESS not-accessible
	STATUS     current
	DESCRIPTION
		"Index DAB STC"
	::= { dabStreamCharacterizationEntry 1 }

dabStcSubChId  OBJECT-TYPE
	SYNTAX     Unsigned32
	MAX-ACCESS read-only
	STATUS     current
	DESCRIPTION
		"Sub-Ch ID"
	::= { dabStreamCharacterizationEntry 2 }

dabStcSubChSa  OBJECT-TYPE
	SYNTAX     Unsigned32
	MAX-ACCESS read-only
	STATUS     current
	DESCRIPTION
		"Sub-Ch SA"
	::= { dabStreamCharacterizationEntry 3 }

dabStcTpl  OBJECT-TYPE
	SYNTAX     OCTET STRING
	MAX-ACCESS read-only
	STATUS     current
	DESCRIPTION
		"TPL"
	::= { dabStreamCharacterizationEntry 4 }

dabStcBitrate  OBJECT-TYPE
	SYNTAX     FloatingPoint
	UNITS	"Kbps"
	MAX-ACCESS read-only
	STATUS     current
	DESCRIPTION
		"Bitrate"
	::= { dabStreamCharacterizationEntry 5 }

-- Precorrector

-- Linear precorrection

modLinearPrecorrectionEnable  OBJECT-TYPE
	SYNTAX     INTEGER {
		off (0),
		on (1)
	}
	MAX-ACCESS read-write
	STATUS     current
	DESCRIPTION
		"Enable/Disable"
	::= { modLinearPrecorrection 1 }

-- modLinearPrecorrectionAdaptative  OBJECT-TYPE
-- 	SYNTAX     INTEGER {
-- 		off (0),
-- 		on (1)
-- 	}
-- 	MAX-ACCESS read-write
-- 	STATUS     current
-- 	DESCRIPTION
-- 		"Adaptative"
-- 	::= { modLinearPrecorrection 2 }

-- Non-linear precorrection

modNonLinearPrecorrectionEnable  OBJECT-TYPE
	SYNTAX     INTEGER {
		off (0),
		adaptative (1),
		static (2)
	}
	MAX-ACCESS read-write
	STATUS     current
	DESCRIPTION
		"Mode"
	::= { modNonLinearPrecorrection 1 }

-- modNonLinearPrecorrectionAdap  OBJECT-TYPE
-- 	SYNTAX     INTEGER {
-- 		off (0),
-- 		on (1)
-- 	}
-- 	MAX-ACCESS read-write
-- 	STATUS     current
-- 	DESCRIPTION
-- 		"Adaptative"
-- 	::= { modNonLinearPrecorrection 2 }

-- Clipping

-- modClippingEnable  OBJECT-TYPE
-- 	SYNTAX     INTEGER {
-- 		off (0),
-- 		on (1)
-- 	}
-- 	MAX-ACCESS read-only
-- 	STATUS     current
-- 	DESCRIPTION
-- 		"Enable/Disable"
-- 	::= { modClipping 1 }

-- modClippingValue  OBJECT-TYPE
-- 	SYNTAX     OCTET STRING
-- 	UNITS 	"dB"
-- 	MAX-ACCESS read-only
-- 	STATUS     current
-- 	DESCRIPTION
-- 		"Clipping"
-- 	::= { modClipping 2 }

-- modClippingPapr  OBJECT-TYPE
-- 	SYNTAX     DisplayString
-- 	UNITS 	"dB"
-- 	MAX-ACCESS read-only
-- 	STATUS     current
-- 	DESCRIPTION
-- 		"PAPR"
-- 	::= { modClipping 3 }

modNonLinearStoredPrecorrection  OBJECT-TYPE
	SYNTAX     DisplayString
	MAX-ACCESS read-only
	STATUS     current
	DESCRIPTION
		"Non-Linear stored precorrection"
	::= { modNonLinearPrecorrection 3 }

modNonLinearPrecorrectorFeedback  OBJECT-TYPE
	SYNTAX     INTEGER {
		notDetected (0),
		detected (1),
		outOfRange (2)
	}
	MAX-ACCESS read-only
	STATUS     current
	DESCRIPTION
		"Non-linear precorrector feedback"
	::= { modNonLinearPrecorrection 5 }

-- Precorrector levels

modPrecorrectorInput  OBJECT-TYPE
	SYNTAX     DisplayString
	UNITS 	"dBFS"
	MAX-ACCESS read-only
	STATUS     current
	DESCRIPTION
		"Input"
	::= { modPrecorrectorLevels 1 }

modPrecorrectorStatus  OBJECT-TYPE
	SYNTAX     INTEGER {
		unlocked (0),
		locked (1)
	}
	MAX-ACCESS read-only
	STATUS     current
	DESCRIPTION
		"Status"
	::= { modPrecorrectorLevels 2 }

modPrecorrectorFeedback  OBJECT-TYPE
	SYNTAX     DisplayString
	UNITS 	"dBFS"
	MAX-ACCESS read-only
	STATUS     current
	DESCRIPTION
		"Feedback"
	::= { modPrecorrectorLevels 3 }

modPrecorrectorOutput  OBJECT-TYPE
	SYNTAX     DisplayString
	UNITS 	"dBFS"
	MAX-ACCESS read-only
	STATUS     current
	DESCRIPTION
		"Output"
	::= { modPrecorrectorLevels 4 }

-- Spectrum measures

modShoulderAlarm  OBJECT-TYPE
	SYNTAX     Unsigned32 (30..60)
	UNITS 	"dB"
	MAX-ACCESS read-write
	STATUS     current
	DESCRIPTION
		"Shoulder alarm"
	::= { modSpectrumMeasures 1 }

modLowerShoulder  OBJECT-TYPE
	SYNTAX     DisplayString
	UNITS 	"dB"
	MAX-ACCESS read-only
	STATUS     current
	DESCRIPTION
		"Lower shoulder"
	::= { modSpectrumMeasures 2 }

modUpperShoulder  OBJECT-TYPE
	SYNTAX     DisplayString
	UNITS 	"dB"
	MAX-ACCESS read-only
	STATUS     current
	DESCRIPTION
		"Upper shoulder"
	::= { modSpectrumMeasures 3 }

modInBandLevelVariation  OBJECT-TYPE
	SYNTAX     DisplayString
	UNITS 	"dB"
	MAX-ACCESS read-only
	STATUS     current
	DESCRIPTION
		"In-band level variation"
	::= { modSpectrumMeasures 4 }

modThresholdMer  OBJECT-TYPE
	SYNTAX     Unsigned32 (20..50)
	UNITS 	"dB"
	MAX-ACCESS read-write
	STATUS     current
	DESCRIPTION
		"MER alarm threshold"
	::= { modSpectrumMeasures 5 }

modMer  OBJECT-TYPE
	SYNTAX     DisplayString
	UNITS 	"dB"
	MAX-ACCESS read-only
	STATUS     current
	DESCRIPTION
		"MER"
	::= { modSpectrumMeasures 6 }

modMerFlt  OBJECT-TYPE
	SYNTAX     FloatingPoint
	UNITS 	"dB"
	MAX-ACCESS read-only
	STATUS     current
	DESCRIPTION
		"MER"
	::= { modSpectrumMeasures 7 }

modBerFlt  OBJECT-TYPE
	SYNTAX     FloatingPoint
	MAX-ACCESS read-only
	STATUS     current
	DESCRIPTION
		"BER"
	::= { modSpectrumMeasures 15 }

-- RF output

outputFrequencyMode  OBJECT-TYPE
	SYNTAX     INTEGER {
		channel (0),
		centralFrequency (1)
	}
	MAX-ACCESS read-write
	STATUS     current
	DESCRIPTION
		"Output Frequency mode"
	::= { rfOutput 1 }

outputFrequency  OBJECT-TYPE
	SYNTAX     DisplayString
	UNITS 	"Hz"
	MAX-ACCESS read-only
	STATUS     current
	DESCRIPTION
		"Output frequency"
	::= { rfOutput 2 }

outputFrequencyFlt  OBJECT-TYPE
	SYNTAX     FloatingPoint
	UNITS 	"Hz"
	MAX-ACCESS read-only
	STATUS     current
	DESCRIPTION
		"Output frequency"
	::= { rfOutput 3 }

-- Channel Mode

outputChannel  OBJECT-TYPE
	SYNTAX     Unsigned32 (14..78)
	MAX-ACCESS read-write
	STATUS     current
	DESCRIPTION
		"Channel"
	::= { outputChannelMode 1 }

outputChannelOffset  OBJECT-TYPE
	SYNTAX     Integer32 (-4..4)
	MAX-ACCESS read-write
	STATUS     current
	DESCRIPTION
		"Channel offset"
	::= { outputChannelMode 2 }

ouputChannelResolution  OBJECT-TYPE
	SYNTAX     INTEGER {
		resolution1div6 (0),
		resolution1div7 (1),
		resolution1div8 (2)
	}
	UNITS 	"MHz"
	MAX-ACCESS read-write
	STATUS     current
	DESCRIPTION
		"Channel resolution"
	::= { outputChannelMode 3 }

dabOutputChannel  OBJECT-TYPE
	SYNTAX     DabOutputChannelType
	MAX-ACCESS read-write
	STATUS     current
	DESCRIPTION
		"DAB output channel"
	::= { outputChannelMode 4 }

outputCentralFrequency  OBJECT-TYPE
	SYNTAX     Unsigned32 (173000000..862000000)
	UNITS 	"Hz"
	MAX-ACCESS read-write
	STATUS     current
	DESCRIPTION
		"Central Frequency"
	::= { outputCentralFrequencyMode 1 }

outputCentralFrequencyMHz  OBJECT-TYPE
	SYNTAX     Unsigned32 (173..862)
	UNITS 	"MHz"
	MAX-ACCESS read-write
	STATUS     current
	DESCRIPTION
		"Central Frequency"
	::= { outputCentralFrequencyMode 2 }

-- Mutes

muteOutputStatus  OBJECT-TYPE
	SYNTAX     INTEGER {
		notMuted (0),
		muted (1),
		mutedSelfProtection (2),
		stageMuted (3)
	}
	MAX-ACCESS read-only
	STATUS     current
	DESCRIPTION
		"Status"
	::= { mutes 1 }

muteCauses  OBJECT-TYPE
	SYNTAX     OCTET STRING (SIZE(256))
	MAX-ACCESS read-only
	STATUS     current
	DESCRIPTION
		"Mute causes. Each line could contain these values. The system language apply for this string.

			es='RF off' en='RF off' fr='RF off'
			es='Error TS' en='TS error' fr='Erreur TS'
			es='Desbordamiento entrada' en='Input overflow' fr='Overflow entree'
			es='Error T2MI' en='T2MI error' fr='Erreur T2MI'
			es='Referencia SFN' en='SFN Reference' fr='Reference SFN'
			es='Margen SFN' en='SFN margin' fr='Marge SFN'
			es='Error BTS' en='BTS error' fr='Erreur BTS'
			es='10MHz' en='10MHz' fr='10MHz'
			es='Temperatura' en='Temperature' fr='Temperature'
			es='Potencia reflejada' en='Reverse power' fr='Puissance reflechie'
			es='Redundancia (Antena)' en='Redundancy (Antenna)' fr='Redondance (Antenne)'
			es='Redundancia (Carga)' en='Redundancy (Load)' fr='Redondance (Charge)'
			es='Redundancia (Conmutacion)' en='Redundancy (Switching)' fr='Redondance (Commutation)'
			es='Potencia elevada' en='Elevated power' fr='Puissance elevee'
			es='Redundancia (Inicializacion)' en='Redundancy (Inicialization)' fr='Redondance (Initialisation)'
			es='Entrada RF' en='RF input' fr='Entree RF'
			es='Error HW PD' en='HW error PD' fr='Erreur HW PD'
			es='RF loop' en='RF loop' fr='RF loop'
			es='Interlock R' en='Interlock R' fr='Interlock R'
			es='Interlock 1' en='Interlock 1' fr='Interlock 1'
			es='Interlock 2' en='Interlock 2' fr='Interlock 2'
			es='Margen de ganancia' en='Gain margin' fr='Marge de gain'
			es='Error MIP' en='MIP error' fr='Erreur MIP'
		"
	::= { mutes 2 }

mutesRf  OBJECT-TYPE
	SYNTAX     DisabledEnabled
	MAX-ACCESS read-write
	STATUS     current
	DESCRIPTION
		"RF mute"
	::= { mutes 3 }

muteTsError  OBJECT-TYPE
	SYNTAX     DisabledEnabled
	MAX-ACCESS read-write
	STATUS     current
	DESCRIPTION
		"TS error mute"
	::= { mutes 4 }

muteMpegOverflow  OBJECT-TYPE
	SYNTAX     DisabledEnabled
	MAX-ACCESS read-write
	STATUS     current
	DESCRIPTION
		"MPEG overflow mute"
	::= { mutes 5 }

muteT2miError  OBJECT-TYPE
	SYNTAX     DisabledEnabled
	MAX-ACCESS read-write
	STATUS     current
	DESCRIPTION
		"T2MI error mute"
	::= { mutes 6 }

muteBtsError  OBJECT-TYPE
	SYNTAX     DisabledEnabled
	MAX-ACCESS read-write
	STATUS     current
	DESCRIPTION
		"BTS error mute"
	::= { mutes 7 }

muteSfnReference  OBJECT-TYPE
	SYNTAX     DisabledEnabled
	MAX-ACCESS read-write
	STATUS     current
	DESCRIPTION
		"SFN Reference mute"
	::= { mutes 8 }

muteSfnMargin  OBJECT-TYPE
	SYNTAX     DisabledEnabled
	MAX-ACCESS read-write
	STATUS     current
	DESCRIPTION
		"SFN Margin mute"
	::= { mutes 9 }

mute10MHz  OBJECT-TYPE
	SYNTAX     DisabledEnabled
	MAX-ACCESS read-write
	STATUS     current
	DESCRIPTION
		"10MHz mute"
	::= { mutes 10 }

muteGainMargin  OBJECT-TYPE
	SYNTAX     DisabledEnabled
	MAX-ACCESS read-write
	STATUS     current
	DESCRIPTION
		"Gain margin mute"
	::= { mutes 11 }

muteErrorMip  OBJECT-TYPE
	SYNTAX     DisabledEnabled
	MAX-ACCESS read-write
	STATUS     current
	DESCRIPTION
		"MIP error mute"
	::= { mutes 12 }

tsErrorMuteHysteresis  OBJECT-TYPE
	SYNTAX     Unsigned32 (0..99)
	MAX-ACCESS read-write
	STATUS     current
	DESCRIPTION
		"TS error mute hysteresis"
	::= { mutes 45 }

muteCausesBinary  OBJECT-TYPE
	SYNTAX     BITS{
		absence10mhz (0),
		btsError (1),
		sfnMargin (2),
		sfnReference (3),
		t2miError (4),
		inputOverflow (5),
		tsError (6),
		rfOff (7),
		rfInput (8),
		redundancyInitialization (9),
		elevatedPower (10),
		redundancySwitching (11),
		redundancyLoad (12),
		redundancyAntenna (13),
		reversePower (14),
		temperature (15),
		muteCausesBin16 (16),
		muteCausesBin17 (17),
		muteCausesBin18 (18),
		interlock2 (19),
		interlock1 (20),
		interlock (21),
		rfLoop (22),
		hwErrorPd (23),
		muteCausesBin24 (24),
		muteCausesBin25 (25),
		muteCausesBin26 (26),
		muteCausesBin27 (27),
		muteCausesBin28 (28),
		muteCausesBin29 (29),
		mipError (30),
		gainMargin (31)
	}
	MAX-ACCESS read-only
	STATUS     current
	DESCRIPTION
		"Mute causes. Binary value."
	::= { mutes 50 }

--  Reference

referenceSourceStatus  OBJECT-TYPE
	SYNTAX     INTEGER {
		referenceInternalHwNotDetect (0),
		referenceGnss (1),
		referenceExternalOcxo (2),
		referenceExternal (3),
		referenceInternal (4),
		referenceInternalOcxo (5)
	}
	MAX-ACCESS read-only
	STATUS     current
	DESCRIPTION
		"Reference"
	::= { referenceSource 1 }

referenceSwitchMode  OBJECT-TYPE
	SYNTAX     INTEGER {
		referenceSwitchAuto (0),
		referenceSwitchGnss (1),
		referenceSwitchExternalOcxo (2),
		referenceSwitchExternal (3),
		referenceSwitchInternal (4),
		referenceSwitchInternalOcxo (5)
	}
	MAX-ACCESS read-write
	STATUS     current
	DESCRIPTION
		"Switching mode"
	::= { referenceSource 2 }

synchronizationReady  OBJECT-TYPE
	SYNTAX     INTEGER {
		locked (0),
		lockedHoldover (1)
	}
	MAX-ACCESS read-write
	STATUS     current
	DESCRIPTION
		"Synchronization module ready"
	::= { referenceSource 3 }

externalReferenceOutputs  OBJECT-TYPE
	SYNTAX     INTEGER {
		auto (0),
		disabled (1),
		enabled (2)
	}
	MAX-ACCESS read-write
	STATUS     current
	DESCRIPTION
		"External reference outputs"
	::= { referenceSource 4 }

selected10Mhz  OBJECT-TYPE
	SYNTAX     INTEGER {
		null (0),
		available (1),
		notAvailable (2)
	}
	MAX-ACCESS read-only
	STATUS     current
	DESCRIPTION
		"Selected 10MHz (10MHz output)"
	::= { referenceSource 5 }

selected1Pps  OBJECT-TYPE
	SYNTAX     INTEGER {
		null (0),
		available (1),
		notAvailable (2)
	}
	MAX-ACCESS read-only
	STATUS     current
	DESCRIPTION
		"Selected 1PPS (1PPS output)"
	::= { referenceSource 6 }

-- Synchronization module

receiverType  OBJECT-TYPE
	SYNTAX     DisplayString
	MAX-ACCESS read-only
	STATUS     current
	DESCRIPTION
		"Receiver type"
	::= { synchronization 2 }

receiverSerial  OBJECT-TYPE
	SYNTAX     DisplayString
	MAX-ACCESS read-only
	STATUS     current
	DESCRIPTION
		"Serial Number"
	::= { synchronization 3 }

synchronizationStatus  OBJECT-TYPE
	SYNTAX     INTEGER {
		notConnected (0),
		detected (1),
		connected (2),
		notConfigured (3),
		unlocked (4),
		locked (5),
		holdover (6),
		postHoldover (7),
		damaged (8),
		notDetected (9),
		sfnNok (10),
		disabled (11),
		communicationError (12),
		versionError (13),
		hwInstallError (14)
	}
	MAX-ACCESS read-only
	STATUS     current
	DESCRIPTION
		"Status"
	::= { synchronization 4 }

satellitesAntenna  OBJECT-TYPE
	SYNTAX     INTEGER {
		notDetected (0),
		detected (1)
	}
	MAX-ACCESS read-only
	STATUS     current
	DESCRIPTION
		"Satellites antenna"
	::= { synchronization 5 }

input1pps  OBJECT-TYPE
	SYNTAX     INTEGER {
		notDetected (0),
		detected (1)
	}
	MAX-ACCESS read-only
	STATUS     current
	DESCRIPTION
		"1PPS intput"
	::= { synchronization 6 }

synchronizationTemperature  OBJECT-TYPE
	SYNTAX     DisplayString
	MAX-ACCESS read-only
	STATUS     current
	DESCRIPTION
		"Synchronization module temperature"
	::= { synchronization 7 }

synchronizationHoldover  OBJECT-TYPE
	SYNTAX     DisplayString
	MAX-ACCESS read-only
	STATUS     current
	DESCRIPTION
		"Holdover time"
	::= { synchronization 8 }

synchronizationHoldoverThreshold  OBJECT-TYPE
	SYNTAX     Unsigned32 (0..255)
	UNITS 	"h"
	MAX-ACCESS read-write
	STATUS     current
	DESCRIPTION
		"Holdover limit"
	::= { synchronization 9 }

endlessHoldoverThresholdEnable  OBJECT-TYPE
	SYNTAX     DisabledEnabled
	MAX-ACCESS read-write
	STATUS     current
	DESCRIPTION
		"Mode"
	::= { synchronization 10 }

input10Mhz  OBJECT-TYPE
	SYNTAX     INTEGER {
		notDetected (0),
		detected (1)
	}
	MAX-ACCESS read-only
	STATUS     current
	DESCRIPTION
		"10Mhz intput"
	::= { synchronization 11 }

antennaStatus  OBJECT-TYPE
	SYNTAX     INTEGER {
		notPowered (0),
		powered (1),
		shortCircuit (2)
	}
	MAX-ACCESS read-only
	STATUS     current
	DESCRIPTION
		"Antenna Status"
	::= { synchronization 12 }

ppsStatus  OBJECT-TYPE
	SYNTAX     INTEGER {
		available (0),
		notAvailable (1)
	}
	MAX-ACCESS read-only
	STATUS     current
	DESCRIPTION
		"PPS Status"
	::= { synchronization 13 }

latitude  OBJECT-TYPE
	SYNTAX     DisplayString
	MAX-ACCESS read-only
	STATUS     current
	DESCRIPTION
		"Latitude"
	::= { synchronization 20 }

longitude  OBJECT-TYPE
	SYNTAX     DisplayString
	MAX-ACCESS read-only
	STATUS     current
	DESCRIPTION
		"Longitude"
	::= { synchronization 21 }

altitude  OBJECT-TYPE
	SYNTAX     DisplayString
	MAX-ACCESS read-only
	STATUS     current
	DESCRIPTION
		"Altitude"
	::= { synchronization 22 }

synchronizationDate  OBJECT-TYPE
	SYNTAX     DisplayString
	MAX-ACCESS read-only
	STATUS     current
	DESCRIPTION
		"Synchronization module date"
	::= { synchronization 23 }

satellite01  OBJECT-TYPE
	SYNTAX     DisplayString
	MAX-ACCESS read-only
	STATUS     obsolete
	DESCRIPTION
		"Synchronization Satellite 1"
	::= { synchronization 30 }

satellite02  OBJECT-TYPE
	SYNTAX     DisplayString
	MAX-ACCESS read-only
	STATUS     obsolete
	DESCRIPTION
		"Synchronization Satellite 2"
	::= { synchronization 31 }

satellite03  OBJECT-TYPE
	SYNTAX     DisplayString
	MAX-ACCESS read-only
	STATUS     obsolete
	DESCRIPTION
		"Synchronization Satellite 3"
	::= { synchronization 32 }

satellite04  OBJECT-TYPE
	SYNTAX     DisplayString
	MAX-ACCESS read-only
	STATUS     obsolete
	DESCRIPTION
		"Synchronization Satellite 4"
	::= { synchronization 33 }

satellite05  OBJECT-TYPE
	SYNTAX     DisplayString
	MAX-ACCESS read-only
	STATUS     obsolete
	DESCRIPTION
		"Synchronization Satellite 5"
	::= { synchronization 34 }

satellite06  OBJECT-TYPE
	SYNTAX     DisplayString
	MAX-ACCESS read-only
	STATUS     obsolete
	DESCRIPTION
		"Synchronization Satellite 6"
	::= { synchronization 35 }

satellite07  OBJECT-TYPE
	SYNTAX     DisplayString
	MAX-ACCESS read-only
	STATUS     obsolete
	DESCRIPTION
		"Synchronization Satellite 7"
	::= { synchronization 36 }

satellite08  OBJECT-TYPE
	SYNTAX     DisplayString
	MAX-ACCESS read-only
	STATUS     obsolete
	DESCRIPTION
		"Synchronization Satellite 8"
	::= { synchronization 37 }

satellitesConstellationTable  OBJECT-TYPE
	SYNTAX SEQUENCE OF SatellitesConstellationEntry
	MAX-ACCESS not-accessible
	STATUS     current
	DESCRIPTION
		"Table for SNR satellites in Constellation GPS/GNSS"
	::= { synchronization 50 }

satellitesConstellationEntry  OBJECT-TYPE
	SYNTAX 	SatellitesConstellationEntry
	MAX-ACCESS not-accessible
	STATUS     current
	DESCRIPTION
		"Entry for a Satellite Info"
	INDEX { constellationIndex }
	::= { satellitesConstellationTable 1 }

SatellitesConstellationEntry ::= SEQUENCE {
	constellationIndex
		Unsigned32,
	satellite01Info
		DisplayString,
	satellite02Info
		DisplayString,
	satellite03Info
		DisplayString,
	satellite04Info
		DisplayString,
	satellite05Info
		DisplayString,
	satellite06Info
		DisplayString,
	satellite07Info
		DisplayString,
	satellite08Info
		DisplayString
}

constellationIndex  OBJECT-TYPE
	SYNTAX     Unsigned32 (1..2)
	MAX-ACCESS not-accessible
	STATUS     current
	DESCRIPTION
		"Index satellite info"
	::= { satellitesConstellationEntry 1 }

satellite01Info  OBJECT-TYPE
	SYNTAX     DisplayString
	MAX-ACCESS read-only
	STATUS     current
	DESCRIPTION
		"Satellite 01 info"
	::= { satellitesConstellationEntry 2 }

satellite02Info  OBJECT-TYPE
	SYNTAX     DisplayString
	MAX-ACCESS read-only
	STATUS     current
	DESCRIPTION
		"Satellite 02 info"
	::= { satellitesConstellationEntry 3 }

satellite03Info  OBJECT-TYPE
	SYNTAX     DisplayString
	MAX-ACCESS read-only
	STATUS     current
	DESCRIPTION
		"Satellite 03 info"
	::= { satellitesConstellationEntry 4 }

satellite04Info  OBJECT-TYPE
	SYNTAX     DisplayString
	MAX-ACCESS read-only
	STATUS     current
	DESCRIPTION
		"Satellite 04 info"
	::= { satellitesConstellationEntry 5 }

satellite05Info  OBJECT-TYPE
	SYNTAX     DisplayString
	MAX-ACCESS read-only
	STATUS     current
	DESCRIPTION
		"Satellite 05 info"
	::= { satellitesConstellationEntry 6 }

satellite06Info  OBJECT-TYPE
	SYNTAX     DisplayString
	MAX-ACCESS read-only
	STATUS     current
	DESCRIPTION
		"Satellite 06 info"
	::= { satellitesConstellationEntry 7 }

satellite07Info  OBJECT-TYPE
	SYNTAX     DisplayString
	MAX-ACCESS read-only
	STATUS     current
	DESCRIPTION
		"Satellite 07 info"
	::= { satellitesConstellationEntry 8 }

satellite08Info  OBJECT-TYPE
	SYNTAX     DisplayString
	MAX-ACCESS read-only
	STATUS     current
	DESCRIPTION
		"Satellite 08 info"
	::= { satellitesConstellationEntry 9 }

-- Amplifier

configuredPower  OBJECT-TYPE
	SYNTAX     OCTET STRING (SIZE(1..3))
	UNITS			"W"
	MAX-ACCESS read-write
	STATUS     current
	DESCRIPTION
		"Configured power"
	::= { amplifier 1 }

powerDisplaOffset  OBJECT-TYPE
	SYNTAX     OCTET STRING (SIZE(1..5))
	UNITS			"dB"
	MAX-ACCESS read-write
	STATUS     current
	DESCRIPTION
		"Power display offset (-30.0 .. 30.0)"
	::= { amplifier 2 }

forwardPower  OBJECT-TYPE
	SYNTAX     DisplayString
	UNITS			"W"
	MAX-ACCESS read-only
	STATUS     current
	DESCRIPTION
		"Forward power"
	::= { amplifier 3 }

reversePower  OBJECT-TYPE
	SYNTAX     DisplayString
	MAX-ACCESS read-only
	STATUS     current
	DESCRIPTION
		"Reserve power"
	::= { amplifier 4 }

exceededPowerThreshold  OBJECT-TYPE
	SYNTAX     OCTET STRING (SIZE(1..3))
	UNITS 	"dB"
	MAX-ACCESS read-write
	STATUS     current
	DESCRIPTION
		"Exceeded power threshold (0.5 .. 2.0)"
	::= { amplifier 5 	}

decreasedPowerThreshold  OBJECT-TYPE
	SYNTAX     OCTET STRING (SIZE(1..4))
	UNITS 	"dB"
	MAX-ACCESS read-write
	STATUS     current
	DESCRIPTION
		"Decreased power threshold (-6.0 .. -1.0)"
	::= { amplifier 6 }

reverserPowerThreshold  OBJECT-TYPE
	SYNTAX     Integer32 (-12..-6)
	UNITS 	"dB"
	MAX-ACCESS read-write
	STATUS     current
	DESCRIPTION
		"Reverse power threshold"
	::= { amplifier 7 }

amplifierStageTemperature  OBJECT-TYPE
	SYNTAX     DisplayString
	UNITS			"C"
	MAX-ACCESS read-only
	STATUS     current
	DESCRIPTION
		"Amplifier stage temperature threshold"
	::= { amplifier 8 }

ldmosTransistor1Current  OBJECT-TYPE
	SYNTAX     OCTET STRING (SIZE(10))
	UNITS 	"A"
	MAX-ACCESS read-only
	STATUS     current
	DESCRIPTION
		"LDMOS Transistor 1 current"
	::= { amplifier 9 }

ldmosTransistor2Current  OBJECT-TYPE
	SYNTAX     OCTET STRING (SIZE(10))
	UNITS 	"A"
	MAX-ACCESS read-only
	STATUS     current
	DESCRIPTION
		"LDMOS Transistor 2 current"
	::= { amplifier 10 }

ldmosTransistor3Current  OBJECT-TYPE
	SYNTAX     OCTET STRING (SIZE(10))
	UNITS 	"A"
	MAX-ACCESS read-only
	STATUS     current
	DESCRIPTION
		"LDMOS Transistor 3 current"
	::= { amplifier 11 }

ldmosTransistor4Current  OBJECT-TYPE
	SYNTAX     OCTET STRING (SIZE(10))
	UNITS 	"A"
	MAX-ACCESS read-only
	STATUS     current
	DESCRIPTION
		"LDMOS Transistor 4 current"
	::= { amplifier 12 }

decreasedPowerThresholdNonCrit  OBJECT-TYPE
	SYNTAX     OCTET STRING (SIZE(1..4))
	UNITS 	"dB"
	MAX-ACCESS read-write
	STATUS     current
	DESCRIPTION
		"Decreased power threshold Non-critical (-6.0 .. -1.0)"
	::= { amplifier 15 }

reversePowerFlt  OBJECT-TYPE
	SYNTAX     FloatingPoint
	UNITS	"W"
	MAX-ACCESS read-only
	STATUS     current
	DESCRIPTION
		"Reserve power"
	::= { amplifier 18 }

--- Automatic power compensation

automaticPowerCompensationEnable  OBJECT-TYPE
	SYNTAX     DisabledEnabled
	MAX-ACCESS read-write
	STATUS     current
	DESCRIPTION
		"Enable/Disable automatic power compensation"
	::= { automaticPowerCompensation 3 }

compensationPerStage  OBJECT-TYPE
	SYNTAX     FloatingPoint
	UNITS	"W"
	MAX-ACCESS read-only
	STATUS     current
	DESCRIPTION
		"Compensation [per stage]"
	::= { automaticPowerCompensation 6 }

-- Multiampli

amplifierStageTable  OBJECT-TYPE
	SYNTAX SEQUENCE OF AmplifierStageEntry
	MAX-ACCESS not-accessible
	STATUS     current
	DESCRIPTION
		"Table for amplifier stages"
	::= { amplifier 20 }

amplifierStageEntry  OBJECT-TYPE
	SYNTAX 	AmplifierStageEntry
	MAX-ACCESS not-accessible
	STATUS     current
	DESCRIPTION
		"Entry for an amplifier stage"
	INDEX { amplifierStageIndex }
	::= { amplifierStageTable 1 }

AmplifierStageEntry ::= SEQUENCE {
	amplifierStageIndex
		Unsigned32,
	amStControlStatus
		INTEGER,
	amStHwStatus
		DisplayString,
 	amStMuteSelfProtection
		DisplayString,
	amStForwardPower
		DisplayString,
	amStReversePower
		DisplayString,
	amStRfPhase
		Unsigned32,
	amStTemperature
		DisplayString,
	amStCurrent1
		DisplayString,
	amStCurrent2
		DisplayString,
	amStCurrent3
		DisplayString,
	amStCurrent4
		DisplayString,
	amStCurrent5
		DisplayString,
	amStCurrent6
		DisplayString,
	amStReversePowerFlt
		FloatingPoint
}

amplifierStageIndex  OBJECT-TYPE
	SYNTAX     Unsigned32 (1..4)
	MAX-ACCESS not-accessible
	STATUS     current
	DESCRIPTION
		"Index amplifier stage"
	::= { amplifierStageEntry 1 }

amStControlStatus  OBJECT-TYPE
	SYNTAX     INTEGER {
		error (0),
		ok (1),
		errorSwVersion (2),
		errorNoSwVersion (3),
		errorNoAddress (4),
		errorCollision (5)
	}
	MAX-ACCESS read-only
	STATUS     current
	DESCRIPTION
		"Control status"
	::= { amplifierStageEntry 2 }

amStHwStatus  OBJECT-TYPE
	SYNTAX    DisplayString
	MAX-ACCESS read-only
	STATUS     current
	DESCRIPTION
		"HW status"
	::= { amplifierStageEntry 3 }

amStMuteSelfProtection  OBJECT-TYPE
	SYNTAX     DisplayString
	MAX-ACCESS read-only
	STATUS     current
	DESCRIPTION
		"Mute (Self-Protection). Each line could contain these values. The system language apply for this string.

			es='Temperatura' en='Temperature' fr='Temperature'
			es='Potencia reflejada' en='Reverse power' fr='Puissance reflechie'
			es='Potencia elevada' en='Elevated power' fr='Puissance elevee'
			es='Error HW PD' en='HW error PD' fr='Erreur HW PD'

		"
	::= { amplifierStageEntry 4 }

amStForwardPower  OBJECT-TYPE
	SYNTAX     DisplayString
	MAX-ACCESS read-only
	STATUS     current
	DESCRIPTION
		"Forward power"
	::= { amplifierStageEntry 5 }

amStReversePower  OBJECT-TYPE
	SYNTAX     DisplayString
	MAX-ACCESS read-only
	STATUS     current
	DESCRIPTION
		"Reverse power"
	::= { amplifierStageEntry 6 }

amStRfPhase  OBJECT-TYPE
	SYNTAX     Unsigned32 (0..3)
	MAX-ACCESS read-write
	STATUS     current
	DESCRIPTION
		"RF Phase"
	::= { amplifierStageEntry 7 }

amStTemperature  OBJECT-TYPE
	SYNTAX     DisplayString
	MAX-ACCESS read-only
	STATUS     current
	DESCRIPTION
		"Amplifier stage temperature"
	::= { amplifierStageEntry 8 }

amStCurrent1  OBJECT-TYPE
	SYNTAX     DisplayString
	UNITS		"A"
	MAX-ACCESS read-only
	STATUS     current
	DESCRIPTION
		"LDMOS transistor 1 current"
	::= { amplifierStageEntry 9 }

amStCurrent2  OBJECT-TYPE
	SYNTAX     DisplayString
	UNITS		"A"
	MAX-ACCESS read-only
	STATUS     current
	DESCRIPTION
		"LDMOS transistor 2 current"
	::= { amplifierStageEntry 10 }

amStCurrent3  OBJECT-TYPE
	SYNTAX     DisplayString
	UNITS		"A"
	MAX-ACCESS read-only
	STATUS     current
	DESCRIPTION
		"LDMOS transistor 3 current"
	::= { amplifierStageEntry 11 }

amStCurrent4  OBJECT-TYPE
	SYNTAX     DisplayString
	UNITS		"A"
	MAX-ACCESS read-only
	STATUS     current
	DESCRIPTION
		"LDMOS transistor 4 current"
	::= { amplifierStageEntry 12 }

amStCurrent5  OBJECT-TYPE
	SYNTAX     DisplayString
	UNITS		"A"
	MAX-ACCESS read-only
	STATUS     current
	DESCRIPTION
		"LDMOS transistor 5 current"
	::= { amplifierStageEntry 13 }

amStCurrent6  OBJECT-TYPE
	SYNTAX     DisplayString
	UNITS		"A"
	MAX-ACCESS read-only
	STATUS     current
	DESCRIPTION
		"LDMOS transistor 6 current"
	::= { amplifierStageEntry 14 }

amStReversePowerFlt  OBJECT-TYPE
	SYNTAX     FloatingPoint
	UNITS	"W"
	MAX-ACCESS read-only
	STATUS     current
	DESCRIPTION
		"Reverse power"
	::= { amplifierStageEntry 15 }

-- Redundancy

-- Redundancy 1+1 & DualDrive 

rPrDdDeviceIdentifier  OBJECT-TYPE
	SYNTAX     INTEGER {
		undefined (0),
		deviceB (1),
		deviceA (2)
	}
	MAX-ACCESS read-only
	STATUS     current
	DESCRIPTION
		"Device identifier.

		Only full redundancy mode (Control Bus).
		Available in PassiveReserve and DualDrive"
	::= { redundancy1p1 1 }

rPrDdControlBusStatus  OBJECT-TYPE
	SYNTAX     INTEGER {
		error (0),
		ok (1),
		versionError (2),
		redundancyTypeError (3),
		collisionError (4)
	}
	MAX-ACCESS read-only
	STATUS     current
	DESCRIPTION
		"Control bus status.

		Only full redundancy mode (Control Bus)
		Available for PassiveReserve and DualDrive"
	::= { redundancy1p1 2 }

rPrDdSystemIp  OBJECT-TYPE
	SYNTAX     IpAddress
	MAX-ACCESS read-write
	STATUS     current
	DESCRIPTION
		"Redundant system IP address.

		Only full redundancy mode (Control Bus)
		Available for PassiveReserve and DualDrive"
	::= { redundancy1p1 3 }

r1p1EnableNCB  OBJECT-TYPE
	SYNTAX     DisabledEnabled
	MAX-ACCESS read-write
	STATUS     current
	DESCRIPTION
		"Enable/disable.

		Only simple redundancy mode (No Control Bus)"
	::= { redundancy1p1 5 }

rPrDdSwitchToAntenna  OBJECT-TYPE
	SYNTAX     INTEGER {
		null (0),
		deviceA (1),
		deviceB (2)
	}
	MAX-ACCESS read-write
	STATUS     current
	DESCRIPTION
		"Switch to antenna.

		Only full redundancy mode (Control Bus)
		Available for PassiveReserve and DualDrive"
	::= { redundancy1p1 6 }

r1p1StatusNCB  OBJECT-TYPE
	SYNTAX     INTEGER {
		enabled (0),
		notReadyInitializing (1),
		loadNotReadyNotVerified (2),
		loadNotReadyVerifying (3),
		loadNotReadyLastVerificationNok (4),
		loadNotReadyLastVerificationOk (5),
		loadNotReadyTestingInput (6),
		loadReady (7),
		antennaNok (8),
		disabled (10),
		loadManual (11),
		antennaManual (12),
		manual (13)
	}
	MAX-ACCESS read-only
	STATUS     current
	DESCRIPTION
		"Status.

		Only simple redundancy mode (No Control Bus)"
	::= { redundancy1p1 7 }

r1p1SwitchingCausesNCB OBJECT-TYPE
	SYNTAX     OCTET STRING (SIZE(256))
	MAX-ACCESS read-only
	STATUS     current
	DESCRIPTION
		"Switching causes.

		Only simple redundancy mode (No Control Bus)"
	::= { redundancy1p1 8 }

r1p1Mode  OBJECT-TYPE
	SYNTAX     INTEGER {
		manual (0),
		automatic (1),
		maintenance (2)
	}
	MAX-ACCESS read-write
	STATUS     current
	DESCRIPTION
		"Mode

		Available for simple and full redundancy mode.
		Available for PassiveReserve and DualDrive."
	::= { redundancy1p1 9 }

r1p1PriorityAB OBJECT-TYPE
	SYNTAX     INTEGER {
		aEqB (0),
		aGtB (1),
		aLtB (2)
	}
	MAX-ACCESS read-write
	STATUS     current
	DESCRIPTION
		"Priority CAN mode
		A Equal/Greather than/Lower than B

		Available for simple and full redundancy mode.
		Available for PassiveReserve and DualDrive."
	::= { redundancy1p1 10 }

r1p1priorityNCB  OBJECT-TYPE
	SYNTAX     INTEGER {
		low (0),
		high (1)
	}
	MAX-ACCESS read-write
	STATUS     current
	DESCRIPTION
		"Priority.

		Only simple redundancy mode (No Control Bus)"
	::= { redundancy1p1 11 }

r1p1AutoReturn OBJECT-TYPE
 SYNTAX					DisabledEnabled
	MAX-ACCESS read-write
	STATUS     current
	DESCRIPTION
		"Priority CAN mode

		Available for simple and full redundancy mode.
		Available for PassiveReserve and DualDrive."
	::= { redundancy1p1 12 }

r1p1Switchings  OBJECT-TYPE
	SYNTAX     Unsigned32
	MAX-ACCESS read-only
	STATUS     current
	DESCRIPTION
		"Performed switchings (today)

		Available for simple and full redundancy mode.
		Avialable for PassiveReserve and DualDrive."
	::= { redundancy1p1 15 }

r1p1MaximumSwitchings  OBJECT-TYPE
	SYNTAX     Unsigned32 (0..99)
	MAX-ACCESS read-write
	STATUS     current
	DESCRIPTION
		"Maximum switchings / day

		Available for simple and full redundancy mode.
		Avialable for PassiveReserve and DualDrive."
	::= { redundancy1p1 16 }

r1p1InputTest  OBJECT-TYPE
	SYNTAX     Unsigned32 (0..99)
	MAX-ACCESS read-write
	STATUS     current
	DESCRIPTION
		"Input test"
	::= { redundancy1p1 17 }

r1p1InputValidation  OBJECT-TYPE
	SYNTAX     Unsigned32 (0..99)
	UNITS 	"seconds"
	MAX-ACCESS read-write
	STATUS     current
	DESCRIPTION
		"Input error test"
	::= { redundancy1p1 18 }

r1p1PowerValidation  OBJECT-TYPE
	SYNTAX     Unsigned32 (0..99)
	UNITS 	"seconds"
	MAX-ACCESS read-write
	STATUS     current
	DESCRIPTION
		"Power validation"
	::= { redundancy1p1 19 }

r1p1SwitchingHysteresis  OBJECT-TYPE
	SYNTAX     Unsigned32 (0..99)
	UNITS 	"seconds"
	MAX-ACCESS read-write
	STATUS     current
	DESCRIPTION
		"Switching hysteresis"
	::= { redundancy1p1 20 }

r1p1RfSwitchStatus  OBJECT-TYPE
	SYNTAX     INTEGER {
		null (0),
		ok (1),
		errorNoPosition (2),
		errorBlocked (3)
	}
	MAX-ACCESS read-only
	STATUS     current
	DESCRIPTION
		"RF switch status"
	::= { redundancy1p1 21 }

r1p1StatusA  OBJECT-TYPE
	SYNTAX     RedundancyDeviceStatus
	MAX-ACCESS read-only
	STATUS     current
	DESCRIPTION
		"Indication for MUX A status."
	::= { r1p1DeviceA 1 }

switchingCausesA  OBJECT-TYPE
	SYNTAX     OCTET STRING (SIZE(256))
	MAX-ACCESS read-only
	STATUS     current
	DESCRIPTION
		"Switchin causes A"
	::= { r1p1DeviceA 5 }

r1p1StatusB  OBJECT-TYPE
	SYNTAX     RedundancyDeviceStatus
	MAX-ACCESS read-only
	STATUS     current
	DESCRIPTION
		"Indication for MUX B status."
	::= { r1p1DeviceB 1 }

switchingCausesB  OBJECT-TYPE
	SYNTAX     OCTET STRING (SIZE(256))
	MAX-ACCESS read-only
	STATUS     current
	DESCRIPTION
		"Switchin causes B"
	::= { r1p1DeviceB 5 }

-- RF Status

r1p1StatusWhenAntenna  OBJECT-TYPE
	SYNTAX     INTEGER {
		rfOff (0),
		rfOn (1)
	}
	MAX-ACCESS read-write
	STATUS     current
	DESCRIPTION
		"When antenna (RF Status when the output is to antenna)"
	::= { r1p1RfStatus 1 }

r1p1StatusWhenLoad  OBJECT-TYPE
	SYNTAX     INTEGER {
		rfOff (0),
		rfOn (1)
	}
	MAX-ACCESS read-write
	STATUS     current
	DESCRIPTION
		"When load (RF Status when the output is to load)"
	::= { r1p1RfStatus 2 }

-- Automatic verifications

r1p1AutoVerificationsStatus  OBJECT-TYPE
	SYNTAX     DisabledEnabled
	MAX-ACCESS read-write
	STATUS     current
	DESCRIPTION
		"Automatic verifications"
	::= { r1p1AutoVerifications 1 }


r1p1AutoVDuration  OBJECT-TYPE
	SYNTAX     Unsigned32 (0..9999)
	UNITS 	"min"
	MAX-ACCESS read-write
	STATUS     current
	DESCRIPTION
		"Duration"
	::= { r1p1AutoVerifications 2 }

r1p1AutoVPerformedVerifications  OBJECT-TYPE
	SYNTAX     Unsigned32
	MAX-ACCESS read-only
	STATUS     current
	DESCRIPTION
		"Performed verifications"
	::= { r1p1AutoVerifications 3 }

r1p1AutoVMaxVerifications  OBJECT-TYPE
	SYNTAX     Unsigned32 (0..99)
	MAX-ACCESS read-write
	STATUS     current
	DESCRIPTION
		"Maximum verification"
	::= { r1p1AutoVerifications 4 }

r1p1AutoVNexVerification  OBJECT-TYPE
	SYNTAX     DisplayString
	MAX-ACCESS read-only
	STATUS     current
	DESCRIPTION
		"Next verification in"
	::= { r1p1AutoVerifications 5 }

-- Automatic verif.: Reiterated with cadende

r1p1AutoVReiteratedEnable  OBJECT-TYPE
	SYNTAX     DisabledEnabled
	MAX-ACCESS read-write
	STATUS     current
	DESCRIPTION
		"enable/disable"
	::= { r1p1AutoVReiterated 1 }

r1p1AutoVReiteratedPeriod  OBJECT-TYPE
	SYNTAX     Unsigned32 (0..99)
	UNITS 	"min"
	MAX-ACCESS read-write
	STATUS     current
	DESCRIPTION
		"Period"
	::= { r1p1AutoVReiterated 2 }

r1p1AutoVReiteratedCadence  OBJECT-TYPE
	SYNTAX     INTEGER {
		simple (0),
		double (1),
		triple (2)
	}
	MAX-ACCESS read-write
	STATUS     current
	DESCRIPTION
		"Cadence"
	::= { r1p1AutoVReiterated 3 }

-- Automatic verifications: Daily

r1p1AutoVDailyEnable  OBJECT-TYPE
	SYNTAX     DisabledEnabled
	MAX-ACCESS read-write
	STATUS     current
	DESCRIPTION
		"enable/disable"
	::= { r1p1AutoVDaily 1 }

r1p1AutoVDailyTime  OBJECT-TYPE
	SYNTAX     OCTET STRING (SIZE(5))
	MAX-ACCESS read-write
	STATUS     current
	DESCRIPTION
		"Time HH:MM"
	::= { r1p1AutoVDaily 2 }

r1p1AutoVDailyMode  OBJECT-TYPE
	SYNTAX     INTEGER {
		always (0),
		ifVerificationNok (1)
	}
	MAX-ACCESS read-write
	STATUS     current
	DESCRIPTION
		"Mode"
	::= { r1p1AutoVDaily 3 }

r1p1AutoVDailyWindow  OBJECT-TYPE
	SYNTAX     Unsigned32 (1..99)
	UNITS 	"days"
	MAX-ACCESS read-write
	STATUS     current
	DESCRIPTION
		"Window (days)"
	::= { r1p1AutoVDaily 4 }

-- Redundancy 1+1: automatic verification alarm

r1p1AutoVAlarmEnable  OBJECT-TYPE
	SYNTAX     DisabledEnabled
	MAX-ACCESS read-write
	STATUS     current
	DESCRIPTION
		"enable/disable"
	::= { r1p1AutoVAlarm 3 }

-- Automatic inversion priority

r1p1PriorityInversionEnable  OBJECT-TYPE
	SYNTAX     DisabledEnabled
	MAX-ACCESS read-write
	STATUS     current
	DESCRIPTION
		"enable/disable"
	::= { r1p1AutoPriorityInversion 1 }

r1p1PriorityInversionPeriod  OBJECT-TYPE
	SYNTAX     Unsigned32 (1..99)
	MAX-ACCESS read-write
	STATUS     current
	DESCRIPTION
		"Period (days)"
	::= { r1p1AutoPriorityInversion 2 }

r1p1PriorityInversionTime  OBJECT-TYPE
	SYNTAX     OCTET STRING (SIZE(5))
	MAX-ACCESS read-write
	STATUS     current
	DESCRIPTION
		"Time HH:MM"
	::= { r1p1AutoPriorityInversion 3 }

r1p1Reset  OBJECT-TYPE
	SYNTAX     NullApply
	MAX-ACCESS read-write
	STATUS     current
	DESCRIPTION
		"To perform a reinitialization of redundancy management"
	::= { redundancy1p1 60 }

-- Sync 

r1p1SyncWeb  OBJECT-TYPE
	SYNTAX     SyncNotSync
	MAX-ACCESS read-write
	STATUS     current
	DESCRIPTION
		"Synchronize (send) the current Web configuration to the redundancy system"
	::= { r1p1Synchronization 5 }

r1p1SyncDate  OBJECT-TYPE
	SYNTAX     SyncNotSync
	MAX-ACCESS read-write
	STATUS     current
	DESCRIPTION
		"Synchronize (send) the current date configuration to the redundancy system"
	::= { r1p1Synchronization 10 }

r1p1SyncSnmp  OBJECT-TYPE
	SYNTAX     SyncNotSync
	MAX-ACCESS read-write
	STATUS     current
	DESCRIPTION
		"Synchronize (send) the current SNMP configuration to the redundancy system"
	::= { r1p1Synchronization 15 }

r1p1SyncIO  OBJECT-TYPE
	SYNTAX     SyncNotSync
	MAX-ACCESS read-write
	STATUS     current
	DESCRIPTION
		"Synchronize (send) the current I/O interface configuration to the redundancy system"
	::= { r1p1Synchronization 18 }

r1p1SyncEvents  OBJECT-TYPE
	SYNTAX     SyncNotSync
	MAX-ACCESS read-write
	STATUS     current
	DESCRIPTION
		"Synchronize (send) the current Events configuration to the redundancy system"
	::= { r1p1Synchronization 20 }

r1p1SyncInput  OBJECT-TYPE
	SYNTAX     SyncNotSync
	MAX-ACCESS read-write
	STATUS     current
	DESCRIPTION
		"Synchronize (send) the current Input configuration [IP, ASI, Switchding] to the redundancy system"
	::= { r1p1Synchronization 25 }

r1p1SyncRfInput  OBJECT-TYPE
	SYNTAX     SyncNotSync
	MAX-ACCESS read-write
	STATUS     current
	DESCRIPTION
		"Synchronize (send) the current RF Input configuration to the redundancy system"
	::= { r1p1Synchronization 30 }

r1p1SyncCanceller  OBJECT-TYPE
	SYNTAX     SyncNotSync
	MAX-ACCESS read-write
	STATUS     current
	DESCRIPTION
		"Synchronize (send) the current canceller configuration to the redundancy system"
	::= { r1p1Synchronization 35 }

r1p1SyncModulator  OBJECT-TYPE
	SYNTAX     SyncNotSync
	MAX-ACCESS read-write
	STATUS     current
	DESCRIPTION
		"Synchronize (send) the current modulator configuration to the redundancy system"
	::= { r1p1Synchronization 40 }

r1p1SyncRfConfiguration  OBJECT-TYPE
	SYNTAX     SyncNotSync
	MAX-ACCESS read-write
	STATUS     current
	DESCRIPTION
		"Synchronize (send) the current RF Configuration configuration to the redundancy system"
	::= { r1p1Synchronization 45 }

r1p1SyncMutes  OBJECT-TYPE
	SYNTAX     SyncNotSync
	MAX-ACCESS read-write
	STATUS     current
	DESCRIPTION
		"Synchronize (send) the current Mutes configuration configuration to the redundancy system"
	::= { r1p1Synchronization 47 }

r1p1SyncAmplifier  OBJECT-TYPE
	SYNTAX     SyncNotSync
	MAX-ACCESS read-write
	STATUS     current
	DESCRIPTION
		"Synchronize (send) the current amplifier configuration to the redundancy system"
	::= { r1p1Synchronization 50 }

r1p1SyncExternalAmplifier  OBJECT-TYPE
	SYNTAX     SyncNotSync
	MAX-ACCESS read-write
	STATUS     current
	DESCRIPTION
		"Synchronize (send) the current external amplifier configuration to the redundancy system"
	::= { r1p1Synchronization 55 }

r1p1SyncReference  OBJECT-TYPE
	SYNTAX     SyncNotSync
	MAX-ACCESS read-write
	STATUS     current
	DESCRIPTION
		"Synchronize (send) the current reference configuration to the redundancy system"
	::= { r1p1Synchronization 60 }

-- Redundancy N+1

rNp1DeviceIdentifier  OBJECT-TYPE
	SYNTAX     INTEGER {
		undefined (0),
		deviceB (1),
		deviceA1 (2),
		deviceA2 (3),
		deviceA3 (4),
		deviceA4 (5),
		deviceA5 (6),
		deviceA6 (7),
		deviceA7 (8),
		deviceA8 (9),
		deviceA9 (10),
		deviceA10 (11),
		deviceA11 (12)
	}
	MAX-ACCESS read-only
	STATUS     current
	DESCRIPTION
		"Device identifier"
	::= { redundancyNp1BConfiguration 5 }

rNp1ControlBusStatus  OBJECT-TYPE
	SYNTAX     INTEGER {
		error (0),
		ok (1),
		versionError (2),
		redundancyTypeError (3),
		collisionError (4)
	}
	MAX-ACCESS read-only
	STATUS     current
	DESCRIPTION
		"Control status"
	::= { redundancyNp1BConfiguration 10 }

rNp1SystemIp  OBJECT-TYPE
	SYNTAX     IpAddress
	MAX-ACCESS read-write
	STATUS     current
	DESCRIPTION
		"Redundant system IP address"
	::= { redundancyNp1BConfiguration 15 }

rNp1NValue  OBJECT-TYPE
	SYNTAX     Unsigned32 (1..11)
	MAX-ACCESS read-write
	STATUS     current
	DESCRIPTION
		"N value"
	::= { redundancyNp1BConfiguration 20 }

rNp1ManualSwitching  OBJECT-TYPE
	SYNTAX     INTEGER {
		null (0),
		deviceBtoLoad (1),
		deviceBtoAntenna1 (2),
		deviceBtoAntenna2 (3),
		deviceBtoAntenna3 (4),
		deviceBtoAntenna4 (5),
		deviceBtoAntenna5 (6),
		deviceBtoAntenna6 (7),
		deviceBtoAntenna7 (8),
		deviceBtoAntenna8 (9),
		deviceBtoAntenna9 (10),
		deviceBtoAntenna10 (11),
		deviceBtoAntenna11 (12)
	}
	MAX-ACCESS read-write
	STATUS     current
	DESCRIPTION
		"Manual switching"
	::= { redundancyNp1BConfiguration 25 }

rNp1Mode  OBJECT-TYPE
	SYNTAX     INTEGER {
		manual (0),
		automatic (1),
		maintenance (2)
	}
	MAX-ACCESS read-write
	STATUS     current
	DESCRIPTION
		"Redundancy mode"
	::= { redundancyNp1BConfiguration 30 }

rNp1AutoReturn OBJECT-TYPE
 SYNTAX					DisabledEnabled
	MAX-ACCESS read-write
	STATUS     current
	DESCRIPTION
		"Auto-return"
	::= { redundancyNp1BConfiguration 35 }

rNp1MaximumRestorations  OBJECT-TYPE
	SYNTAX     Unsigned32 (1..99)
	MAX-ACCESS read-write
	STATUS     current
	DESCRIPTION
		"Maximum restorations / window"
	::= { redundancyNp1BConfiguration 40 }

rNp1Window  OBJECT-TYPE
	SYNTAX     Unsigned32 (1..99)
	MAX-ACCESS read-write
	STATUS     current
	DESCRIPTION
		"Window (days)"
	::= { redundancyNp1BConfiguration 45 }

rNp1InputErrorTest  OBJECT-TYPE
	SYNTAX     Unsigned32 (0..99)
	UNITS	"seconds"
	MAX-ACCESS read-write
	STATUS     current
	DESCRIPTION
		"Input error test"
	::= { redundancyNp1BConfiguration 50 }

rNp1SwitchingHysteresis  OBJECT-TYPE
	SYNTAX     Unsigned32 (0..99)
	UNITS 	"seconds"
	MAX-ACCESS read-write
	STATUS     current
	DESCRIPTION
		"Switching hysteresis"
	::= { redundancyNp1BConfiguration 55 }


-- RF status control 

-- Device B RF Status and priority

rNp1RfAControlTable  OBJECT-TYPE
	SYNTAX SEQUENCE OF DeviceAConfigurationEntry
	MAX-ACCESS not-accessible
	STATUS     current
	DESCRIPTION
		"Table for RF and priorities table"
	::= { rNp1RfControl 5 }

rNp1RfAControlEntry  OBJECT-TYPE
	SYNTAX 	DeviceAConfigurationEntry
	MAX-ACCESS not-accessible
	STATUS     current
	DESCRIPTION
		"Entry for a device A configuration"
	INDEX { deviceRfAControlIndex }
	::= { rNp1RfAControlTable 1 }

DeviceAConfigurationEntry ::= SEQUENCE {
	deviceRfAControlIndex
		Unsigned32,
	deviceARf
		INTEGER
}

deviceRfAControlIndex  OBJECT-TYPE
	SYNTAX     Unsigned32 (1..11)
	MAX-ACCESS not-accessible
	STATUS     current
	DESCRIPTION
		"Device A configuration index"
	::= { rNp1RfAControlEntry 1 }

deviceARf OBJECT-TYPE
	SYNTAX     INTEGER {
		rfOff (0),
		rfOn (1)
	}
	MAX-ACCESS read-write
	STATUS     current
	DESCRIPTION
		"RF status"
	::= { rNp1RfAControlEntry 2 }

-- Priority

rNp1DeviceAPriorityTable  OBJECT-TYPE
	SYNTAX SEQUENCE OF DeviceAPriorityEntry
	MAX-ACCESS not-accessible
	STATUS     current
	DESCRIPTION
		"Table for RF and priorities table"
	::= { rNp1DeviceAPriorites 5 }

rNp1DeviceAPriorityEntry  OBJECT-TYPE
	SYNTAX 	DeviceAPriorityEntry
	MAX-ACCESS not-accessible
	STATUS     current
	DESCRIPTION
		"Entry for a device A configuration"
	INDEX { deviceAPriorityIndex }
	::= { rNp1DeviceAPriorityTable 1 }

DeviceAPriorityEntry ::= SEQUENCE {
	deviceAPriorityIndex
		Unsigned32,
	deviceAPriority
		INTEGER
}

deviceAPriorityIndex  OBJECT-TYPE
	SYNTAX     Unsigned32 (1..11)
	MAX-ACCESS not-accessible
	STATUS     current
	DESCRIPTION
		"Device A configuration index"
	::= { rNp1DeviceAPriorityEntry 1 }

deviceAPriority  OBJECT-TYPE
	SYNTAX     INTEGER {
		disabled (0),
		highest1 (1),
		priority2 (2),
		priority3 (3),
		priority4 (4),
		priority5 (5),
		priority6 (6),
		priority8 (7),
		priority9 (8),
		priority10 (9),
		priority11 (11),
		dummyAntenna (12)
	}
	MAX-ACCESS read-write
	STATUS     current
	DESCRIPTION
		"Priority"
	::= { rNp1DeviceAPriorityEntry 2 }

-- Device B RF Status and priority

rNp1DeviceToLoad  OBJECT-TYPE
    SYNTAX     INTEGER {
        rfOff (0),
        rfOn (1)
    }
    MAX-ACCESS read-write
    STATUS     current
    DESCRIPTION
        "Device to load"
    ::= { rNp1DeviceBConfiguration 5 }

rNp1PriorityManagement  OBJECT-TYPE
    SYNTAX      DisabledEnabled
    MAX-ACCESS read-write
    STATUS     current
    DESCRIPTION
        "Priotiry management"
    ::= { rNp1DeviceBConfiguration 10 }
 

-- Device B

rNp1ConfigurationDeviceB  OBJECT-TYPE
	SYNTAX     INTEGER {
		undefined (0),
		deviceA1 (1),
		deviceA2 (2),
		deviceA3 (3),
		deviceA4 (4),
		deviceA5 (5),
		deviceA6 (6),
		deviceA7 (7),
		deviceA8 (8),
		deviceA9 (9),
		deviceA10 (10),
		deviceA11 (11)
	}
	MAX-ACCESS read-write
	STATUS     current
	DESCRIPTION
		"Applied configuration"
	::= { rNp1DeviceBStatus 5 }

rNp1DeviceBStatusValue  OBJECT-TYPE
	SYNTAX     RedundancyDeviceStatus
	MAX-ACCESS read-only
	STATUS     current
	DESCRIPTION
		"Status"
	::= { rNp1DeviceBStatus 10 }

rNp1SwitchingCauses OBJECT-TYPE
	SYNTAX     OCTET STRING (SIZE(256))
	MAX-ACCESS read-only
	STATUS     current
	DESCRIPTION
		"Switching causes"
	::= { rNp1DeviceBStatus 15 }

-- Ax devices table

rNp1DeviceAStatusTable  OBJECT-TYPE
	SYNTAX SEQUENCE OF DeviceAStatusEntry
	MAX-ACCESS not-accessible
	STATUS     current
	DESCRIPTION
		"Table for Devices A"
	::= { redundancyNp1BConfiguration 65 }

rNp1DeviceAStatusEntry  OBJECT-TYPE
	SYNTAX 	DeviceAStatusEntry
	MAX-ACCESS not-accessible
	STATUS     current
	DESCRIPTION
		"Entry for a Device A"
	INDEX { deviceAStatusIndex }
	::= { rNp1DeviceAStatusTable 1 }

DeviceAStatusEntry ::= SEQUENCE {
	deviceAStatusIndex
		Unsigned32,
	deviceAStatusValue
		RedundancyDeviceStatus,
	deviceAStatusSwitchingCauses
		OCTET STRING,
	deviceAStatusRestorations
		Unsigned32,
	deviceARfSwitchStatus
		RedundancyRfSwitchStatus
}

deviceAStatusIndex  OBJECT-TYPE
	SYNTAX     Unsigned32 (1..11)
	MAX-ACCESS not-accessible
	STATUS     current
	DESCRIPTION
		"Device A status index"
	::= { rNp1DeviceAStatusEntry 1 }

deviceAStatusValue  OBJECT-TYPE
	SYNTAX     RedundancyDeviceStatus
	MAX-ACCESS read-only
	STATUS     current
	DESCRIPTION
		"Status"
	::= { rNp1DeviceAStatusEntry 2 }

deviceAStatusSwitchingCauses OBJECT-TYPE
	SYNTAX     OCTET STRING (SIZE(256))
	MAX-ACCESS read-only
	STATUS     current
	DESCRIPTION
		"Switching causes"
	::= { rNp1DeviceAStatusEntry 3 }

deviceAStatusRestorations OBJECT-TYPE
	SYNTAX     Unsigned32 (0..255)
	MAX-ACCESS read-only
	STATUS     current
	DESCRIPTION
		"Perfored restorations (window)"
	::= { rNp1DeviceAStatusEntry 4 }

deviceARfSwitchStatus OBJECT-TYPE
	SYNTAX     RedundancyRfSwitchStatus
	MAX-ACCESS read-only
	STATUS     current
	DESCRIPTION
		"RF Switch Status"
	::= { rNp1DeviceAStatusEntry 5 }

-- Automatic verifications

rNp1AutoVerificationsStatus  OBJECT-TYPE
	SYNTAX     DisabledEnabled
	MAX-ACCESS read-write
	STATUS     current
	DESCRIPTION
		"Automatic verifications"
	::= { rNp1AutoVerifications 5 }


rNp1AutoVDuration  OBJECT-TYPE
	SYNTAX     Unsigned32 (0..9999)
	UNITS 	"min"
	MAX-ACCESS read-write
	STATUS     current
	DESCRIPTION
		"Duration"
	::= { rNp1AutoVerifications 10 }

rNp1AutoVPerformedVerifications  OBJECT-TYPE
	SYNTAX     Unsigned32
	MAX-ACCESS read-only
	STATUS     current
	DESCRIPTION
		"Performed verifications"
	::= { rNp1AutoVerifications 15 }

rNp1AutoVMaxVerifications  OBJECT-TYPE
	SYNTAX     Unsigned32 (0..99)
	MAX-ACCESS read-write
	STATUS     current
	DESCRIPTION
		"Maximum verification"
	::= { rNp1AutoVerifications 20 }

rNp1AutoVNexVerification  OBJECT-TYPE
	SYNTAX     DisplayString
	MAX-ACCESS read-only
	STATUS     current
	DESCRIPTION
		"Next verification in"
	::= { rNp1AutoVerifications 25 }

-- Automatic verif.: Reiterated with cadende

rNp1AutoVReiteratedEnable  OBJECT-TYPE
	SYNTAX     DisabledEnabled
	MAX-ACCESS read-write
	STATUS     current
	DESCRIPTION
		"enable/disable"
	::= { rNp1AutoVReiterated 5 }

rNp1AutoVReiteratedPeriod  OBJECT-TYPE
	SYNTAX     Unsigned32 (1..99)
	UNITS 	"min"
	MAX-ACCESS read-write
	STATUS     current
	DESCRIPTION
		"Period"
	::= { rNp1AutoVReiterated 10 }

rNp1AutoVReiteratedCadence  OBJECT-TYPE
	SYNTAX     INTEGER {
		simple (0),
		double (1),
		triple (2)
	}
	MAX-ACCESS read-write
	STATUS     current
	DESCRIPTION
		"Cadence"
	::= { rNp1AutoVReiterated 15 }

-- Automatic verifications: Daily

rNp1AutoVDailyEnable  OBJECT-TYPE
	SYNTAX     DisabledEnabled
	MAX-ACCESS read-write
	STATUS     current
	DESCRIPTION
		"enable/disable"
	::= { rNp1AutoVDaily 5 }

rNp1AutoVDailyWindow  OBJECT-TYPE
	SYNTAX     Unsigned32 (1..99)
	UNITS 	"days"
	MAX-ACCESS read-write
	STATUS     current
	DESCRIPTION
		"Window"
	::= { rNp1AutoVDaily 6 }

rNp1AutoVDailyMode  OBJECT-TYPE
	SYNTAX     INTEGER {
		always (0),
		ifVerificationNok (1)
	}
	MAX-ACCESS read-write
	STATUS     current
	DESCRIPTION
		"Mode"
	::= { rNp1AutoVDaily 7 }

rNp1AutoVDailyTime  OBJECT-TYPE
	SYNTAX     OCTET STRING (SIZE(5))
	MAX-ACCESS read-write
	STATUS     current
	DESCRIPTION
		"Time HH:MM"
	::= { rNp1AutoVDaily 10 }

-- Automatic Verification Alarm

rNp1VerificationAlarm  OBJECT-TYPE
	SYNTAX     DisabledEnabled
	MAX-ACCESS read-write
	STATUS     current
	DESCRIPTION
		"Time HH:MM"
	::= { rNp1AutomaticVerificationAlarm 5 }

-- Reset n+1

rNp1Reset  OBJECT-TYPE
	SYNTAX     NullApply
	MAX-ACCESS read-write
	STATUS     current
	DESCRIPTION
		"To perform a reinitialization of redundancy counters"
	::= { redundancyNp1BConfiguration 100 }

-- Devices B Synchronization

rNp1SyncAllConfigurations  OBJECT-TYPE
	SYNTAX     NullApply
	MAX-ACCESS read-write
	STATUS     current
	DESCRIPTION
		"To synchronize all the configurations"
	::= { redundancyNp1BSynchronization 3 }

rNp1DeviceBSynchronizationTable  OBJECT-TYPE
	SYNTAX SEQUENCE OF DeviceBSynchronizationEntry
	MAX-ACCESS not-accessible
	STATUS     current
	DESCRIPTION
		"Table for synchronizations"
	::= { redundancyNp1BSynchronization 5 }

rNp1DeviceBSynchronizationEntry  OBJECT-TYPE
	SYNTAX 	DeviceBSynchronizationEntry
	MAX-ACCESS not-accessible
	STATUS     current
	DESCRIPTION
		"Entry for A synchronization"
	INDEX { deviceBSynchronizationAIndex }
	::= { rNp1DeviceBSynchronizationTable 1 }

DeviceBSynchronizationEntry ::= SEQUENCE {
	deviceBSynchronizationAIndex
		Unsigned32,
	deviceBConfigurationA
		INTEGER,
	deviceBSynchronizeA
		INTEGER
}

deviceBSynchronizationAIndex  OBJECT-TYPE
	SYNTAX     Unsigned32 (1..11)
	MAX-ACCESS not-accessible
	STATUS     current
	DESCRIPTION
		"Device A synchronization index"
	::= { rNp1DeviceBSynchronizationEntry 1 }

deviceBConfigurationA  OBJECT-TYPE
	SYNTAX     INTEGER {
		notAvailable (0),
		notSynchronized (1),
		synchronized (2),
		synchronizedModified (3)
	}
	MAX-ACCESS read-only
	STATUS     current
	DESCRIPTION
		"Configuration"
	::= { rNp1DeviceBSynchronizationEntry 2 }

deviceBSynchronizeA OBJECT-TYPE
	SYNTAX     NullApply 
	MAX-ACCESS read-write
	STATUS     current
	DESCRIPTION
		"Synchronize"
	::= { rNp1DeviceBSynchronizationEntry 3 }

-- ASI Matrix

asiMatrixControlStatus  OBJECT-TYPE
	SYNTAX     DisplayString
	MAX-ACCESS read-only
	STATUS     current
	DESCRIPTION
		"ASI Matrix control status"
	::= { redundancyAsi 3 }

asiMatrixHwStatus  OBJECT-TYPE
	SYNTAX     DisplayString
	MAX-ACCESS read-only
	STATUS     current
	DESCRIPTION
		"ASI Matrix hardware status"
	::= { redundancyAsi 6 }

asiMatrixSelected  OBJECT-TYPE
	SYNTAX     INTEGER {
		none (0),
		input1 (1),
		input2 (2),
		input3 (3),
		input4 (4),
		input5 (5),
		input6 (6),
		input7 (7),
		input8 (8),
		input9 (9),
		input10 (10),
		input11 (11)
	}
	MAX-ACCESS read-only
	STATUS     current
	DESCRIPTION
		"ASI Matrix input selected"
	::= { redundancyAsi 10 }

asi1InputLoopStatus  OBJECT-TYPE
	SYNTAX     INTEGER {
		none (0),
		ok (1),
		nok (2)
	}
	MAX-ACCESS read-only
	STATUS     current
	DESCRIPTION
		"ASI 1 input loop status"
	::= { redundancyAsi 15 }

asi2InputLoopStatus  OBJECT-TYPE
	SYNTAX     INTEGER {
		none (0),
		ok (1),
		nok (2)
	}
	MAX-ACCESS read-only
	STATUS     current
	DESCRIPTION
		"ASI 1 input loop status"
	::= { redundancyAsi 20 }

asiMatrixInputStatusTable  OBJECT-TYPE
	SYNTAX SEQUENCE OF AsiMatrixInputStatusEntry
	MAX-ACCESS not-accessible
	STATUS     current
	DESCRIPTION
		"Table for ASI Matrix Input status information"
	::= { redundancyAsi 25 }

asiMatrixInputStatusEntry  OBJECT-TYPE
	SYNTAX 	AsiMatrixInputStatusEntry
	MAX-ACCESS not-accessible
	STATUS     current
	DESCRIPTION
		"Entry for ASI Matrix Input status information"
	INDEX { asiMatrixInputStatusIndex }
	::= { asiMatrixInputStatusTable 1 }

AsiMatrixInputStatusEntry ::= SEQUENCE {
	asiMatrixInputStatusIndex 
		Unsigned32,
	asi1InputStatus
		INTEGER,
	asi2InputStatus
		INTEGER
}

asiMatrixInputStatusIndex   OBJECT-TYPE
	SYNTAX     Unsigned32 (1..11)
	MAX-ACCESS not-accessible
	STATUS     current
	DESCRIPTION
		"Index ASI Matrix input index"
	::= { asiMatrixInputStatusEntry  1 }

asi1InputStatus  OBJECT-TYPE
	SYNTAX     INTEGER {
		null (0),
		ok (1),
		nok (2)
	}
	MAX-ACCESS read-only
	STATUS     current
	DESCRIPTION
		"ASI 1 Matrix input status"
	::= { asiMatrixInputStatusEntry 2 }

asi2InputStatus  OBJECT-TYPE
	SYNTAX     INTEGER {
		null (0),
		ok (1),
		nok (2)
	}
	MAX-ACCESS read-only
	STATUS     current
	DESCRIPTION
		"ASI 2 input status"
	::= { asiMatrixInputStatusEntry 3 }

-- ETI Matrix

etiMatrixControlStatus  OBJECT-TYPE
	SYNTAX     DisplayString
	MAX-ACCESS read-only
	STATUS     current
	DESCRIPTION
		"ETI Matrix control status"
	::= { redundancyEti 3 }

etiMatrixHwStatus  OBJECT-TYPE
	SYNTAX     DisplayString
	MAX-ACCESS read-only
	STATUS     current
	DESCRIPTION
		"ETI Matrix hardware status"
	::= { redundancyEti 6 }

etiMatrixSelected  OBJECT-TYPE
	SYNTAX     INTEGER {
		none (0),
		input1 (1),
		input2 (2),
		input3 (3),
		input4 (4),
		input5 (5),
		input6 (6),
		input7 (7),
		input8 (8),
		input9 (9),
		input10 (10),
		input11 (11)
	}
	MAX-ACCESS read-only
	STATUS     current
	DESCRIPTION
		"ETI Matrix input selected"
	::= { redundancyEti 10 }

eti1InputLoopStatus  OBJECT-TYPE
	SYNTAX     INTEGER {
		none (0),
		ok (1),
		nok (2)
	}
	MAX-ACCESS read-only
	STATUS     current
	DESCRIPTION
		"ETI 1 input loop status"
	::= { redundancyEti 15 }

eti2InputLoopStatus  OBJECT-TYPE
	SYNTAX     INTEGER {
		none (0),
		ok (1),
		nok (2)
	}
	MAX-ACCESS read-only
	STATUS     current
	DESCRIPTION
		"ETI 1 input loop status"
	::= { redundancyEti 20 }

etiMatrixInputStatusTable  OBJECT-TYPE
	SYNTAX SEQUENCE OF EtiMatrixInputStatusEntry
	MAX-ACCESS not-accessible
	STATUS     current
	DESCRIPTION
		"Table for ETI Matrix Input status information"
	::= { redundancyEti 25 }

etiMatrixInputStatusEntry  OBJECT-TYPE
	SYNTAX 	EtiMatrixInputStatusEntry
	MAX-ACCESS not-accessible
	STATUS     current
	DESCRIPTION
		"Entry for ETI Matrix Input status information"
	INDEX { etiMatrixInputStatusIndex }
	::= { etiMatrixInputStatusTable 1 }

EtiMatrixInputStatusEntry ::= SEQUENCE {
	etiMatrixInputStatusIndex 
		Unsigned32,
	eti1InputStatus
		INTEGER,
	eti2InputStatus
		INTEGER
}

etiMatrixInputStatusIndex   OBJECT-TYPE
	SYNTAX     Unsigned32 (1..11)
	MAX-ACCESS not-accessible
	STATUS     current
	DESCRIPTION
		"Index ETI Matrix input index"
	::= { etiMatrixInputStatusEntry  1 }

eti1InputStatus  OBJECT-TYPE
	SYNTAX     INTEGER {
		null (0),
		ok (1),
		nok (2)
	}
	MAX-ACCESS read-only
	STATUS     current
	DESCRIPTION
		"ETI 1 Matrix input status"
	::= { etiMatrixInputStatusEntry 2 }

eti2InputStatus  OBJECT-TYPE
	SYNTAX     INTEGER {
		null (0),
		ok (1),
		nok (2)
	}
	MAX-ACCESS read-only
	STATUS     current
	DESCRIPTION
		"ETI 2 input status"
	::= { etiMatrixInputStatusEntry 3 }

-- alarmas.xml

faultSummationStatus  OBJECT-TYPE
	SYNTAX     AlarmStatus
	MAX-ACCESS read-only
	STATUS     current
	DESCRIPTION
		"Fault Summation"
	::= { status 1 }

warningSummationStatus  OBJECT-TYPE
	SYNTAX     AlarmStatus
	MAX-ACCESS read-only
	STATUS     current
	DESCRIPTION
		"Warning Summation"
	::= { status 2 }

amplifierStatus  OBJECT-TYPE
	SYNTAX     AlarmStatus
	MAX-ACCESS read-only
	STATUS     current
	DESCRIPTION
		"Amplifier"
	::= { statusAmplifier 1 }

exceededOutputPower  OBJECT-TYPE
	SYNTAX     AlarmStatus
	MAX-ACCESS read-only
	STATUS     current
	DESCRIPTION
		"Exceeded power"
	::= { statusAmplifier 2 }

decreasedOutputPower  OBJECT-TYPE
	SYNTAX     AlarmStatus
	MAX-ACCESS read-only
	STATUS     current
	DESCRIPTION
		"Decreased Power"
	::= { statusAmplifier 3 }

reflectPowerStatus  OBJECT-TYPE
	SYNTAX     AlarmStatus
	MAX-ACCESS read-only
	STATUS     current
	DESCRIPTION
		"Reflected Power"
	::= { statusAmplifier 4 }

temperatureAmplifierStatus  OBJECT-TYPE
	SYNTAX     AlarmStatus
	MAX-ACCESS read-only
	STATUS     current
	DESCRIPTION
		"Temperature [Amplifier]"
	::= { statusAmplifier 5 }

decreasedOutputPowerNonCritical  OBJECT-TYPE
	SYNTAX     AlarmStatus
	MAX-ACCESS read-only
	STATUS     current
	DESCRIPTION
		"Decreased Power Non-critical [Amplifier]"
	::= { statusAmplifier 6 }

asiInputStatus  OBJECT-TYPE
	SYNTAX     AlarmStatus
	MAX-ACCESS read-only
	STATUS     current
	DESCRIPTION
		"ASI input"
	::= { statusAsiInput 1 }

asi1ErrorStatus  OBJECT-TYPE
	SYNTAX     AlarmStatus
	MAX-ACCESS read-only
	STATUS     current
	DESCRIPTION
		"ASI 1 error"
	::= { statusAsiInput 2 }

asi2ErrorStatus  OBJECT-TYPE
	SYNTAX     AlarmStatus
	MAX-ACCESS read-only
	STATUS     current
	DESCRIPTION
		"ASI 2 error"
	::= { statusAsiInput 3 }

ipInputStatus  OBJECT-TYPE
	SYNTAX     AlarmStatus
	MAX-ACCESS read-only
	STATUS     current
	DESCRIPTION
		"Input IP"
	::= { statusIpInput 1 }

ipSocket1ErrorStatus  OBJECT-TYPE
	SYNTAX     AlarmStatus
	MAX-ACCESS read-only
	STATUS     current
	DESCRIPTION
		"IP Socket 1 Error"
	::= { statusIpInput 2 }

ipSocket2ErrorStatus  OBJECT-TYPE
	SYNTAX     AlarmStatus
	MAX-ACCESS read-only
	STATUS     current
	DESCRIPTION
		"IP Socket 2 Error"
	::= { statusIpInput 3 }

satReceiver1Status  OBJECT-TYPE
	SYNTAX     AlarmStatus
	MAX-ACCESS read-only
	STATUS     current
	DESCRIPTION
		"Satellite Receiver 1"
	::= { statusSatelliteReceiver1 1 }

unlockSatReceiver1Status  OBJECT-TYPE
	SYNTAX     AlarmStatus
	MAX-ACCESS read-only
	STATUS     current
	DESCRIPTION
		"Unlock Satellite Receiver 1"
	::= { statusSatelliteReceiver1 2 }

rfSignalSatReceiver1Status  OBJECT-TYPE
	SYNTAX     AlarmStatus
	MAX-ACCESS read-only
	STATUS     current
	DESCRIPTION
		"RF signal Satellite Receiver 1"
	::= { statusSatelliteReceiver1 3 }

lnbOverloadSatReceiver1Status  OBJECT-TYPE
	SYNTAX     AlarmStatus
	MAX-ACCESS read-only
	STATUS     current
	DESCRIPTION
		"LNB overload Satellite Receiver 1"
	::= { statusSatelliteReceiver1 4 }

temperatureSatReceiver1Status  OBJECT-TYPE
	SYNTAX     AlarmStatus
	MAX-ACCESS read-only
	STATUS     current
	DESCRIPTION
		"Temperature Satellite Receiver 1"
	::= { statusSatelliteReceiver1 5 }

camSatReceiver1Status  OBJECT-TYPE
	SYNTAX     AlarmStatus
	MAX-ACCESS read-only
	STATUS     current
	DESCRIPTION
		"CAM Satellite Receiver 1"
	::= { statusSatelliteReceiver1 6 }

smartCardSatReceiver1Status  OBJECT-TYPE
	SYNTAX     AlarmStatus
	MAX-ACCESS read-only
	STATUS     current
	DESCRIPTION
		"Smart Card Satellite Receiver 1"
	::= { statusSatelliteReceiver1 7 }

smartCardRightsSatReceiver1Stat  OBJECT-TYPE
	SYNTAX     AlarmStatus
	MAX-ACCESS read-only
	STATUS     current
	DESCRIPTION
		"Smart card rights Satellite Receiver 1"
	::= { statusSatelliteReceiver1 8 }

asiOutputSatReceiver1Status  OBJECT-TYPE
	SYNTAX     AlarmStatus
	MAX-ACCESS read-only
	STATUS     current
	DESCRIPTION
		"ASI output Satellite Receiver 1"
	::= { statusSatelliteReceiver1 9 }

satReceiver2Status  OBJECT-TYPE
	SYNTAX     AlarmStatus
	MAX-ACCESS read-only
	STATUS     current
	DESCRIPTION
		"Satellite Receiver 2"
	::= { statusSatelliteReceiver2 1 }

unlockSatReceiver2Status  OBJECT-TYPE
	SYNTAX     AlarmStatus
	MAX-ACCESS read-only
	STATUS     current
	DESCRIPTION
		"Unlock Satellite Receiver 2"
	::= { statusSatelliteReceiver2 2 }

rfSignalSatReceiver2Status  OBJECT-TYPE
	SYNTAX     AlarmStatus
	MAX-ACCESS read-only
	STATUS     current
	DESCRIPTION
		"RF signal Satellite Receiver 2"
	::= { statusSatelliteReceiver2 3 }

lnbOverloadSatReceiver2Status  OBJECT-TYPE
	SYNTAX     AlarmStatus
	MAX-ACCESS read-only
	STATUS     current
	DESCRIPTION
		"LNB overload Satellite Receiver 2"
	::= { statusSatelliteReceiver2 4 }

temperatureSatReceiver2Status  OBJECT-TYPE
	SYNTAX     AlarmStatus
	MAX-ACCESS read-only
	STATUS     current
	DESCRIPTION
		"Temperature Satellite Receiver 1"
	::= { statusSatelliteReceiver2 5 }

dttReceiver1AlarmStatus  OBJECT-TYPE
	SYNTAX     AlarmStatus
	MAX-ACCESS read-only
	STATUS     current
	DESCRIPTION
		"DTT Receiver 1"
	::= { statusTerrestialReceiver1 1 }

unlockDttReceiver1Status  OBJECT-TYPE
	SYNTAX     AlarmStatus
	MAX-ACCESS read-only
	STATUS     current
	DESCRIPTION
		"Unlock DTT Receiver 1"
	::= { statusTerrestialReceiver1 2 }

rfSignalDttReceiver1Status  OBJECT-TYPE
	SYNTAX     AlarmStatus
	MAX-ACCESS read-only
	STATUS     current
	DESCRIPTION
		"RF signal DTT Receiver 1"
	::= { statusTerrestialReceiver1 3 }

temperatureDttReceiver1Status  OBJECT-TYPE
	SYNTAX     AlarmStatus
	MAX-ACCESS read-only
	STATUS     current
	DESCRIPTION
		"Temperature DTT Receiver 1"
	::= { statusTerrestialReceiver1 4 }

dttReceiver2AlarmStatus  OBJECT-TYPE
	SYNTAX     AlarmStatus
	MAX-ACCESS read-only
	STATUS     current
	DESCRIPTION
		"DTT Receiver 2"
	::= { statusTerrestialReceiver2 1 }

unlockDttReceiver2Status  OBJECT-TYPE
	SYNTAX     AlarmStatus
	MAX-ACCESS read-only
	STATUS     current
	DESCRIPTION
		"Unlock DTT Receiver 2"
	::= { statusTerrestialReceiver2 2 }

rfSignalDttReceiver2Status  OBJECT-TYPE
	SYNTAX     AlarmStatus
	MAX-ACCESS read-only
	STATUS     current
	DESCRIPTION
		"RF signal DTT Receiver 2"
	::= { statusTerrestialReceiver2 3 }

temperatureDttReceiver2Status  OBJECT-TYPE
	SYNTAX     AlarmStatus
	MAX-ACCESS read-only
	STATUS     current
	DESCRIPTION
		"Temperature DTT Receiver 2"
	::= { statusTerrestialReceiver2 4 }

modulatorStatus  OBJECT-TYPE
	SYNTAX     AlarmStatus
	MAX-ACCESS read-only
	STATUS     current
	DESCRIPTION
		"Modulator"
	::= { statusModulator 1 }

tsErrorStatus  OBJECT-TYPE
	SYNTAX     AlarmStatus
	MAX-ACCESS read-only
	STATUS     current
	DESCRIPTION
		"TS error"
	::= { statusModulator 2 }

mipErrorStatus  OBJECT-TYPE
	SYNTAX     AlarmStatus
	MAX-ACCESS read-only
	STATUS     current
	DESCRIPTION
		"MIP error"
	::= { statusModulator 3 }

mpegOverflowStatus  OBJECT-TYPE
	SYNTAX     AlarmStatus
	MAX-ACCESS read-only
	STATUS     current
	DESCRIPTION
		"MPEG Overflow"
	::= { statusModulator 4 }

t2miErrorStatus  OBJECT-TYPE
	SYNTAX     AlarmStatus
	MAX-ACCESS read-only
	STATUS     current
	DESCRIPTION
		"T2MI error"
	::= { statusModulator 5 }

btsErrorStatus  OBJECT-TYPE
	SYNTAX     AlarmStatus
	MAX-ACCESS read-only
	STATUS     current
	DESCRIPTION
		"BTS error"
	::= { statusModulator 6 }

sfnErrorStatus  OBJECT-TYPE
	SYNTAX     AlarmStatus
	MAX-ACCESS read-only
	STATUS     current
	DESCRIPTION
		"SFN error"
	::= { statusModulator 7 }

sfnMargin  OBJECT-TYPE
	SYNTAX     AlarmStatus
	MAX-ACCESS read-only
	STATUS     current
	DESCRIPTION
		"Margin SFN"
	::= { statusModulator 8 }

temperatureModulatorStatus  OBJECT-TYPE
	SYNTAX     AlarmStatus
	MAX-ACCESS read-only
	STATUS     current
	DESCRIPTION
		"Temperature [Modulator]"
	::= { statusModulator 9 }

modulatorOutputStatus  OBJECT-TYPE
	SYNTAX     AlarmStatus
	MAX-ACCESS read-only
	STATUS     current
	DESCRIPTION
		"Modulator Output"
	::= { statusModulator 10 }

modulatorShouldersStatus  OBJECT-TYPE
	SYNTAX     AlarmStatus
	MAX-ACCESS read-only
	STATUS     current
	DESCRIPTION
		"Modulator shoulders status"
	::= { statusModulator 11 }

modulatorMerStatus  OBJECT-TYPE
	SYNTAX     AlarmStatus
	MAX-ACCESS read-only
	STATUS     current
	DESCRIPTION
		"Modulator MER status"
	::= { statusModulator 12 }

modulatorExternalFeedbackStatus  OBJECT-TYPE
	SYNTAX     AlarmStatus
	MAX-ACCESS read-only
	STATUS     current
	DESCRIPTION
		"Modulator External Feedback status"
	::= { statusModulator 13 }

modulatorBerStatus  OBJECT-TYPE
	SYNTAX     AlarmStatus
	MAX-ACCESS read-only
	STATUS     current
	DESCRIPTION
		"BER"
	::= { statusModulator 14 }

inputDabErrorStatus  OBJECT-TYPE
	SYNTAX     AlarmStatus
	MAX-ACCESS read-only
	STATUS     current
	DESCRIPTION
		"Input DAB error"
	::= { statusModulator 15 }

rfInputStatus  OBJECT-TYPE
	SYNTAX     AlarmStatus
	MAX-ACCESS read-only
	STATUS     current
	DESCRIPTION
		"RF Input"
	::= { statusRfInput 1 }

echoCancellerStatus  OBJECT-TYPE
	SYNTAX     AlarmStatus
	MAX-ACCESS read-only
	STATUS     current
	DESCRIPTION
		"Echo canceller status"
	::= { statusEchoCanceller 1 }

inputLevelStatus  OBJECT-TYPE
	SYNTAX     AlarmStatus
	MAX-ACCESS read-only
	STATUS     current
	DESCRIPTION
		"Echo canceller input level status"
	::= { statusEchoCanceller 2 }

reference10MHzStatus  OBJECT-TYPE
	SYNTAX     AlarmStatus
	MAX-ACCESS read-only
	STATUS     current
	DESCRIPTION
		"Echo canceller 10MHz reference status"
	::= { statusEchoCanceller 3 }

temperatureECStatus  OBJECT-TYPE
	SYNTAX     AlarmStatus
	MAX-ACCESS read-only
	STATUS     current
	DESCRIPTION
		"Echo canceller temperature status"
	::= { statusEchoCanceller 4 }

outputLevelStatus  OBJECT-TYPE
	SYNTAX     AlarmStatus
	MAX-ACCESS read-only
	STATUS     current
	DESCRIPTION
		"Echo canceller output level"
	::= { statusEchoCanceller 5 }

cancellerShouldersStatus  OBJECT-TYPE
	SYNTAX     AlarmStatus
	MAX-ACCESS read-only
	STATUS     current
	DESCRIPTION
		"Canceller shoulders status"
	::= { statusEchoCanceller 6 }

cancellerMerStatus  OBJECT-TYPE
	SYNTAX     AlarmStatus
	MAX-ACCESS read-only
	STATUS     current
	DESCRIPTION
		"Canceller MER"
	::= { statusEchoCanceller 7 }

gainMarginStatus  OBJECT-TYPE
	SYNTAX     AlarmStatus
	MAX-ACCESS read-only
	STATUS     current
	DESCRIPTION
		"Gain margin"
	::= { statusEchoCanceller 8 }

cancExternalFeedbackStatus  OBJECT-TYPE
	SYNTAX     AlarmStatus
	MAX-ACCESS read-only
	STATUS     current
	DESCRIPTION
		"External feedback"
	::= { statusEchoCanceller 9 }

etiInputStatus  OBJECT-TYPE
	SYNTAX     AlarmStatus
	MAX-ACCESS read-only
	STATUS     current
	DESCRIPTION
		"ETI input"
	::= { statusEtiInput 1 }

eti1ErrorStatus  OBJECT-TYPE
	SYNTAX     AlarmStatus
	MAX-ACCESS read-only
	STATUS     current
	DESCRIPTION
		"ETI 1 error"
	::= { statusEtiInput 2 }

eti2ErrorStatus  OBJECT-TYPE
	SYNTAX     AlarmStatus
	MAX-ACCESS read-only
	STATUS     current
	DESCRIPTION
		"ETI 2 error"
	::= { statusEtiInput 3 }

rfOutputStatus  OBJECT-TYPE
	SYNTAX     AlarmStatus
	MAX-ACCESS read-only
	STATUS     current
	DESCRIPTION
		"RF Output"
	::= { statusRfOutput 1 }

synchronizationModuleStatus  OBJECT-TYPE
	SYNTAX     AlarmStatus
	MAX-ACCESS read-only
	STATUS     current
	DESCRIPTION
		"Synchronization module"
	::= { synchronizationModule 1 }

synchronizationAntennaStatus  OBJECT-TYPE
	SYNTAX     AlarmStatus
	MAX-ACCESS read-only
	STATUS     current
	DESCRIPTION
		"Synchronization Antenna"
	::= { synchronizationModule 2 }

synchronizationUnlockStatus  OBJECT-TYPE
	SYNTAX     AlarmStatus
	MAX-ACCESS read-only
	STATUS     current
	DESCRIPTION
		"Synchronization Unlock"
	::= { synchronizationModule 3 }

synchronizationHoldoverStatus  OBJECT-TYPE
	SYNTAX     AlarmStatus
	MAX-ACCESS read-only
	STATUS     current
	DESCRIPTION
		"Synchronization Holdover"
	::= { synchronizationModule 4 }

synchronizationHwErrorStatus  OBJECT-TYPE
	SYNTAX     AlarmStatus
	MAX-ACCESS read-only
	STATUS     current
	DESCRIPTION
		"Synchronization HW error"
	::= { synchronizationModule 5 }

temperatureSynchronizationStatus  OBJECT-TYPE
	SYNTAX     AlarmStatus
	MAX-ACCESS read-only
	STATUS     current
	DESCRIPTION
		"Temperature [Synchronization]"
	::= { synchronizationModule 6 }

input10MhzStatus  OBJECT-TYPE
	SYNTAX     AlarmStatus
	MAX-ACCESS read-only
	STATUS     current
	DESCRIPTION
		"10MHz input [Synchronization]"
	::= { synchronizationModule 7 }

input1ppsStatus  OBJECT-TYPE
	SYNTAX     AlarmStatus
	MAX-ACCESS read-only
	STATUS     current
	DESCRIPTION
		"1pps input [Synchronization]"
	::= { synchronizationModule 8 }

rackCoolingStatus  OBJECT-TYPE
	SYNTAX     AlarmStatus
	MAX-ACCESS read-only
	STATUS     current
	DESCRIPTION
		"Rack Cooling"
	::= { rackCoolingBoards 1 }

rackCoolingTemperatureStatus  OBJECT-TYPE
	SYNTAX     AlarmStatus
	MAX-ACCESS read-only
	STATUS     current
	DESCRIPTION
		"Temperature [Rack Cooling]"
	::= { rackCoolingBoards 2 }

pressureDifferenceStatus  OBJECT-TYPE
	SYNTAX     AlarmStatus
	MAX-ACCESS read-only
	STATUS     current
	DESCRIPTION
		"PressureDifference [Rack Cooling]"
	::= { rackCoolingBoards 3 }

rackCoolingHwErrorStatus  OBJECT-TYPE
	SYNTAX     AlarmStatus
	MAX-ACCESS read-only
	STATUS     current
	DESCRIPTION
		"HW error [Rack Cooling]"
	::= { rackCoolingBoards 4 }

hwErrorStatus  OBJECT-TYPE
	SYNTAX     AlarmStatus
	MAX-ACCESS read-only
	STATUS     current
	DESCRIPTION
		"HW Error"
	::= { statusHwError 1 }

ldmosTransistorsStatus  OBJECT-TYPE
	SYNTAX     AlarmStatus
	MAX-ACCESS read-only
	STATUS     current
	DESCRIPTION
		"LDMOS Transistors"
	::= { statusHwError 2 }

internalErrorStatus  OBJECT-TYPE
	SYNTAX     AlarmStatus
	MAX-ACCESS read-only
	STATUS     current
	DESCRIPTION
		"Internal Error"
	::= { statusHwError 3 }

localOscillatorStatus  OBJECT-TYPE
	SYNTAX     AlarmStatus
	MAX-ACCESS read-only
	STATUS     current
	DESCRIPTION
		"Local Oscillator"
	::= { statusHwError 4 }

internalDcSupplyVoltageStatus  OBJECT-TYPE
	SYNTAX     AlarmStatus
	MAX-ACCESS read-only
	STATUS     current
	DESCRIPTION
		"Local Oscillator"
	::= { statusHwError 5 }

nonLinearSenseFeedback  OBJECT-TYPE
	SYNTAX     AlarmStatus
	MAX-ACCESS read-only
	STATUS     current
	DESCRIPTION
		"Non-linear sense feedback"
	::= { statusHwError 6 }

amplifierOutputSample  OBJECT-TYPE
	SYNTAX     AlarmStatus
	MAX-ACCESS read-only
	STATUS     current
	DESCRIPTION
		"Amplifier output sample"
	::= { statusHwError 7 }

fanStatus  OBJECT-TYPE
	SYNTAX     AlarmStatus
	MAX-ACCESS read-only
	STATUS     current
	DESCRIPTION
		"Fan"
	::= { statusFan 1 }

fan1Status  OBJECT-TYPE
	SYNTAX     AlarmStatus
	MAX-ACCESS read-only
	STATUS     current
	DESCRIPTION
		"Fan 1"
	::= { statusFan 2 }

fan2Status  OBJECT-TYPE
	SYNTAX     AlarmStatus
	MAX-ACCESS read-only
	STATUS     current
	DESCRIPTION
		"Fan 2"
	::= { statusFan 3 }

fan3Status  OBJECT-TYPE
	SYNTAX     AlarmStatus
	MAX-ACCESS read-only
	STATUS     current
	DESCRIPTION
		"Fan 3"
	::= { statusFan 4 }

externalStatus  OBJECT-TYPE
	SYNTAX     AlarmStatus
	MAX-ACCESS read-only
	STATUS     current
	DESCRIPTION
		"External Alarm"
	::= { statusExternal 1 }

external1Status  OBJECT-TYPE
	SYNTAX     AlarmStatus
	MAX-ACCESS read-only
	STATUS     current
	DESCRIPTION
		"External Alarm 1"
	::= { statusExternal 2 }

external2Status  OBJECT-TYPE
	SYNTAX     AlarmStatus
	MAX-ACCESS read-only
	STATUS     current
	DESCRIPTION
		"External Alarm 2"
	::= { statusExternal 3 }

acPowerSupplyStatus  OBJECT-TYPE
	SYNTAX     AlarmStatus
	MAX-ACCESS read-only
	STATUS     current
	DESCRIPTION
		"AC power supply Alarm"
	::= { statusPowerSupply 1 }

acPsuAStatus  OBJECT-TYPE
	SYNTAX     AlarmStatus
	MAX-ACCESS read-only
	STATUS     current
	DESCRIPTION
		"PSU A"
	::= { statusPowerSupply 2 }

acPsuBStatus  OBJECT-TYPE
	SYNTAX     AlarmStatus
	MAX-ACCESS read-only
	STATUS     current
	DESCRIPTION
		"PSU B"
	::= { statusPowerSupply 3 }

amplifierStage1Status  OBJECT-TYPE
	SYNTAX     AlarmStatus
	MAX-ACCESS read-only
	STATUS     current
	DESCRIPTION
		"Amplifier Stage 1 status"
	::= { statusAmplifierStage1 1 }

aS1InputLevelStatus  OBJECT-TYPE
	SYNTAX     AlarmStatus
	MAX-ACCESS read-only
	STATUS     current
	DESCRIPTION
		"Amplifier Stage 1: Input level status"
	::= { statusAmplifierStage1 2 }

aS1ExceededPowerStatus  OBJECT-TYPE
	SYNTAX     AlarmStatus
	MAX-ACCESS read-only
	STATUS     current
	DESCRIPTION
		"Amplifier Stage 1: Exceeded Power status"
	::= { statusAmplifierStage1 3 }

aS1DecreasedPowerStatus  OBJECT-TYPE
	SYNTAX     AlarmStatus
	MAX-ACCESS read-only
	STATUS     current
	DESCRIPTION
		"Amplifier Stage 1: Decreased Power status"
	::= { statusAmplifierStage1 4 }

aS1ReflectedPowerStatus  OBJECT-TYPE
	SYNTAX     AlarmStatus
	MAX-ACCESS read-only
	STATUS     current
	DESCRIPTION
		"Amplifier Stage 1: Reflected Power status"
	::= { statusAmplifierStage1 5 }

aS1TemperatureStatus  OBJECT-TYPE
	SYNTAX     AlarmStatus
	MAX-ACCESS read-only
	STATUS     current
	DESCRIPTION
		"Amplifier Stage 1: Temperature status"
	::= { statusAmplifierStage1 6 }

aS1HwErrorStatus  OBJECT-TYPE
	SYNTAX     AlarmStatus
	MAX-ACCESS read-only
	STATUS     current
	DESCRIPTION
		"Amplifier Stage 1: HW error status"
	::= { statusAmplifierStage1 7 }

aS1PsusErrorStatus  OBJECT-TYPE
	SYNTAX     AlarmStatus
	MAX-ACCESS read-only
	STATUS     current
	DESCRIPTION
		"Amplifier Stage 1: Error PSUs"
	::= { statusAmplifierStage1 8 }

amplifierStage2Status  OBJECT-TYPE
	SYNTAX     AlarmStatus
	MAX-ACCESS read-only
	STATUS     current
	DESCRIPTION
		"Amplifier Stage 2 status"
	::= { statusAmplifierStage2 1 }

aS2InputLevelStatus  OBJECT-TYPE
	SYNTAX     AlarmStatus
	MAX-ACCESS read-only
	STATUS     current
	DESCRIPTION
		"Amplifier Stage 2: Input level status"
	::= { statusAmplifierStage2 2 }

aS2ExceededPowerStatus  OBJECT-TYPE
	SYNTAX     AlarmStatus
	MAX-ACCESS read-only
	STATUS     current
	DESCRIPTION
		"Amplifier Stage 2: Exceeded Power status"
	::= { statusAmplifierStage2 3 }

aS2DecreasedPowerStatus  OBJECT-TYPE
	SYNTAX     AlarmStatus
	MAX-ACCESS read-only
	STATUS     current
	DESCRIPTION
		"Amplifier Stage 2: Decreased Power status"
	::= { statusAmplifierStage2 4 }

aS2ReflectedPowerStatus  OBJECT-TYPE
	SYNTAX     AlarmStatus
	MAX-ACCESS read-only
	STATUS     current
	DESCRIPTION
		"Amplifier Stage 2: Reflected Power status"
	::= { statusAmplifierStage2 5 }

aS2TemperatureStatus  OBJECT-TYPE
	SYNTAX     AlarmStatus
	MAX-ACCESS read-only
	STATUS     current
	DESCRIPTION
		"Amplifier Stage 2: Temperature status"
	::= { statusAmplifierStage2 6 }

aS2HwErrorStatus  OBJECT-TYPE
	SYNTAX     AlarmStatus
	MAX-ACCESS read-only
	STATUS     current
	DESCRIPTION
		"Amplifier Stage 2: HW error status"
	::= { statusAmplifierStage2 7 }

aS2PsusErrorStatus  OBJECT-TYPE
	SYNTAX     AlarmStatus
	MAX-ACCESS read-only
	STATUS     current
	DESCRIPTION
		"Amplifier Stage 2: Error PSUs"
	::= { statusAmplifierStage2 8 }

amplifierStage3Status  OBJECT-TYPE
	SYNTAX     AlarmStatus
	MAX-ACCESS read-only
	STATUS     current
	DESCRIPTION
		"Amplifier Stage 3 status"
	::= { statusAmplifierStage3 1 }

aS3InputLevelStatus  OBJECT-TYPE
	SYNTAX     AlarmStatus
	MAX-ACCESS read-only
	STATUS     current
	DESCRIPTION
		"Amplifier Stage 3: Input level status"
	::= { statusAmplifierStage3 2 }

aS3ExceededPowerStatus  OBJECT-TYPE
	SYNTAX     AlarmStatus
	MAX-ACCESS read-only
	STATUS     current
	DESCRIPTION
		"Amplifier Stage 3: Exceeded Power status"
	::= { statusAmplifierStage3 3 }

aS3DecreasedPowerStatus  OBJECT-TYPE
	SYNTAX     AlarmStatus
	MAX-ACCESS read-only
	STATUS     current
	DESCRIPTION
		"Amplifier Stage 3: Decreased Power status"
	::= { statusAmplifierStage3 4 }

aS3ReflectedPowerStatus  OBJECT-TYPE
	SYNTAX     AlarmStatus
	MAX-ACCESS read-only
	STATUS     current
	DESCRIPTION
		"Amplifier Stage 3: Reflected Power status"
	::= { statusAmplifierStage3 5 }

aS3TemperatureStatus  OBJECT-TYPE
	SYNTAX     AlarmStatus
	MAX-ACCESS read-only
	STATUS     current
	DESCRIPTION
		"Amplifier Stage 3: Temperature status"
	::= { statusAmplifierStage3 6 }

aS3HwErrorStatus  OBJECT-TYPE
	SYNTAX     AlarmStatus
	MAX-ACCESS read-only
	STATUS     current
	DESCRIPTION
		"Amplifier Stage 3: HW error status"
	::= { statusAmplifierStage3 7 }

aS3PsusErrorStatus  OBJECT-TYPE
	SYNTAX     AlarmStatus
	MAX-ACCESS read-only
	STATUS     current
	DESCRIPTION
		"Amplifier Stage 3: Error PSUs"
	::= { statusAmplifierStage3 8 }

amplifierStage4Status  OBJECT-TYPE
	SYNTAX     AlarmStatus
	MAX-ACCESS read-only
	STATUS     current
	DESCRIPTION
		"Amplifier Stage 4 status"
	::= { statusAmplifierStage4 1 }

aS4InputLevelStatus  OBJECT-TYPE
	SYNTAX     AlarmStatus
	MAX-ACCESS read-only
	STATUS     current
	DESCRIPTION
		"Amplifier Stage 4: Input level status"
	::= { statusAmplifierStage4 2 }

aS4ExceededPowerStatus  OBJECT-TYPE
	SYNTAX     AlarmStatus
	MAX-ACCESS read-only
	STATUS     current
	DESCRIPTION
		"Amplifier Stage 4: Exceeded Power status"
	::= { statusAmplifierStage4 3 }

aS4DecreasedPowerStatus  OBJECT-TYPE
	SYNTAX     AlarmStatus
	MAX-ACCESS read-only
	STATUS     current
	DESCRIPTION
		"Amplifier Stage 4: Decreased Power status"
	::= { statusAmplifierStage4 4 }

aS4ReflectedPowerStatus  OBJECT-TYPE
	SYNTAX     AlarmStatus
	MAX-ACCESS read-only
	STATUS     current
	DESCRIPTION
		"Amplifier Stage 4: Reflected Power status"
	::= { statusAmplifierStage4 5 }

aS4TemperatureStatus  OBJECT-TYPE
	SYNTAX     AlarmStatus
	MAX-ACCESS read-only
	STATUS     current
	DESCRIPTION
		"Amplifier Stage 4: Temperature status"
	::= { statusAmplifierStage4 6 }

aS4HwErrorStatus  OBJECT-TYPE
	SYNTAX     AlarmStatus
	MAX-ACCESS read-only
	STATUS     current
	DESCRIPTION
		"Amplifier Stage 4: HW error status"
	::= { statusAmplifierStage4 7 }

aS4PsusErrorStatus  OBJECT-TYPE
	SYNTAX     AlarmStatus
	MAX-ACCESS read-only
	STATUS     current
	DESCRIPTION
		"Amplifier Stage 4: Error PSUs"
	::= { statusAmplifierStage4 8 }

amplifierStagesStatus  OBJECT-TYPE
	SYNTAX     AlarmStatus
	MAX-ACCESS read-only
	STATUS     current
	DESCRIPTION
		"Amplifier Stage status"
	::= { statusAmplifierStages 1 }

aSsInputLevelStatus  OBJECT-TYPE
	SYNTAX     AlarmStatus
	MAX-ACCESS read-only
	STATUS     current
	DESCRIPTION
		"Amplifier Stages: Input level status"
	::= { statusAmplifierStages 2 }

aSsExceededPowerStatus  OBJECT-TYPE
	SYNTAX     AlarmStatus
	MAX-ACCESS read-only
	STATUS     current
	DESCRIPTION
		"Amplifier Stages: Exceeded Power status"
	::= { statusAmplifierStages 3 }

aSsDecreasedPowerStatus  OBJECT-TYPE
	SYNTAX     AlarmStatus
	MAX-ACCESS read-only
	STATUS     current
	DESCRIPTION
		"Amplifier Stages: Decreased Power status"
	::= { statusAmplifierStages 4 }

aSsReflectedPowerStatus  OBJECT-TYPE
	SYNTAX     AlarmStatus
	MAX-ACCESS read-only
	STATUS     current
	DESCRIPTION
		"Amplifier Stages: Reflected Power status"
	::= { statusAmplifierStages 5 }

aSsTemperatureStatus  OBJECT-TYPE
	SYNTAX     AlarmStatus
	MAX-ACCESS read-only
	STATUS     current
	DESCRIPTION
		"Amplifier Stages: Temperature status"
	::= { statusAmplifierStages 6 }

aSsHwErrorStatus  OBJECT-TYPE
	SYNTAX     AlarmStatus
	MAX-ACCESS read-only
	STATUS     current
	DESCRIPTION
		"Amplifier Stages: HW error status"
	::= { statusAmplifierStages 7 }

aSsPsusErrorStatus  OBJECT-TYPE
	SYNTAX     AlarmStatus
	MAX-ACCESS read-only
	STATUS     current
	DESCRIPTION
		"Amplifier Stages: Error PSUs"
	::= { statusAmplifierStages 8 }

-- systemInitStatus  OBJECT-TYPE
-- 	SYNTAX     AlarmStatus
-- 	MAX-ACCESS read-only
-- 	STATUS     current
-- 	DESCRIPTION
-- 		"System Init"
-- 	::= { statusSystem 1 }
--
-- guiOperationStatus  OBJECT-TYPE
-- 	SYNTAX     AlarmStatus
-- 	MAX-ACCESS read-only
-- 	STATUS     current
-- 	DESCRIPTION
-- 		"GUI operation"
-- 	::= { statusSystem 2 }
--
-- muteStatus  OBJECT-TYPE
-- 	SYNTAX     AlarmStatus
-- 	MAX-ACCESS read-only
-- 	STATUS     current
-- 	DESCRIPTION
-- 		"Mute"
-- 	::= { statusSystem 3 }
--
-- inputSourceSelectedStatus  OBJECT-TYPE
-- 	SYNTAX     AlarmStatus
-- 	MAX-ACCESS read-only
-- 	STATUS     current
-- 	DESCRIPTION
-- 		"Input Source Selected"
-- 	::= { statusSystem 4 }
--
-- selectedReferenceStatus  OBJECT-TYPE
-- 	SYNTAX     AlarmStatus
-- 	MAX-ACCESS read-only
-- 	STATUS     current
-- 	DESCRIPTION
-- 		"Selected Reference"
-- 	::= { statusSystem 5 }
--
-- outputRelay1Status  OBJECT-TYPE
-- 	SYNTAX     AlarmStatus
-- 	MAX-ACCESS read-only
-- 	STATUS     current
-- 	DESCRIPTION
-- 		"Output Relay 1"
-- 	::= { statusSystem 6 }
--
-- outputRelay2Status  OBJECT-TYPE
-- 	SYNTAX     AlarmStatus
-- 	MAX-ACCESS read-only
-- 	STATUS     current
-- 	DESCRIPTION
-- 		"Output Relay 2"
-- 	::= { statusSystem 7 }
--
-- forcedMfnStatus  OBJECT-TYPE
-- 	SYNTAX     AlarmStatus
-- 	MAX-ACCESS read-only
-- 	STATUS     current
-- 	DESCRIPTION
-- 		"Forced MFN (reference error)"
-- 	::= { statusSystem 8 }
--
-- localModeTimeoutStatus  OBJECT-TYPE
-- 	SYNTAX     AlarmStatus
-- 	MAX-ACCESS read-only
-- 	STATUS     current
-- 	DESCRIPTION
-- 		"Local mode timeout"
-- 	::= { statusSystem 9 }
--
-- redundancySwitchStatus  OBJECT-TYPE
-- 	SYNTAX     AlarmStatus
-- 	MAX-ACCESS read-only
-- 	STATUS     current
-- 	DESCRIPTION
-- 		"Redundance Switch "
-- 	::= { statusSystem 10 }
--
-- startOfVerificationStatus  OBJECT-TYPE
-- 	SYNTAX     AlarmStatus
-- 	MAX-ACCESS read-only
-- 	STATUS     current
-- 	DESCRIPTION
-- 		"Start of verification"
-- 	::= { statusSystem 11 }
--
-- endOfVerificationStatus  OBJECT-TYPE
-- 	SYNTAX     AlarmStatus
-- 	MAX-ACCESS read-only
-- 	STATUS     current
-- 	DESCRIPTION
-- 		"End of verification"
-- 	::= { statusSystem 12 }
--
-- configurationFromBackup  OBJECT-TYPE
-- 	SYNTAX     AlarmStatus
-- 	MAX-ACCESS read-only
-- 	STATUS     current
-- 	DESCRIPTION
-- 		"Configuration from backup"
-- 	::= { statusSystem 13 }
--
-- restoreFromBackup  OBJECT-TYPE
-- 	SYNTAX     AlarmStatus
-- 	MAX-ACCESS read-only
-- 	STATUS     current
-- 	DESCRIPTION
-- 		"Restore from backup"
-- 	::= { statusSystem 14 }
--
-- errorConfigurationFromBackup  OBJECT-TYPE
-- 	SYNTAX     AlarmStatus
-- 	MAX-ACCESS read-only
-- 	STATUS     current
-- 	DESCRIPTION
-- 		"Error configuring from backup"
-- 	::= { statusSystem 15 }
--
-- errorRestoringFromBackup  OBJECT-TYPE
-- 	SYNTAX     AlarmStatus
-- 	MAX-ACCESS read-only
-- 	STATUS     current
-- 	DESCRIPTION
-- 		"Error restoring from backup"
-- 	::= { statusSystem 16 }
--
-- systemShutdown  OBJECT-TYPE
-- 	SYNTAX     AlarmStatus
-- 	MAX-ACCESS read-only
-- 	STATUS     current
-- 	DESCRIPTION
-- 		"System shutdown"
-- 	::= { statusSystem 17 }
--
-- systemDateAndTimeSrc  OBJECT-TYPE
-- 	SYNTAX     AlarmStatus
-- 	MAX-ACCESS read-only
-- 	STATUS     current
-- 	DESCRIPTION
-- 		"Change in date and time source"
-- 	::= { statusSystem 18 }
--
dcInputStatus  OBJECT-TYPE
	SYNTAX     AlarmStatus
	MAX-ACCESS read-only
	STATUS     current
	DESCRIPTION
		"DC Input status"
	::= { statusDcInput 1 }

redundancySysStatus  OBJECT-TYPE
	SYNTAX     AlarmStatus
	MAX-ACCESS read-only
	STATUS     current
	DESCRIPTION
		"Redundancy"
	::= { redundancySys 1 }

redundancySysCommunicationStatus  OBJECT-TYPE
	SYNTAX     AlarmStatus
	MAX-ACCESS read-only
	STATUS     current
	DESCRIPTION
		"Communication error"
	::= { redundancySys 2 }

redundancySysSwitchStatus  OBJECT-TYPE
	SYNTAX     AlarmStatus
	MAX-ACCESS read-only
	STATUS     current
	DESCRIPTION
		"RF switch error"
	::= { redundancySys 3 }

redundancySysReserveStatus  OBJECT-TYPE
	SYNTAX     AlarmStatus
	MAX-ACCESS read-only
	STATUS     current
	DESCRIPTION
		"Reserve not ready"
	::= { redundancySys 4 }

redundancyInputAsiMatrixStatus  OBJECT-TYPE
	SYNTAX     AlarmStatus
	MAX-ACCESS read-only
	STATUS     current
	DESCRIPTION
		"Inputs ASI matrix"
	::= { redundancySys 5 }

redundancyHwMatrixStatus  OBJECT-TYPE
	SYNTAX     AlarmStatus
	MAX-ACCESS read-only
	STATUS     current
	DESCRIPTION
		"HW error ASI matrix"
	::= { redundancySys 6 }

redundancyHwRfMatrixStatus  OBJECT-TYPE
	SYNTAX     AlarmStatus
	MAX-ACCESS read-only
	STATUS     current
	DESCRIPTION
		"HW error RF matrix"
	::= { redundancySys 7 }

redundancyInputEtiMatrixStatus  OBJECT-TYPE
	SYNTAX     AlarmStatus
	MAX-ACCESS read-only
	STATUS     current
	DESCRIPTION
		"Inputs ETI matrix"
	::= { redundancySys 8 }

redundancyHwEtiMatrixStatus  OBJECT-TYPE
	SYNTAX     AlarmStatus
	MAX-ACCESS read-only
	STATUS     current
	DESCRIPTION
		"HW error ETI matrix"
	::= { redundancySys 9 }

faultSummationTrap  NOTIFICATION-TYPE
	OBJECTS { faultSummationStatus,
		eventTrapLogId,
		eventTimeStamp,
		eventInitialStatus,
		eventFinalStatus,
		eventAdditionalText,
	 	redundancyId }
	STATUS     current
	DESCRIPTION
		"Fault summation trap "
	::= { eventsTx 1 }

warningSummationTrap  NOTIFICATION-TYPE
	OBJECTS { warningSummationStatus,
		eventTrapLogId,
		eventTimeStamp,
		eventInitialStatus,
		eventFinalStatus,
		eventAdditionalText,
	 	redundancyId }
	STATUS     current
	DESCRIPTION
		"Warning summation trap "
	::= { eventsTx 2 }

amplifierSumTrap  NOTIFICATION-TYPE
	OBJECTS { amplifierStatus,
		eventTrapLogId,
		eventTimeStamp,
		eventInitialStatus,
		eventFinalStatus,
		eventAdditionalText,
	 	redundancyId }
	STATUS     current
	DESCRIPTION
		"Amplifier Summatio trap "
	::= { eventsTx 3 }

exceededOutputPowerTrap  NOTIFICATION-TYPE
	OBJECTS { exceededOutputPower,
		eventTrapLogId,
		eventTimeStamp,
		eventInitialStatus,
		eventFinalStatus,
		eventAdditionalText,
	 	redundancyId }
	STATUS     current
	DESCRIPTION
		"Exceeded output power trap "
	::= { eventsTx 4 }

decreasedOutputPowerTrap  NOTIFICATION-TYPE
	OBJECTS { decreasedOutputPower,
		eventTrapLogId,
		eventTimeStamp,
		eventInitialStatus,
		eventFinalStatus,
		eventAdditionalText,
	 	redundancyId }
	STATUS     current
	DESCRIPTION
		"Decreased output power trap "
	::= { eventsTx 5 }

reflectedPowerTrap  NOTIFICATION-TYPE
	OBJECTS { reflectPowerStatus,
		eventTrapLogId,
		eventTimeStamp,
		eventInitialStatus,
		eventFinalStatus,
		eventAdditionalText,
	 	redundancyId }
	STATUS     current
	DESCRIPTION
		"Reflected power trap "
	::= { eventsTx 6 }

temperatureAmplifierTrap  NOTIFICATION-TYPE
	OBJECTS { temperatureAmplifierStatus,
		eventTrapLogId,
		eventTimeStamp,
		eventInitialStatus,
		eventFinalStatus,
		eventAdditionalText,
	 	redundancyId }
	STATUS     current
	DESCRIPTION
		"Temperature amplifier trap "
	::= { eventsTx 7 }

asiInputTrap  NOTIFICATION-TYPE
	OBJECTS { asiInputStatus,
		eventTrapLogId,
		eventTimeStamp,
		eventInitialStatus,
		eventFinalStatus,
		eventAdditionalText,
	 	redundancyId }
	STATUS     current
	DESCRIPTION
		"ASI input trap "
	::= { eventsTx 8 }

asi1ErrorTrap  NOTIFICATION-TYPE
	OBJECTS { asi1ErrorStatus,
		eventTrapLogId,
		eventTimeStamp,
		eventInitialStatus,
		eventFinalStatus,
		eventAdditionalText,
	 	redundancyId }
	STATUS     current
	DESCRIPTION
		"ASI 1 error trap "
	::= { eventsTx 9 }

asi2ErrorTrap  NOTIFICATION-TYPE
	OBJECTS { asi2ErrorStatus,
		eventTrapLogId,
		eventTimeStamp,
		eventInitialStatus,
		eventFinalStatus,
		eventAdditionalText,
	 	redundancyId }
	STATUS     current
	DESCRIPTION
		"ASI 2 error trap "
	::= { eventsTx 10 }

ipInputSumTrap  NOTIFICATION-TYPE
	OBJECTS { ipInputAlarmStatus,
		eventTrapLogId,
		eventTimeStamp,
		eventInitialStatus,
		eventFinalStatus,
		eventAdditionalText,
	 	redundancyId }
	STATUS     current
	DESCRIPTION
		"IP input summation trap "
	::= { eventsTx 11 }

ipSocket1ErrorTrap  NOTIFICATION-TYPE
	OBJECTS { ipSocket1ErrorStatus,
		eventTrapLogId,
		eventTimeStamp,
		eventInitialStatus,
		eventFinalStatus,
		eventAdditionalText,
	 	redundancyId }
	STATUS     current
	DESCRIPTION
		"IP socket 1 error trap "
	::= { eventsTx 12 }

ipSocket2ErrorTrap  NOTIFICATION-TYPE
	OBJECTS { ipSocket2ErrorStatus,
		eventTrapLogId,
		eventTimeStamp,
		eventInitialStatus,
		eventFinalStatus,
		eventAdditionalText,
	 	redundancyId }
	STATUS     current
	DESCRIPTION
		"IP socket 2 error trap "
	::= { eventsTx 13 }

satReceiver1Trap  NOTIFICATION-TYPE
	OBJECTS { satReceiver1Status,
		eventTrapLogId,
		eventTimeStamp,
		eventInitialStatus,
		eventFinalStatus,
		eventAdditionalText,
	 	redundancyId }
	STATUS     current
	DESCRIPTION
		"Satellite Receiver 1 trap "
	::= { eventsTx 14 }

unlockSatReceiver1Trap  NOTIFICATION-TYPE
	OBJECTS { unlockSatReceiver1Status,
		eventTrapLogId,
		eventTimeStamp,
		eventInitialStatus,
		eventFinalStatus,
		eventAdditionalText,
	 	redundancyId }
	STATUS     current
	DESCRIPTION
		"Unlock satellite receiver 1 trap "
	::= { eventsTx 15 }

rfSignalSatReceiver1Trap  NOTIFICATION-TYPE
	OBJECTS { rfSignalSatReceiver1Status,
		eventTrapLogId,
		eventTimeStamp,
		eventInitialStatus,
		eventFinalStatus,
		eventAdditionalText,
	 	redundancyId }
	STATUS     current
	DESCRIPTION
		"RF signal satellite receiver 1 trap "
	::= { eventsTx 16 }

lnbOverloadSatReceiver1Trap  NOTIFICATION-TYPE
	OBJECTS { lnbOverloadSatReceiver1Status,
		eventTrapLogId,
		eventTimeStamp,
		eventInitialStatus,
		eventFinalStatus,
		eventAdditionalText,
	 	redundancyId }
	STATUS     current
	DESCRIPTION
		"LNB overload satellity receiver 1 trap "
	::= { eventsTx 17 }

temperatureSatReceiver1Trap  NOTIFICATION-TYPE
	OBJECTS { temperatureSatReceiver1Status,
		eventTrapLogId,
		eventTimeStamp,
		eventInitialStatus,
		eventFinalStatus,
		eventAdditionalText,
	 	redundancyId }
	STATUS     current
	DESCRIPTION
		"Temperature satellity receiver 1 trap "
	::= { eventsTx 18 }

satReceiver2Trap  NOTIFICATION-TYPE
	OBJECTS { satReceiver2Status,
		eventTrapLogId,
		eventTimeStamp,
		eventInitialStatus,
		eventFinalStatus,
		eventAdditionalText,
	 	redundancyId }
	STATUS     current
	DESCRIPTION
		"Satellite receiver 2 trap "
	::= { eventsTx 19 }

unlockSatReceiver2Trap  NOTIFICATION-TYPE
	OBJECTS { unlockSatReceiver2Status,
		eventTrapLogId,
		eventTimeStamp,
		eventInitialStatus,
		eventFinalStatus,
		eventAdditionalText,
	 	redundancyId }
	STATUS     current
	DESCRIPTION
		"Unlock satellite receiver 2 trap "
	::= { eventsTx 20 }

rfSignalSatReceiver2Trap  NOTIFICATION-TYPE
	OBJECTS { rfSignalSatReceiver1Status,
		eventTrapLogId,
		eventTimeStamp,
		eventInitialStatus,
		eventFinalStatus,
		eventAdditionalText,
	 	redundancyId }
	STATUS     current
	DESCRIPTION
		"RF signal satellite receiver 2 trap "
	::= { eventsTx 21 }

lnbOverloadSatReceiver2Trap  NOTIFICATION-TYPE
	OBJECTS { lnbOverloadSatReceiver2Status,
		eventTrapLogId,
		eventTimeStamp,
		eventInitialStatus,
		eventFinalStatus,
		eventAdditionalText,
	 	redundancyId }
	STATUS     current
	DESCRIPTION
		"LNB overload satellite receiver 2 trap "
	::= { eventsTx 22 }

temperatureSatReceiver2Trap  NOTIFICATION-TYPE
	OBJECTS { temperatureSatReceiver2Status,
		eventTrapLogId,
		eventTimeStamp,
		eventInitialStatus,
		eventFinalStatus,
		eventAdditionalText,
	 	redundancyId }
	STATUS     current
	DESCRIPTION
		"Temperature satellite receiver 2 trap "
	::= { eventsTx 23 }

dttReceiver1Trap  NOTIFICATION-TYPE
	OBJECTS { dttReceiver1AlarmStatus,
		eventTrapLogId,
		eventTimeStamp,
		eventInitialStatus,
		eventFinalStatus,
		eventAdditionalText,
	 	redundancyId }
	STATUS     current
	DESCRIPTION
		"DTT receiver 1 trap "
	::= { eventsTx 24 }

unlockDttReceiver1Trap  NOTIFICATION-TYPE
	OBJECTS { unlockDttReceiver1Status,
		eventTrapLogId,
		eventTimeStamp,
		eventInitialStatus,
		eventFinalStatus,
		eventAdditionalText,
	 	redundancyId }
	STATUS     current
	DESCRIPTION
		"Unlock DTT receiver 1 trap "
	::= { eventsTx 25 }

rfSignalDttReceiver1Trap  NOTIFICATION-TYPE
	OBJECTS { rfSignalDttReceiver1Status,
		eventTrapLogId,
		eventTimeStamp,
		eventInitialStatus,
		eventFinalStatus,
		eventAdditionalText,
	 	redundancyId }
	STATUS     current
	DESCRIPTION
		"RF signal DTT receiver 1 trap "
	::= { eventsTx 26 }

temperatureDttReceiver1Trap  NOTIFICATION-TYPE
	OBJECTS { temperatureDttReceiver1Status,
		eventTrapLogId,
		eventTimeStamp,
		eventInitialStatus,
		eventFinalStatus,
		eventAdditionalText,
	 	redundancyId }
	STATUS     current
	DESCRIPTION
		"Temperature DTT receiver 1 trap "
	::= { eventsTx 27 }

dttReceiver2Trap  NOTIFICATION-TYPE
	OBJECTS { dttReceiver2AlarmStatus,
		eventTrapLogId,
		eventTimeStamp,
		eventInitialStatus,
		eventFinalStatus,
		eventAdditionalText,
	 	redundancyId }
	STATUS     current
	DESCRIPTION
		"DTT receiver 2 trap "
	::= { eventsTx 28 }

unlockDttReceiver2Trap  NOTIFICATION-TYPE
	OBJECTS { unlockDttReceiver2Status,
		eventTrapLogId,
		eventTimeStamp,
		eventInitialStatus,
		eventFinalStatus,
		eventAdditionalText,
	 	redundancyId }
	STATUS     current
	DESCRIPTION
		"Unlock DTT receiver 2 trap "
	::= { eventsTx 29 }

rfSignalDttReceiver2Trap  NOTIFICATION-TYPE
	OBJECTS { rfSignalDttReceiver2Status,
		eventTrapLogId,
		eventTimeStamp,
		eventInitialStatus,
		eventFinalStatus,
		eventAdditionalText,
	 	redundancyId }
	STATUS     current
	DESCRIPTION
		"RF signal DTT receiver 2 trap "
	::= { eventsTx 30 }

temperatureDttReceiver2Trap  NOTIFICATION-TYPE
	OBJECTS { temperatureDttReceiver2Status,
		eventTrapLogId,
		eventTimeStamp,
		eventInitialStatus,
		eventFinalStatus,
		eventAdditionalText,
	 	redundancyId }
	STATUS     current
	DESCRIPTION
		"Temperature DTT receiver 2 trap "
	::= { eventsTx 31 }

modulatorSumTrap  NOTIFICATION-TYPE
	OBJECTS { modulatorAlarmStatus,
		eventTrapLogId,
		eventTimeStamp,
		eventInitialStatus,
		eventFinalStatus,
		eventAdditionalText,
	 	redundancyId }
	STATUS     current
	DESCRIPTION
		"Modulator summation trap "
	::= { eventsTx 32 }

tsErrorTrap  NOTIFICATION-TYPE
	OBJECTS { tsErrorStatus,
		eventTrapLogId,
		eventTimeStamp,
		eventInitialStatus,
		eventFinalStatus,
		eventAdditionalText,
	 	redundancyId }
	STATUS     current
	DESCRIPTION
		"TS error trap "
	::= { eventsTx 33 }

mipErrorTrap  NOTIFICATION-TYPE
	OBJECTS { mipErrorStatus,
		eventTrapLogId,
		eventTimeStamp,
		eventInitialStatus,
		eventFinalStatus,
		eventAdditionalText,
	 	redundancyId }
	STATUS     current
	DESCRIPTION
		"MIP error trap "
	::= { eventsTx 34 }

mpegOverflowTrap  NOTIFICATION-TYPE
	OBJECTS { mpegOverflowStatus,
		eventTrapLogId,
		eventTimeStamp,
		eventInitialStatus,
		eventFinalStatus,
		eventAdditionalText,
	 	redundancyId }
	STATUS     current
	DESCRIPTION
		"MPEG overflow trap "
	::= { eventsTx 35 }

t2miErrorTrap  NOTIFICATION-TYPE
	OBJECTS { t2miErrorStatus,
		eventTrapLogId,
		eventTimeStamp,
		eventInitialStatus,
		eventFinalStatus,
		eventAdditionalText,
	 	redundancyId }
	STATUS     current
	DESCRIPTION
		"T2MI error trap "
	::= { eventsTx 36 }

sfnReferenceTrap  NOTIFICATION-TYPE
	OBJECTS { sfnErrorStatus,
		eventTrapLogId,
		eventTimeStamp,
		eventInitialStatus,
		eventFinalStatus,
		eventAdditionalText,
	 	redundancyId }
	STATUS     current
	DESCRIPTION
		"SFN reference trap "
	::= { eventsTx 37 }

sfnMarginTrap  NOTIFICATION-TYPE
	OBJECTS { sfnMargin,
		eventTrapLogId,
		eventTimeStamp,
		eventInitialStatus,
		eventFinalStatus,
		eventAdditionalText,
	 	redundancyId }
	STATUS     current
	DESCRIPTION
		"SFN margin trap "
	::= { eventsTx 38 }

temperatureModulatorTrap  NOTIFICATION-TYPE
	OBJECTS { temperatureModulatorStatus,
		eventTrapLogId,
		eventTimeStamp,
		eventInitialStatus,
		eventFinalStatus,
		eventAdditionalText,
	 	redundancyId }
	STATUS     current
	DESCRIPTION
		"Temperature modulator trap "
	::= { eventsTx 39 }

modulatorOutputTrap  NOTIFICATION-TYPE
	OBJECTS { modulatorOutputStatus,
		eventTrapLogId,
		eventTimeStamp,
		eventInitialStatus,
		eventFinalStatus,
		eventAdditionalText,
	 	redundancyId }
	STATUS     current
	DESCRIPTION
		"Modulator output trap "
	::= { eventsTx 40 }

rfOutputTrap  NOTIFICATION-TYPE
	OBJECTS { rfOutputStatus,
		eventTrapLogId,
		eventTimeStamp,
		eventInitialStatus,
		eventFinalStatus,
		eventAdditionalText,
	 	redundancyId }
	STATUS     current
	DESCRIPTION
		"RF output trap "
	::= { eventsTx 41 }

cancellerShouldersTrap  NOTIFICATION-TYPE
	OBJECTS { cancellerShouldersStatus,
		eventTrapLogId,
		eventTimeStamp,
		eventInitialStatus,
		eventFinalStatus,
		eventAdditionalText,
	 	redundancyId }
	STATUS     current
	DESCRIPTION
		"Canceller shoulders trap "
	::= { eventsTx 42 }

input10MhzTrap  NOTIFICATION-TYPE
	OBJECTS { input10MhzStatus,
		eventTrapLogId,
		eventTimeStamp,
		eventInitialStatus,
		eventFinalStatus,
		eventAdditionalText,
	 	redundancyId }
	STATUS     current
	DESCRIPTION
		"Input 10MHz trap "
	::= { eventsTx 43 }

input1ppsTrap  NOTIFICATION-TYPE
	OBJECTS { input1ppsStatus,
		eventTrapLogId,
		eventTimeStamp,
		eventInitialStatus,
		eventFinalStatus,
		eventAdditionalText,
	 	redundancyId }
	STATUS     current
	DESCRIPTION
		"Input 1PPS trap "
	::= { eventsTx 44 }

synchronizationModuleTrap  NOTIFICATION-TYPE
	OBJECTS { synchronizationAlarmStatus,
		eventTrapLogId,
		eventTimeStamp,
		eventInitialStatus,
		eventFinalStatus,
		eventAdditionalText,
	 	redundancyId }
	STATUS     current
	DESCRIPTION
		"Synchronization module trap "
	::= { eventsTx 45 }

synchronizationAntennaTrap  NOTIFICATION-TYPE
	OBJECTS { synchronizationAntennaStatus,
		eventTrapLogId,
		eventTimeStamp,
		eventInitialStatus,
		eventFinalStatus,
		eventAdditionalText,
	 	redundancyId }
	STATUS     current
	DESCRIPTION
		"Synchronization antenna trap "
	::= { eventsTx 46 }

synchronizationUnlockTrap  NOTIFICATION-TYPE
	OBJECTS { synchronizationUnlockStatus,
		eventTrapLogId,
		eventTimeStamp,
		eventInitialStatus,
		eventFinalStatus,
		eventAdditionalText,
	 	redundancyId }
	STATUS     current
	DESCRIPTION
		"Shynchronization unlock trap "
	::= { eventsTx 47 }

synchronizationHoldoverTrap  NOTIFICATION-TYPE
	OBJECTS { synchronizationHoldoverStatus,
		eventTrapLogId,
		eventTimeStamp,
		eventInitialStatus,
		eventFinalStatus,
		eventAdditionalText,
	 	redundancyId }
	STATUS     current
	DESCRIPTION
		"Synchronization holdover trap "
	::= { eventsTx 48 }

synchronizationHwErrorTrap  NOTIFICATION-TYPE
	OBJECTS { synchronizationHwErrorStatus,
		eventTrapLogId,
		eventTimeStamp,
		eventInitialStatus,
		eventFinalStatus,
		eventAdditionalText,
	 	redundancyId }
	STATUS     current
	DESCRIPTION
		"Syncronization HW error trap "
	::= { eventsTx 49 }

temperatureSynchronizationTrap  NOTIFICATION-TYPE
	OBJECTS { temperatureSynchronizationStatus,
		eventTrapLogId,
		eventTimeStamp,
		eventInitialStatus,
		eventFinalStatus,
		eventAdditionalText,
	 	redundancyId }
	STATUS     current
	DESCRIPTION
		"Temperature syncrhonization trap "
	::= { eventsTx 50 }

reference10MHzTrap  NOTIFICATION-TYPE
	OBJECTS { reference10MHzStatus,
		eventTrapLogId,
		eventTimeStamp,
		eventInitialStatus,
		eventFinalStatus,
		eventAdditionalText,
	 	redundancyId }
	STATUS     current
	DESCRIPTION
		"Reference 10MHz trap "
	::= { eventsTx 51 }

dateAndTimeReferenceEventTrap  NOTIFICATION-TYPE
	OBJECTS { eventTrapLogId,
		eventTimeStamp,
		eventInitialStatus,
		eventFinalStatus,
		eventAdditionalText,
	 	redundancyId }
	STATUS     current
	DESCRIPTION
		"Date and time reference trap "
	::= { eventsTx 52 }

acPowerSupplyTrap  NOTIFICATION-TYPE
	OBJECTS { acPowerSupplyStatus,
		eventTrapLogId,
		eventTimeStamp,
		eventInitialStatus,
		eventFinalStatus,
		eventAdditionalText,
	 	redundancyId }
	STATUS     current
	DESCRIPTION
		"AC power supply trap "
	::= { eventsTx 53 }

psuATrap  NOTIFICATION-TYPE
	OBJECTS { acPsuAStatus,
		eventTrapLogId,
		eventTimeStamp,
		eventInitialStatus,
		eventFinalStatus,
		eventAdditionalText,
	 	redundancyId }
	STATUS     current
	DESCRIPTION
		"PSU A trap "
	::= { eventsTx 54 }

psuBTrap  NOTIFICATION-TYPE
	OBJECTS { acPsuBStatus,
		eventTrapLogId,
		eventTimeStamp,
		eventInitialStatus,
		eventFinalStatus,
		eventAdditionalText,
	 	redundancyId }
	STATUS     current
	DESCRIPTION
		"PSU B trap "
	::= { eventsTx 55 }

hwErrorTrap  NOTIFICATION-TYPE
	OBJECTS { hwErrorStatus,
		eventTrapLogId,
		eventTimeStamp,
		eventInitialStatus,
		eventFinalStatus,
		eventAdditionalText,
	 	redundancyId }
	STATUS     current
	DESCRIPTION
		"HW error trap "
	::= { eventsTx 57 }

ldmosTransistorsTrap  NOTIFICATION-TYPE
	OBJECTS { ldmosTransistorsStatus,
		eventTrapLogId,
		eventTimeStamp,
		eventInitialStatus,
		eventFinalStatus,
		eventAdditionalText,
	 	redundancyId }
	STATUS     current
	DESCRIPTION
		"LDMOS transistors trap "
	::= { eventsTx 58 }

internalErrorTrap  NOTIFICATION-TYPE
	OBJECTS { internalErrorStatus,
		eventTrapLogId,
		eventTimeStamp,
		eventInitialStatus,
		eventFinalStatus,
		eventAdditionalText,
	 	redundancyId }
	STATUS     current
	DESCRIPTION
		"Internal error trap "
	::= { eventsTx 59 }

localOscillatorTrap  NOTIFICATION-TYPE
	OBJECTS { localOscillatorStatus,
		eventTrapLogId,
		eventTimeStamp,
		eventInitialStatus,
		eventFinalStatus,
		eventAdditionalText,
	 	redundancyId }
	STATUS     current
	DESCRIPTION
		"Local oscillator trap "
	::= { eventsTx 60 }

internalDcSupplyVoltageTrap  NOTIFICATION-TYPE
	OBJECTS { internalDcSupplyVoltageStatus,
		eventTrapLogId,
		eventTimeStamp,
		eventInitialStatus,
		eventFinalStatus,
		eventAdditionalText,
	 	redundancyId }
	STATUS     current
	DESCRIPTION
		"Internal DC supply voltage trap "
	::= { eventsTx 61 }

fanSumTrap  NOTIFICATION-TYPE
	OBJECTS { fanAlarmStatus,
		eventTrapLogId,
		eventTimeStamp,
		eventInitialStatus,
		eventFinalStatus,
		eventAdditionalText,
	 	redundancyId }
	STATUS     current
	DESCRIPTION
		"FAN sumation trap "
	::= { eventsTx 62 }

fan1Trap  NOTIFICATION-TYPE
	OBJECTS { fan1Status,
		eventTrapLogId,
		eventTimeStamp,
		eventInitialStatus,
		eventFinalStatus,
		eventAdditionalText,
	 	redundancyId }
	STATUS     current
	DESCRIPTION
		"FAN 1 trap "
	::= { eventsTx 63 }

fan2Trap  NOTIFICATION-TYPE
	OBJECTS { fan2Status,
		eventTrapLogId,
		eventTimeStamp,
		eventInitialStatus,
		eventFinalStatus,
		eventAdditionalText,
	 	redundancyId }
	STATUS     current
	DESCRIPTION
		"FAN 2 trap "
	::= { eventsTx 64 }

fan3Trap  NOTIFICATION-TYPE
	OBJECTS { fan3Status,
		eventTrapLogId,
		eventTimeStamp,
		eventInitialStatus,
		eventFinalStatus,
		eventAdditionalText,
	 	redundancyId }
	STATUS     current
	DESCRIPTION
		"FAN 3 trap "
	::= { eventsTx 65 }

externalAlarmTrap  NOTIFICATION-TYPE
	OBJECTS { externalAlarmStatus,
		eventTrapLogId,
		eventTimeStamp,
		eventInitialStatus,
		eventFinalStatus,
		eventAdditionalText,
	 	redundancyId }
	STATUS     current
	DESCRIPTION
		"External alarm trap "
	::= { eventsTx 66 }

externalAlarm1Trap  NOTIFICATION-TYPE
	OBJECTS { external1Status,
		eventTrapLogId,
		eventTimeStamp,
		eventInitialStatus,
		eventFinalStatus,
		eventAdditionalText,
	 	redundancyId }
	STATUS     current
	DESCRIPTION
		"External alarm 1 trap "
	::= { eventsTx 67 }

externalAlarm2Trap  NOTIFICATION-TYPE
	OBJECTS { external2Status,
		eventTrapLogId,
		eventTimeStamp,
		eventInitialStatus,
		eventFinalStatus,
		eventAdditionalText,
	 	redundancyId }
	STATUS     current
	DESCRIPTION
		"External alarm 2 trap "
	::= { eventsTx 68 }

systemInitEventTrap  NOTIFICATION-TYPE
	OBJECTS { eventTrapLogId,
		eventTimeStamp,
		eventAdditionalText,
	 	redundancyId }
	STATUS     current
	DESCRIPTION
		"System init trap "
	::= { eventsTx 69 }

guiOperationEventTrap  NOTIFICATION-TYPE
	OBJECTS { eventTrapLogId,
		eventTimeStamp,
		eventAdditionalText,
	 	redundancyId }
	STATUS     current
	DESCRIPTION
		"GUI operation trap "
	::= { eventsTx 70 }

muteEventTrap  NOTIFICATION-TYPE
	OBJECTS { eventTrapLogId,
		eventTimeStamp,
		eventAdditionalText,
	 	redundancyId }
	STATUS     current
	DESCRIPTION
		"MUTE trap "
	::= { eventsTx 71 }

inputSourceSelectedEventTrap  NOTIFICATION-TYPE
	OBJECTS { eventTrapLogId,
		eventTimeStamp,
		eventAdditionalText }
	STATUS     current
	DESCRIPTION
		"Input source selected trap "
	::= { eventsTx 72 }

selectedReferenceEventTrap  NOTIFICATION-TYPE
	OBJECTS { eventTrapLogId,
		eventTimeStamp,
		eventAdditionalText,
	 	redundancyId }
	STATUS     current
	DESCRIPTION
		"Selected reference trap "
	::= { eventsTx 73 }

outputRelay1Trap  NOTIFICATION-TYPE
	OBJECTS { eventTrapLogId,
		eventTimeStamp,
		eventInitialStatus,
		eventFinalStatus,
		eventAdditionalText,
	 	redundancyId }
	STATUS     current
	DESCRIPTION
		"Output relay 1 trap "
	::= { eventsTx 74 }

outputRelay2Trap  NOTIFICATION-TYPE
	OBJECTS { eventTrapLogId,
		eventTimeStamp,
		eventInitialStatus,
		eventFinalStatus,
		eventAdditionalText,
	 	redundancyId }
	STATUS     current
	DESCRIPTION
		"Output relay 2 trap "
	::= { eventsTx 75 }

forcedMfnEventTrap  NOTIFICATION-TYPE
	OBJECTS { eventTrapLogId,
		eventTimeStamp,
		eventAdditionalText,
	 	redundancyId }
	STATUS     current
	DESCRIPTION
		"Forced MFN trap "
	::= { eventsTx 76 }

localModeTimeoutEventTrap  NOTIFICATION-TYPE
	OBJECTS { eventTrapLogId,
		eventTimeStamp,
		eventAdditionalText,
	 	redundancyId }
	STATUS     current
	DESCRIPTION
		"Local mode timeout trap "
	::= { eventsTx 77 }

redundancyEventTrap  NOTIFICATION-TYPE
	OBJECTS { eventTrapLogId,
		eventTimeStamp,
		eventAdditionalText,
	 	redundancyId }
	STATUS     current
	DESCRIPTION
		"Redundancy trap "
	::= { eventsTx 78 }

btsErrorTrap  NOTIFICATION-TYPE
	OBJECTS { btsErrorStatus,
		eventTrapLogId,
		eventTimeStamp,
		eventInitialStatus,
		eventFinalStatus,
		eventAdditionalText,
	 	redundancyId }
	STATUS     current
	DESCRIPTION
		"BTS error trap "
	::= { eventsTx 81 }

nonLinearSenseFeedbackTrap  NOTIFICATION-TYPE
	OBJECTS { nonLinearSenseFeedback,
		eventTrapLogId,
		eventTimeStamp,
		eventInitialStatus,
		eventFinalStatus,
		eventAdditionalText,
	 	redundancyId }
	STATUS     current
	DESCRIPTION
		"Non linear sense feedback trap "
	::= { eventsTx 82 }

modulatorShouldersTrap  NOTIFICATION-TYPE
	OBJECTS { modulatorShouldersStatus,
		eventTrapLogId,
		eventTimeStamp,
		eventInitialStatus,
		eventFinalStatus,
		eventAdditionalText,
	 	redundancyId }
	STATUS     current
	DESCRIPTION
		"Modulator shoulder trap "
	::= { eventsTx 83 }

configurationFromBackupEventTrap  NOTIFICATION-TYPE
	OBJECTS { eventTrapLogId,
		eventTimeStamp,
		eventInitialStatus,
		eventFinalStatus,
		eventAdditionalText,
	 	redundancyId }
	STATUS     current
	DESCRIPTION
		"Configuration from backup trap "
	::= { eventsTx 84 }

rfInputTrap  NOTIFICATION-TYPE
	OBJECTS { rfInputStatus,
		eventTrapLogId,
		eventTimeStamp,
		eventInitialStatus,
		eventFinalStatus,
		eventAdditionalText,
	 	redundancyId }
	STATUS     current
	DESCRIPTION
		"RF input trap "
	::= { eventsTx 88 }

echoCancellerTrap  NOTIFICATION-TYPE
	OBJECTS { echoCancellerStatus,
		eventTrapLogId,
		eventTimeStamp,
		eventInitialStatus,
		eventFinalStatus,
		eventAdditionalText,
	 	redundancyId }
	STATUS     current
	DESCRIPTION
		"Echo canceller trap "
	::= { eventsTx 89 }

inputLevelTrap  NOTIFICATION-TYPE
	OBJECTS { inputLevelStatus,
		eventTrapLogId,
		eventTimeStamp,
		eventInitialStatus,
		eventFinalStatus,
		eventAdditionalText,
	 	redundancyId }
	STATUS     current
	DESCRIPTION
		"Input level trap "
	::= { eventsTx 90 }

temperatureECTrap  NOTIFICATION-TYPE
	OBJECTS { temperatureECStatus,
		eventTrapLogId,
		eventTimeStamp,
		eventInitialStatus,
		eventFinalStatus,
		eventAdditionalText,
	 	redundancyId }
	STATUS     current
	DESCRIPTION
		"Temperature EC Trap "
	::= { eventsTx 91 }

outputLevelTrap  NOTIFICATION-TYPE
	OBJECTS { outputLevelStatus,
		eventTrapLogId,
		eventTimeStamp,
		eventInitialStatus,
		eventFinalStatus,
		eventAdditionalText,
	 	redundancyId }
	STATUS     current
	DESCRIPTION
		"Output level trap "
	::= { eventsTx 92 }

amplifierOutputSampleTrap  NOTIFICATION-TYPE
	OBJECTS { amplifierOutputSample,
		eventTrapLogId,
		eventTimeStamp,
		eventInitialStatus,
		eventFinalStatus,
		eventAdditionalText,
	 	redundancyId }
	STATUS     current
	DESCRIPTION
		"Amplifier output sample status trap"
	::= { eventsTx 93 }

systemShutdownEventTrap  NOTIFICATION-TYPE
	OBJECTS { eventTrapLogId,
		eventTimeStamp,
		eventAdditionalText,
	 	redundancyId }
	STATUS     current
	DESCRIPTION
		"System shutdown trap "
	::= { eventsTx 94 }

standardAutoConfigurationTrap  NOTIFICATION-TYPE
	OBJECTS { eventTrapLogId,
		eventTimeStamp,
		eventAdditionalText,
	 	redundancyId }
	STATUS     current
	DESCRIPTION
		"Standard auto-configuration"
	::= { eventsTx 106 }

cancellerMerStatusTrap  NOTIFICATION-TYPE
	OBJECTS { cancellerMerStatus,
		eventTrapLogId,
		eventTimeStamp,
		eventInitialStatus,
		eventFinalStatus,
		eventAdditionalText }
	STATUS     current
	DESCRIPTION
		"Canceller MER trap"
	::= { eventsTx 107 }

gainMarginStatusTrap  NOTIFICATION-TYPE
	OBJECTS { gainMarginStatus,
		eventTrapLogId,
		eventTimeStamp,
		eventInitialStatus,
		eventFinalStatus,
		eventAdditionalText,
	 	redundancyId }
	STATUS     current
	DESCRIPTION
		"Gain margin trap"
	::= { eventsTx 108 }

cancExternalFeedbackStatusTrap  NOTIFICATION-TYPE
	OBJECTS { cancExternalFeedbackStatus,
		eventTrapLogId,
		eventTimeStamp,
		eventInitialStatus,
		eventFinalStatus,
		eventAdditionalText,
	 	redundancyId }
	STATUS     current
	DESCRIPTION
		"Canceller External feedback trap"
	::= { eventsTx 109 }

modulatorMerStatusTrap  NOTIFICATION-TYPE
	OBJECTS { modulatorMerStatus,
		eventTrapLogId,
		eventTimeStamp,
		eventInitialStatus,
		eventFinalStatus,
		eventAdditionalText,
	 	redundancyId }
	STATUS     current
	DESCRIPTION
		"Modulator MER trap"
	::= { eventsTx 110 }

modExternalFeedbackStatusTrap  NOTIFICATION-TYPE
	OBJECTS { modulatorExternalFeedbackStatus,
		eventTrapLogId,
		eventTimeStamp,
		eventInitialStatus,
		eventFinalStatus,
		eventAdditionalText,
	 	redundancyId }
	STATUS     current
	DESCRIPTION
		"Modulator MER trap"
	::= { eventsTx 111 }

modBerStatusTrap  NOTIFICATION-TYPE
	OBJECTS { modulatorBerStatus,
		eventTrapLogId,
		eventTimeStamp,
		eventInitialStatus,
		eventFinalStatus,
		eventAdditionalText,
	 	redundancyId }
	STATUS     current
	DESCRIPTION
		"Modulator BER trap"
	::= { eventsTx 164 }


amplifierStage1SumTrap  NOTIFICATION-TYPE
	OBJECTS { amplifierStage1Status,
		eventTrapLogId,
		eventTimeStamp,
		eventInitialStatus,
		eventFinalStatus,
		eventAdditionalText,
	 	redundancyId }
	STATUS     current
	DESCRIPTION
		"Amplifier Stage 1 trap"
	::= { eventsTx 112 }

aS1InputLevelTrap  NOTIFICATION-TYPE
	OBJECTS { aS1InputLevelStatus,
		eventTrapLogId,
		eventTimeStamp,
		eventInitialStatus,
		eventFinalStatus,
		eventAdditionalText,
	 	redundancyId }
	STATUS     current
	DESCRIPTION
		"Amplifier Stage 1 Input Level trap"
	::= { eventsTx 113 }

aS1ExceededPowerTrap  NOTIFICATION-TYPE
	OBJECTS { aS1ExceededPowerStatus,
		eventTrapLogId,
		eventTimeStamp,
		eventInitialStatus,
		eventFinalStatus,
		eventAdditionalText,
	 	redundancyId }
	STATUS     current
	DESCRIPTION
		"Amplifier Stage 1 Exceeded Power trap"
	::= { eventsTx 114 }

aS1DecreasedPowerTrap  NOTIFICATION-TYPE
	OBJECTS { aS1DecreasedPowerStatus,
		eventTrapLogId,
		eventTimeStamp,
		eventInitialStatus,
		eventFinalStatus,
		eventAdditionalText,
	 	redundancyId }
	STATUS     current
	DESCRIPTION
		"Amplifier Stage 1 Decreased Power trap"
	::= { eventsTx 115 }

aS1ReflectedPowerTrap  NOTIFICATION-TYPE
	OBJECTS { aS1ReflectedPowerStatus,
		eventTrapLogId,
		eventTimeStamp,
		eventInitialStatus,
		eventFinalStatus,
		eventAdditionalText,
	 	redundancyId }
	STATUS     current
	DESCRIPTION
		"Amplifier Stage 1 Reflected Power trap"
	::= { eventsTx 116 }

aS1TemperatureTrap  NOTIFICATION-TYPE
	OBJECTS { aS1TemperatureStatus,
		eventTrapLogId,
		eventTimeStamp,
		eventInitialStatus,
		eventFinalStatus,
		eventAdditionalText,
	 	redundancyId }
	STATUS     current
	DESCRIPTION
		"Amplifier Stage 1 Temperature trap"
	::= { eventsTx 117 }

aS1HwErrorTrap  NOTIFICATION-TYPE
	OBJECTS { aS1HwErrorStatus,
		eventTrapLogId,
		eventTimeStamp,
		eventInitialStatus,
		eventFinalStatus,
		eventAdditionalText,
	 	redundancyId }
	STATUS     current
	DESCRIPTION
		"Amplifier Stage 1 HW error trap"
	::= { eventsTx 118 }

amplifierStage2SumTrap  NOTIFICATION-TYPE
	OBJECTS { amplifierStage2Status,
		eventTrapLogId,
		eventTimeStamp,
		eventInitialStatus,
		eventFinalStatus,
		eventAdditionalText,
	 	redundancyId }
	STATUS     current
	DESCRIPTION
		"Amplifier Stage 2 trap"
	::= { eventsTx 119 }

aS2InputLevelTrap  NOTIFICATION-TYPE
	OBJECTS { aS2InputLevelStatus,
		eventTrapLogId,
		eventTimeStamp,
		eventInitialStatus,
		eventFinalStatus,
		eventAdditionalText,
	 	redundancyId }
	STATUS     current
	DESCRIPTION
		"Amplifier Stage 2 Input Level trap"
	::= { eventsTx 120 }

aS2ExceededPowerTrap  NOTIFICATION-TYPE
	OBJECTS { aS2ExceededPowerStatus,
		eventTrapLogId,
		eventTimeStamp,
		eventInitialStatus,
		eventFinalStatus,
		eventAdditionalText,
	 	redundancyId }
	STATUS     current
	DESCRIPTION
		"Amplifier Stage 2 Exceeded Power trap"
	::= { eventsTx 121 }

aS2DecreasedPowerTrap  NOTIFICATION-TYPE
	OBJECTS { aS2DecreasedPowerStatus,
		eventTrapLogId,
		eventTimeStamp,
		eventInitialStatus,
		eventFinalStatus,
		eventAdditionalText,
	 	redundancyId }
	STATUS     current
	DESCRIPTION
		"Amplifier Stage 2 Decreased Power trap"
	::= { eventsTx 122 }

aS2ReflectedPowerTrap  NOTIFICATION-TYPE
	OBJECTS { aS2ReflectedPowerStatus,
		eventTrapLogId,
		eventTimeStamp,
		eventInitialStatus,
		eventFinalStatus,
		eventAdditionalText,
	 	redundancyId }
	STATUS     current
	DESCRIPTION
		"Amplifier Stage 2 Reflected Power trap"
	::= { eventsTx 123 }

aS2TemperatureTrap  NOTIFICATION-TYPE
	OBJECTS { aS2TemperatureStatus,
		eventTrapLogId,
		eventTimeStamp,
		eventInitialStatus,
		eventFinalStatus,
		eventAdditionalText,
	 	redundancyId }
	STATUS     current
	DESCRIPTION
		"Amplifier Stage 2 Temperature trap"
	::= { eventsTx 124 }

aS2HwErrorTrap  NOTIFICATION-TYPE
	OBJECTS { aS2HwErrorStatus,
		eventTrapLogId,
		eventTimeStamp,
		eventInitialStatus,
		eventFinalStatus,
		eventAdditionalText,
	 	redundancyId }
	STATUS     current
	DESCRIPTION
		"Amplifier Stage 2 HW error trap"
	::= { eventsTx 125 }

amplifierStage3SumTrap  NOTIFICATION-TYPE
	OBJECTS { amplifierStage3Status,
		eventTrapLogId,
		eventTimeStamp,
		eventInitialStatus,
		eventFinalStatus,
		eventAdditionalText,
	 	redundancyId }
	STATUS     current
	DESCRIPTION
		"Amplifier Stage 3 trap"
	::= { eventsTx 126 }

aS3InputLevelTrap  NOTIFICATION-TYPE
	OBJECTS { aS3InputLevelStatus,
		eventTrapLogId,
		eventTimeStamp,
		eventInitialStatus,
		eventFinalStatus,
		eventAdditionalText,
	 	redundancyId }
	STATUS     current
	DESCRIPTION
		"Amplifier Stage 3 Input Level trap"
	::= { eventsTx 127 }

aS3ExceededPowerTrap  NOTIFICATION-TYPE
	OBJECTS { aS3ExceededPowerStatus,
		eventTrapLogId,
		eventTimeStamp,
		eventInitialStatus,
		eventFinalStatus,
		eventAdditionalText,
	 	redundancyId }
	STATUS     current
	DESCRIPTION
		"Amplifier Stage 3 Exceeded Power trap"
	::= { eventsTx 128 }

aS3DecreasedPowerTrap  NOTIFICATION-TYPE
	OBJECTS { aS3DecreasedPowerStatus,
		eventTrapLogId,
		eventTimeStamp,
		eventInitialStatus,
		eventFinalStatus,
		eventAdditionalText,
	 	redundancyId }
	STATUS     current
	DESCRIPTION
		"Amplifier Stage 3 Decreased Power trap"
	::= { eventsTx 129 }

aS3ReflectedPowerTrap  NOTIFICATION-TYPE
	OBJECTS { aS3ReflectedPowerStatus,
		eventTrapLogId,
		eventTimeStamp,
		eventInitialStatus,
		eventFinalStatus,
		eventAdditionalText,
	 	redundancyId }
	STATUS     current
	DESCRIPTION
		"Amplifier Stage 3 Reflected Power trap"
	::= { eventsTx 130 }

aS3TemperatureTrap  NOTIFICATION-TYPE
	OBJECTS { aS3TemperatureStatus,
		eventTrapLogId,
		eventTimeStamp,
		eventInitialStatus,
		eventFinalStatus,
		eventAdditionalText,
	 	redundancyId }
	STATUS     current
	DESCRIPTION
		"Amplifier Stage 3 Temperature trap"
	::= { eventsTx 131 }

aS3HwErrorTrap  NOTIFICATION-TYPE
	OBJECTS { aS3HwErrorStatus,
		eventTrapLogId,
		eventTimeStamp,
		eventInitialStatus,
		eventFinalStatus,
		eventAdditionalText,
	 	redundancyId }
	STATUS     current
	DESCRIPTION
		"Amplifier Stage 3 HW error trap"
	::= { eventsTx 132 }

amplifierStage4SumTrap  NOTIFICATION-TYPE
	OBJECTS { amplifierStage4Status,
		eventTrapLogId,
		eventTimeStamp,
		eventInitialStatus,
		eventFinalStatus,
		eventAdditionalText,
	 	redundancyId }
	STATUS     current
	DESCRIPTION
		"Amplifier Stage 4 trap"
	::= { eventsTx 133 }

aS4InputLevelTrap  NOTIFICATION-TYPE
	OBJECTS { aS4InputLevelStatus,
		eventTrapLogId,
		eventTimeStamp,
		eventInitialStatus,
		eventFinalStatus,
		eventAdditionalText,
	 	redundancyId }
	STATUS     current
	DESCRIPTION
		"Amplifier Stage 4 Input Level trap"
	::= { eventsTx 134 }

aS4ExceededPowerTrap  NOTIFICATION-TYPE
	OBJECTS { aS4ExceededPowerStatus,
		eventTrapLogId,
		eventTimeStamp,
		eventInitialStatus,
		eventFinalStatus,
		eventAdditionalText,
	 	redundancyId }
	STATUS     current
	DESCRIPTION
		"Amplifier Stage 4 Exceeded Power trap"
	::= { eventsTx 135 }

aS4DecreasedPowerTrap  NOTIFICATION-TYPE
	OBJECTS { aS4DecreasedPowerStatus,
		eventTrapLogId,
		eventTimeStamp,
		eventInitialStatus,
		eventFinalStatus,
		eventAdditionalText,
	 	redundancyId }
	STATUS     current
	DESCRIPTION
		"Amplifier Stage 4 Decreased Power trap"
	::= { eventsTx 136 }

aS4ReflectedPowerTrap  NOTIFICATION-TYPE
	OBJECTS { aS4ReflectedPowerStatus,
		eventTrapLogId,
		eventTimeStamp,
		eventInitialStatus,
		eventFinalStatus,
		eventAdditionalText,
	 	redundancyId }
	STATUS     current
	DESCRIPTION
		"Amplifier Stage 4 Reflected Power trap"
	::= { eventsTx 137 }

aS4TemperatureTrap  NOTIFICATION-TYPE
	OBJECTS { aS4TemperatureStatus,
		eventTrapLogId,
		eventTimeStamp,
		eventInitialStatus,
		eventFinalStatus,
		eventAdditionalText,
	 	redundancyId }
	STATUS     current
	DESCRIPTION
		"Amplifier Stage 4 Temperature trap"
	::= { eventsTx 138 }

aS4HwErrorTrap  NOTIFICATION-TYPE
	OBJECTS { aS4HwErrorStatus,
		eventTrapLogId,
		eventTimeStamp,
		eventInitialStatus,
		eventFinalStatus,
		eventAdditionalText,
	 	redundancyId }
	STATUS     current
	DESCRIPTION
		"Amplifier Stage 4 HW error trap"
	::= { eventsTx 139 }

aS1PsusErrorTrap  NOTIFICATION-TYPE
	OBJECTS { aS1PsusErrorStatus,
		eventTrapLogId,
		eventTimeStamp,
		eventInitialStatus,
		eventFinalStatus,
		eventAdditionalText,
	 	redundancyId }
	STATUS     current
	DESCRIPTION
		"Amplifier Stage 1 PSUs error trap"
	::= { eventsTx 145 }

aS2PsusErrorTrap  NOTIFICATION-TYPE
	OBJECTS { aS2PsusErrorStatus,
		eventTrapLogId,
		eventTimeStamp,
		eventInitialStatus,
		eventFinalStatus,
		eventAdditionalText,
	 	redundancyId }
	STATUS     current
	DESCRIPTION
		"Amplifier Stage 2 PSUs error trap"
	::= { eventsTx 146 }

aS3PsusErrorTrap  NOTIFICATION-TYPE
	OBJECTS { aS3PsusErrorStatus,
		eventTrapLogId,
		eventTimeStamp,
		eventInitialStatus,
		eventFinalStatus,
		eventAdditionalText,
	 	redundancyId }
	STATUS     current
	DESCRIPTION
		"Amplifier Stage 3 PSUs error trap"
	::= { eventsTx 147 }

aS4PsusErrorTrap  NOTIFICATION-TYPE
	OBJECTS { aS4PsusErrorStatus,
		eventTrapLogId,
		eventTimeStamp,
		eventInitialStatus,
		eventFinalStatus,
		eventAdditionalText,
	 	redundancyId }
	STATUS     current
	DESCRIPTION
		"Amplifier Stage 4 PSUs error trap"
	::= { eventsTx 148 }

-- Amplifiers >4

amplifierStagesSumTrap  NOTIFICATION-TYPE
	OBJECTS { amplifierStagesStatus,
		eventTrapLogId,
		eventTimeStamp,
		eventInitialStatus,
		eventFinalStatus,
		eventAdditionalText,
	 	redundancyId }
	STATUS     current
	DESCRIPTION
		"Amplifier Stages trap"
	::= { eventsTx 175 }

aSsInputLevelTrap  NOTIFICATION-TYPE
	OBJECTS { aSsInputLevelStatus,
		eventTrapLogId,
		eventTimeStamp,
		eventInitialStatus,
		eventFinalStatus,
		eventAdditionalText,
	 	redundancyId }
	STATUS     current
	DESCRIPTION
		"Amplifier Stages Input Level trap"
	::= { eventsTx 176 }

aSsExceededPowerTrap  NOTIFICATION-TYPE
	OBJECTS { aSsExceededPowerStatus,
		eventTrapLogId,
		eventTimeStamp,
		eventInitialStatus,
		eventFinalStatus,
		eventAdditionalText,
	 	redundancyId }
	STATUS     current
	DESCRIPTION
		"Amplifier Stages Exceeded Power trap"
	::= { eventsTx 177 }

aSsDecreasedPowerTrap  NOTIFICATION-TYPE
	OBJECTS { aSsDecreasedPowerStatus,
		eventTrapLogId,
		eventTimeStamp,
		eventInitialStatus,
		eventFinalStatus,
		eventAdditionalText,
	 	redundancyId }
	STATUS     current
	DESCRIPTION
		"Amplifier Stages Decreased Power trap"
	::= { eventsTx 178 }

aSsReflectedPowerTrap  NOTIFICATION-TYPE
	OBJECTS { aSsReflectedPowerStatus,
		eventTrapLogId,
		eventTimeStamp,
		eventInitialStatus,
		eventFinalStatus,
		eventAdditionalText,
	 	redundancyId }
	STATUS     current
	DESCRIPTION
		"Amplifier Stages  Reflected Power trap"
	::= { eventsTx 179 }

aSsTemperatureTrap  NOTIFICATION-TYPE
	OBJECTS { aSsTemperatureStatus,
		eventTrapLogId,
		eventTimeStamp,
		eventInitialStatus,
		eventFinalStatus,
		eventAdditionalText,
	 	redundancyId }
	STATUS     current
	DESCRIPTION
		"Amplifier Stages Temperature trap"
	::= { eventsTx 180 }

aSsHwErrorTrap  NOTIFICATION-TYPE
	OBJECTS { aSsHwErrorStatus,
		eventTrapLogId,
		eventTimeStamp,
		eventInitialStatus,
		eventFinalStatus,
		eventAdditionalText,
	 	redundancyId }
	STATUS     current
	DESCRIPTION
		"Amplifier Stages HW error trap"
	::= { eventsTx 181 }

aSsPsusErrorTrap  NOTIFICATION-TYPE
	OBJECTS { aSsPsusErrorStatus,
		eventTrapLogId,
		eventTimeStamp,
		eventInitialStatus,
		eventFinalStatus,
		eventAdditionalText,
	 	redundancyId }
	STATUS     current
	DESCRIPTION
		"Amplifier Stages PSUs error trap"
	::= { eventsTx 182 }

decreasedOuputPowerNonCritTrap  NOTIFICATION-TYPE
	OBJECTS { decreasedOutputPowerNonCritical,
		eventTrapLogId,
		eventTimeStamp,
		eventInitialStatus,
		eventFinalStatus,
		eventAdditionalText,
	 	redundancyId }
	STATUS     current
	DESCRIPTION
		"Decreased Output Power Non-critical trap"
	::= { eventsTx 149 }

lockingStart1ppsEventTrap  NOTIFICATION-TYPE
	OBJECTS { eventTrapLogId,
		eventTimeStamp,
		eventAdditionalText,
	 	redundancyId }
	STATUS     current
	DESCRIPTION
		"1PPS locking restart"
	::= { eventsTx 150 }

rackCoolingEventTrap  NOTIFICATION-TYPE
	OBJECTS { rackCoolingStatus,
		eventTrapLogId,
		eventTimeStamp,
		eventInitialStatus,
		eventFinalStatus,
		eventAdditionalText,
	 	redundancyId }
	STATUS     current
	DESCRIPTION
		"Rack cooling status trap"
	::= { eventsTx 152 }

rackCoolingTemperatureEventTrap  NOTIFICATION-TYPE
	OBJECTS { rackCoolingTemperatureStatus,
		eventTrapLogId,
		eventTimeStamp,
		eventInitialStatus,
		eventFinalStatus,
		eventAdditionalText,
	 	redundancyId }
	STATUS     current
	DESCRIPTION
		"Rack cooling temperature trap"
	::= { eventsTx 153 }

rackCPressureDifferenceTrap  NOTIFICATION-TYPE
	OBJECTS { pressureDifferenceStatus,
		eventTrapLogId,
		eventTimeStamp,
		eventInitialStatus,
		eventFinalStatus,
		eventAdditionalText,
	 	redundancyId }
	STATUS     current
	DESCRIPTION
		"Rack cooling pressure difference trap"
	::= { eventsTx 154 }

rackCoolingHwErrorEventTrap  NOTIFICATION-TYPE
	OBJECTS { rackCoolingHwErrorStatus,
		eventTrapLogId,
		eventTimeStamp,
		eventInitialStatus,
		eventFinalStatus,
		eventAdditionalText,
	 	redundancyId }
	STATUS     current
	DESCRIPTION
		"Rack cooling HW error trap"
	::= { eventsTx 155 }

ioInterfaceInputEventTrap  NOTIFICATION-TYPE
	OBJECTS { eventTrapLogId,
		eventTimeStamp,
		eventInitialStatus,
		eventFinalStatus,
		eventAdditionalText,
	 	redundancyId }
	STATUS     current
	DESCRIPTION
		"I/O Interface: Input trap"
	::= { eventsTx 156 }

ioInterfaceOutputEventTrap  NOTIFICATION-TYPE
	OBJECTS { eventTrapLogId,
		eventTimeStamp,
		eventInitialStatus,
		eventFinalStatus,
		eventAdditionalText,
	 	redundancyId }
	STATUS     current
	DESCRIPTION
		"I/O Interface: Output trap"
	::= { eventsTx 157 }

dcInputEventTrap  NOTIFICATION-TYPE
	OBJECTS { dcInputStatus,
		eventTrapLogId,
		eventTimeStamp,
		eventInitialStatus,
		eventFinalStatus,
		eventAdditionalText,
	 	redundancyId }
	STATUS     current
	DESCRIPTION
		"DC input trap"
	::= { eventsTx 158 }

externalDcPowerSupplyEventTrap  NOTIFICATION-TYPE
	OBJECTS { rackCoolingHwErrorStatus,
		eventTrapLogId,
		eventTimeStamp,
		eventInitialStatus,
		eventFinalStatus,
		eventAdditionalText,
	 	redundancyId }
	STATUS     current
	DESCRIPTION
		"External DC power supply trap"
	::= { eventsTx 159 }

redundancySysEventTrap  NOTIFICATION-TYPE
	OBJECTS { redundancySysStatus,
		eventTrapLogId,
		eventTimeStamp,
		eventInitialStatus,
		eventFinalStatus,
		eventAdditionalText,
	 	redundancyId }
	STATUS     current
	DESCRIPTION
		"Redundancy System trap"
	::= { eventsTx 160 }

redundancySysComEventTrap  NOTIFICATION-TYPE
	OBJECTS { redundancySysCommunicationStatus,
		eventTrapLogId,
		eventTimeStamp,
		eventInitialStatus,
		eventFinalStatus,
		eventAdditionalText,
	 	redundancyId }
	STATUS     current
	DESCRIPTION
		"Redundancy System Commuication Error trap"
	::= { eventsTx 161 }

redundancySysSwitchEventTrap  NOTIFICATION-TYPE
	OBJECTS { redundancySysSwitchStatus,
		eventTrapLogId,
		eventTimeStamp,
		eventInitialStatus,
		eventFinalStatus,
		eventAdditionalText,
	 	redundancyId }
	STATUS     current
	DESCRIPTION
		"Redundancy System Switch Error trap"
	::= { eventsTx 162 }

redundancySysReserveEventTrap  NOTIFICATION-TYPE
	OBJECTS { redundancySysReserveStatus,
		eventTrapLogId,
		eventTimeStamp,
		eventInitialStatus,
		eventFinalStatus,
		eventAdditionalText,
	 	redundancyId }
	STATUS     current
	DESCRIPTION
		"Redundancy System Reserve Ready trap"
	::= { eventsTx 163 }

redundancyInputAsiMatrixTrap  NOTIFICATION-TYPE
	OBJECTS { redundancyInputAsiMatrixStatus,
		eventTrapLogId,
		eventTimeStamp,
		eventInitialStatus,
		eventFinalStatus,
		eventAdditionalText,
	 	redundancyId }
	STATUS     current
	DESCRIPTION
		"Inputs ASI matrix trap"
	::= { eventsTx 165 }

redundancyHwMatrixEventTrap  NOTIFICATION-TYPE
	OBJECTS { redundancyHwMatrixStatus,
		eventTrapLogId,
		eventTimeStamp,
		eventInitialStatus,
		eventFinalStatus,
		eventAdditionalText,
	 	redundancyId }
	STATUS     current
	DESCRIPTION
		"HW error ASI matrix trap"
	::= { eventsTx 166 }
  
inputDabErrorStatusEventTrap  NOTIFICATION-TYPE
	OBJECTS { inputDabErrorStatus,
		eventTrapLogId,
		eventTimeStamp,
		eventInitialStatus,
		eventFinalStatus,
		eventAdditionalText,
	 	redundancyId }
	STATUS     current
	DESCRIPTION
		"Input DAB error trap"
	::= { eventsTx 167 }

etiInputTrap  NOTIFICATION-TYPE
	OBJECTS { etiInputStatus,
		eventTrapLogId,
		eventTimeStamp,
		eventInitialStatus,
		eventFinalStatus,
		eventAdditionalText,
	 	redundancyId }
	STATUS     current
	DESCRIPTION
		"ETI input trap "
	::= { eventsTx 168 }

eti1ErrorTrap  NOTIFICATION-TYPE
	OBJECTS { eti1ErrorStatus,
		eventTrapLogId,
		eventTimeStamp,
		eventInitialStatus,
		eventFinalStatus,
		eventAdditionalText,
	 	redundancyId }
	STATUS     current
	DESCRIPTION
		"ETI 1 error trap"
	::= { eventsTx 169 }

camSatReceiver1Trap  NOTIFICATION-TYPE
	OBJECTS { camSatReceiver1Status,
		eventTrapLogId,
		eventTimeStamp,
		eventInitialStatus,
		eventFinalStatus,
		eventAdditionalText,
	 	redundancyId }
	STATUS     current
	DESCRIPTION
		"CAM satellity receiver 1 trap "
	::= { eventsTx 170 }

smartCardSatReceiver1Trap  NOTIFICATION-TYPE
	OBJECTS { smartCardSatReceiver1Status,
		eventTrapLogId,
		eventTimeStamp,
		eventInitialStatus,
		eventFinalStatus,
		eventAdditionalText,
	 	redundancyId }
	STATUS     current
	DESCRIPTION
		"Smart card satellity receiver 1 trap "
	::= { eventsTx 171 }

smartCardRightsSatReceiver1Trap  NOTIFICATION-TYPE
	OBJECTS { smartCardRightsSatReceiver1Stat,
		eventTrapLogId,
		eventTimeStamp,
		eventInitialStatus,
		eventFinalStatus,
		eventAdditionalText,
	 	redundancyId }
	STATUS     current
	DESCRIPTION
		"Smart card rights satellity receiver 1 trap "
	::= { eventsTx 172 }

asiOutputSatReceiver1Trap  NOTIFICATION-TYPE
	OBJECTS { asiOutputSatReceiver1Status,
		eventTrapLogId,
		eventTimeStamp,
		eventInitialStatus,
		eventFinalStatus,
		eventAdditionalText,
	 	redundancyId }
	STATUS     current
	DESCRIPTION
		"ASI output satellity receiver 1 trap "
	::= { eventsTx 173 }

redundancyHwRfMatrixEventTrap  NOTIFICATION-TYPE
	OBJECTS { redundancyHwRfMatrixStatus,
		eventTrapLogId,
		eventTimeStamp,
		eventInitialStatus,
		eventFinalStatus,
		eventAdditionalText,
	 	redundancyId }
	STATUS     current
	DESCRIPTION
		"HW error RF matrix trap"
	::= { eventsTx 174 }

redundancyInputEtiMatrixTrap  NOTIFICATION-TYPE
	OBJECTS { redundancyInputAsiMatrixStatus,
		eventTrapLogId,
		eventTimeStamp,
		eventInitialStatus,
		eventFinalStatus,
		eventAdditionalText,
	 	redundancyId }
	STATUS     current
	DESCRIPTION
		"Inputs ETI matrix trap"
	::= { eventsTx 183 }

redundancyHwEtiMatrixEventTrap  NOTIFICATION-TYPE
	OBJECTS { redundancyHwEtiMatrixStatus,
		eventTrapLogId,
		eventTimeStamp,
		eventInitialStatus,
		eventFinalStatus,
		eventAdditionalText,
	 	redundancyId }
	STATUS     current
	DESCRIPTION
		"HW error ETI matrix trap"
	::= { eventsTx 184 }

shortTermMonitoringEventTrap  NOTIFICATION-TYPE
	OBJECTS { eventTrapLogId,
		eventTimeStamp,
		eventAdditionalText,
	 	redundancyId }
	STATUS     current
	DESCRIPTION
		"Short-term monitoring"
	::= { eventsTx 185 }

autoconfFromInputEventTrap  NOTIFICATION-TYPE
	OBJECTS { eventTrapLogId,
		eventTimeStamp,
		eventAdditionalText,
	 	redundancyId }
	STATUS     current
	DESCRIPTION
		"Autoconfiguration from input"
	::= { eventsTx 186 }

channelAdaptationEventTrap  NOTIFICATION-TYPE
	OBJECTS { eventTrapLogId,
		eventTimeStamp,
		eventAdditionalText,
	 	redundancyId }
	STATUS     current
	DESCRIPTION
		"Channel adaptation"
	::= { eventsTx 187 }

dttReceiver1BerMuteTrap  NOTIFICATION-TYPE
	OBJECTS { eventTrapLogId,
		eventTimeStamp,
		eventAdditionalText,
	 	redundancyId }
	STATUS     current
	DESCRIPTION
		"DTT receiver 1: BER mute"
	::= { eventsTx 188 }

dttReceiver2BerMuteTrap  NOTIFICATION-TYPE
	OBJECTS { eventTrapLogId,
		eventTimeStamp,
		eventAdditionalText,
	 	redundancyId }
	STATUS     current
	DESCRIPTION
		"DTT receiver 2: BER mute"
	::= { eventsTx 189 }

automaticPowerCompensationTrap  NOTIFICATION-TYPE
	OBJECTS { eventTrapLogId,
		eventTimeStamp,
		eventAdditionalText,
	 	redundancyId }
	STATUS     current
	DESCRIPTION
		"Automatic power compensation"
	::= { eventsTx 190 }

eti2ErrorTrap  NOTIFICATION-TYPE
	OBJECTS { eti2ErrorStatus,
		eventTrapLogId,
		eventTimeStamp,
		eventInitialStatus,
		eventFinalStatus,
		eventAdditionalText,
	 	redundancyId }
	STATUS     current
	DESCRIPTION
		"ETI 2 error trap"
	::= { eventsTx 191 }

testTrap  NOTIFICATION-TYPE
	OBJECTS { localTime,
		name,
	 	redundancyId }
	STATUS     current
	DESCRIPTION
		"Test trap "
	::= { eventsTx 500 }

keepaliveTrap  NOTIFICATION-TYPE
	OBJECTS { localTime,
		name,
	 	redundancyId }
	STATUS     current
	DESCRIPTION
		"Keepalive trap "
	::= { eventsTx 501 }

eventTrapLogId  OBJECT-TYPE
	SYNTAX     Unsigned32 (1..256)
	MAX-ACCESS accessible-for-notify
	STATUS     current
	DESCRIPTION
		"Event log ID"
	::= { eventContent 1 }

eventTimeStamp  OBJECT-TYPE
	SYNTAX     DisplayString
	MAX-ACCESS accessible-for-notify
	STATUS     current
	DESCRIPTION
		"Event time stamp "
	::= { eventContent 2 }

eventInitialStatus  OBJECT-TYPE
	SYNTAX     EventStatus
	MAX-ACCESS accessible-for-notify
	STATUS     current
	DESCRIPTION
		"Event initial status "
	::= { eventContent 3 }

eventFinalStatus  OBJECT-TYPE
	SYNTAX     EventStatus
	MAX-ACCESS accessible-for-notify
	STATUS     current
	DESCRIPTION
		"Event final status "
	::= { eventContent 4 }

eventAdditionalText  OBJECT-TYPE
	SYNTAX     DisplayString
	MAX-ACCESS accessible-for-notify
	STATUS     current
	DESCRIPTION
		"Event additional text "
	::= { eventContent 5 }

redundancyId  OBJECT-TYPE
	SYNTAX     INTEGER {
		notRedundancy (0),
		deviceA (1),
		deviceB (2),
		deviceNp1B (3),
		deviceNp1A1 (4),
		deviceNp1A2 (5),
		deviceNp1A3 (6),
		deviceNp1A4 (7),
		deviceNp1A5 (8),
		deviceNp1A6 (9),
		deviceNp1A7 (10),
		deviceNp1A8 (11),
		deviceNp1A9 (12),
		deviceNp1A10 (13),
		deviceNp1A11 (14)
	}
	MAX-ACCESS accessible-for-notify
	STATUS     current
	DESCRIPTION
		"Redundancy ID. Information for redundancy systems. The sender is A (1) or B (2); otherwise will be without redundancy (0)."
	::= { eventContent 6 }

-- oidTest  OBJECT-TYPE
-- 	SYNTAX     Integer32
-- 	MAX-ACCESS read-write
-- 	STATUS     current
-- 	DESCRIPTION
-- 		"OID for testting uses "
-- 	::= { testBranch 1 }

groupFS  OBJECT-GROUP
	OBJECTS { actualPassword,
		adminUserPassword,
		amplifier1p1,
		amplifierAlarmName,
		amplifierExt1,
		amplifierExt2,
		amplifierTrap,
		amplifierFault,
		amplifierLed,
		amplifierLog,
		amplifierOn,
		amplifierStageTemperature,
		amplifierStatus,
		amplifierWarning,
		amplifierStage1AlarmName,
		amplifierStage1AlarmStatus,
		amplifierStage1On,
		amplifierStage1Log,
		amplifierStage1Fault,
		amplifierStage1Warning,
		amplifierStage1Led,
		amplifierStage11p1,
		amplifierStage1Ext1,
		amplifierStage1Ext2,
		amplifierStage1Trap,
		amplifierStage2AlarmName,
		amplifierStage2AlarmStatus,
		amplifierStage2On,
		amplifierStage2Log,
		amplifierStage2Fault,
		amplifierStage2Warning,
		amplifierStage2Led,
		amplifierStage21p1,
		amplifierStage2Ext1,
		amplifierStage2Ext2,
		amplifierStage2Trap,
		amplifierStage3AlarmName,
		amplifierStage3AlarmStatus,
		amplifierStage3On,
		amplifierStage3Log,
		amplifierStage3Fault,
		amplifierStage3Warning,
		amplifierStage3Led,
		amplifierStage31p1,
		amplifierStage3Ext1,
		amplifierStage3Ext2,
		amplifierStage3Trap,
		amplifierStage4AlarmName,
		amplifierStage4AlarmStatus,
		amplifierStage4On,
		amplifierStage4Log,
		amplifierStage4Fault,
		amplifierStage4Warning,
		amplifierStage4Led,
		amplifierStage41p1,
		amplifierStage4Ext1,
		amplifierStage4Ext2,
		amplifierStage4Trap,
		amplifierStagesAlarmName,
		amplifierStagesAlarmStatus,
		amplifierStagesOn,
		amplifierStagesLog,
		amplifierStagesFault,
		amplifierStagesWarning,
		amplifierStagesLed,
		amplifierStages1p1,
		amplifierStagesExt1,
		amplifierStagesExt2,
		amplifierStagesTrap,
		autorefreshWebConfig,
		asi1ErrorStatus,
		asi1p1,
		asi2ErrorStatus,
		asiAlarmName,
		asiAlarmStatus,
		asiExt1,
		asiExt2,
		asiTrap,
		asiFault,
		asiLed,
		asiLog,
		asiOn,
		autorefreshWebTime,
		outputCentralFrequency,
		outputCentralFrequencyMHz,
		confirmNewPassword,
		connectedWebUsers,
		asiInputStatus,
		asiWarning,
		btsErrorStatus,
		codeRate,
		outputChannelOffset,
		ouputChannelResolution,
		dabOutputChannel,
		configuredPower,
		powerDisplaOffset,
		-- modClippingEnable,
		-- modClippingPapr,
		dateTime1,
		-- modClippingValue,
		dateTime2,
		dateTimeSource,
		dateTimeStatus,
		dcLine1Voltage,
		dcLine2Voltage,
		dcLine3Voltage,
		dcLine4Voltage,
		dcInVoltage,
		dhcp,
		exceededPowerThreshold,
		enableAuthenTraps,
		--endOfVerificationStatus,
		--configurationFromBackup,
		--restoreFromBackup,
		--errorConfigurationFromBackup,
		--errorRestoringFromBackup,
		--systemShutdown,
		--systemDateAndTimeSrc,
		dcInputStatus,
		redundancySysStatus,
		redundancySysCommunicationStatus,
		redundancySysSwitchStatus,
		redundancySysReserveStatus,
		redundancyInputAsiMatrixStatus,
		redundancyHwMatrixStatus,
		redundancyHwRfMatrixStatus,
		redundancyInputEtiMatrixStatus,
		redundancyHwEtiMatrixStatus,
		errorHw1p1,
		-- dvbt1ppsActiveEdge,
		-- dvbt21ppsActiveEdge,
		errorHwAlarmName,
		dvbt2Bandwidth,
		dvbt2CellIdOverwrite,
		errorHwAlarmStatus,
		dvbt2ExtendedCarrierMode,
		dvbt2FftSize,
		dvbt2FramesPerSuperframe,
		dvbt2CellIdUser,
		dvbt2CellIdT2mi,
		errorHwExt1,
		dvbt2GuardInterval,
		errorHwExt2,
		errorHwTrap,
		dvbt2FrequencyOverwrite,
		errorHwFault,
		dvbt2TimeOffset,
		dvbt2FrequencyT2mi,
		dvbt2InputBufferDelay,
		dvbt2ProcessingDelay,
		dvbt2L1SignallingModulation,
		errorHwLed,
		errorHwLog,
		dvbt2Delay,
		dvbt2MisoGroup,
		dvbt2OfdmSymbolsPerSuperframe,
		errorHwOn,
		errorHwWarning,
		dvbt2PaprReduction,
		dvbt2PilotPattern,
		dvbt2NetworkDelayMargin,
		dvbt2LocalDelay,
		dvbt2BufferDuration,
		input10MhzStatus,
		external1p1,
		externalAlarmName,
		powerSupplyAlarmName,
		powerSupplyAlarmStatus,
		powerSupplyOn,
		powerSupplyLog,
		powerSupplyFault,
		powerSupplyWarning,
		powerSupplyLed,
		powerSupply1p1,
		powerSupplyExt1,
		powerSupplyExt2,
		powerSupplyTrap,
		dvbt2PreambleFormat,
		dvbt2L1PostScrambling,
		dvbt2LiteCompatible,
		dvbt2InputMode,
		externalAlarmStatus,
		dvbt2NetworkType,
		dvbt2SuperFrameDuration,
		externalExt1,
		dvbt2NetworkIdUser,
		dvbt2NetworkIdT2mi,
		dvbt2NetworkIdOverwrite,
		externalExt2,
		externalTrap,
		fan1p1,
		dvbt2TransmitterId,
		fastTrapSync,
		faultSummationStatus,
		gbe1,
		gbe2,
		dvbt2SystemIdOverwrite,
		dvbt2SfnRelativeReference,
		dvbt2SfnAbsoluteReference,
		dvbt2TimeStamp,
		gbe3,
		dvbt2SystemIdUser,
		dvbt2SystemIdT2mi,
		gbe4,
		--ethernetMode,
		--networkGbe1,
		--networkGbe2,
		--networkGbe3,
		--networkGbe4,
		--ifaceGbe1,
		--ifaceGbe2,
		--ifaceGbe3,
		--ifaceGbe4,
		gbe1LinkConfiguration,
		gbe2LinkConfiguration,
		gbe3LinkConfiguration,
		gbe4LinkConfiguration,
		external1Status,
		external2Status,
		acPowerSupplyStatus,
		acPsuAStatus,
		acPsuBStatus,
		amplifierStage1Status,
		aS1InputLevelStatus,
		aS1ExceededPowerStatus,
		aS1DecreasedPowerStatus,
		aS1ReflectedPowerStatus,
		aS1TemperatureStatus,
		aS1HwErrorStatus,
		aS1PsusErrorStatus,
		amplifierStage2Status,
		aS2InputLevelStatus,
		aS2ExceededPowerStatus,
		aS2DecreasedPowerStatus,
		aS2ReflectedPowerStatus,
		aS2TemperatureStatus,
		aS2HwErrorStatus,
		aS2PsusErrorStatus,
		amplifierStage3Status,
		aS3InputLevelStatus,
		aS3ExceededPowerStatus,
		aS3DecreasedPowerStatus,
		aS3ReflectedPowerStatus,
		aS3TemperatureStatus,
		aS3HwErrorStatus,
		aS3PsusErrorStatus,
		amplifierStage4Status,
		aS4InputLevelStatus,
		aS4ExceededPowerStatus,
		aS4DecreasedPowerStatus,
		aS4ReflectedPowerStatus,
		aS4TemperatureStatus,
		aS4HwErrorStatus,
		aS4PsusErrorStatus,
		amplifierStagesStatus,
		aSsInputLevelStatus,
		aSsExceededPowerStatus,
		aSsDecreasedPowerStatus,
		aSsReflectedPowerStatus,
		aSsTemperatureStatus,
		aSsHwErrorStatus,
		aSsPsusErrorStatus,
		externalFault,
		externalLed,
		dvbt2Profile,
		externalLog,
		externalOn,
		externalWarning,
		dvbt2T2miPid,
		fan01OperatingTime,
		fan01Reset,
		dvbt2Version,
		fan01Status,
		fan02OperatingTime,
		fanAlarmName,
		fanAlarmStatus,
		utcOffset,
		dvbtAutoconfigurationMip,
		--forcedMfnStatus,
		fan1Status,
		dvbtBandwidth,
		dvbtConstellation,
		dvbtCellId,
		dvbtFec,
		dvbtGuardInterval,
		ecAdditionDelay,
		ecCurrentDelay,
		ecBandwidth,
		ecBandwidthAdaptation,
		ecReferenceLevel,
		ecShoulderAlarm,
		ecLowerShoulder,
		fanExt1,
		dvbtCellIdEnable,
		fanExt2,
		fanTrap,
		dvbtInputBufferDelay,
		dvbtCurrentNetworkDelay,
		dvbtProcessingDelay,
		dvbtNetworkDelayMargin,
		dvbtDelay,
		ecCancellationLevel,
		fanFault,
		dvbtTransmitterId,
		dvbtTimeOffset,
		dvbtMaximumNetworkDelay,
		fanLed,
		fanLog,
		fanOn,
		dvbtNetworkType,
		ecInBandLevelVariation,
		ecNonLinearStoredPrecorrection,
		ecNonLinearPrecorrectorFeedback,
		ecInputLevel,
		fan02Reset,
		fan02Status,
		fan03OperatingTime,
		fan03Reset,
		fanSpeed,
		fan03Status,
		amStFanSpeed,
		amStFan1OperatingTime,
		amStFan2OperatingTime,
		amStFan1rpm,
		amStFan2rpm,
		rcTag,
		rcControlStatus,
		rcHwStatus,
		rcCoolingMode,
		rcFan1,
		rcFan2,
		rcTemperature,
		rcTemperatureTarget,
---		rcPressureDifference,
		rcFan1SpeedManual,
		rcFan2SpeedManual,
		rcFan1Speed,
		rcFan1Tachometer,
		rcFan1OperatingTime,
		rcFan1Reset,
		rcFan2Speed,
		rcFan2Tachometer,
		rcFan2OperatingTime,
		rcFan2Reset,
		rcIdentifyBoard,
		rcExternalSensor1,
		rcExternalSensor2,
		forwardPower,
		dvbtLocalDelay,
		dvbtBufferDuration,
		dvbtRetransmissionDelay,
		ecOutputCancellation,
		ecGainMargin,
		-- ecMode,
		ecEnable,
		ecWindow01,
		ecWindow02,
		ecWindow03,
		ecWindow04,
		ecWindow05,
		ecWindow06,
		ecWindow07,
		ecWindow08,
		ecWindow09,
		ecWindow10,
		ecWindow11,
		ecWindow12,
		ecWindow13,
		ecWindow14,
		ecWindow15,
		ecWindow16,
		ecUnmuteRetriesInterval,
		ecLinearPrecorrection,
		ecNonLinearPrecorrection,
		ecSlopeCorrection,
		ecPrecorrectorFeedback,
		ecPrecorrectorInput,
		ecPrecorrectorOutput,
		ecPrecorrectorStatus,
		ecTemperature,
		ecUpperShoulder,
		modThresholdMer,
		modMer,
		modMerFlt, 
		modBerFlt,
		modShoulderAlarm,
		eventLog,
		eventTrap,
		eventName,
		eventOn,
		fecType,
		geral1p1,
		geralAlarmName,
		geralAlarmStatus,
		language,
		location,
		operationMode,
		autoreturnToRemote,
		externalStatus,
		fanWarning,
		geralExt1,
		geralExt2,
		geralTrap,
		geralFault,
		geralLed,
		input01StandByStatus,
		isdbtBitrateLB,
		isdbtBerLB,
		geralLog,
		input01Description,
		input01Duration,
		input01Mode,
		isdbtBtsRateLock,
		isdbtCasBiss,
		isdbtCasMode,
		isdbtCasPass,
		isdbtCasInjectId,
		isdbtBtsDecompression,
		isdbtBtsIipPid,
		isdbtBtsAuxPid,
		isdbtBtsPidRemapping,
		isdbtBtsRestorePcr,
		isdbtBtsBypass,
		isdbtBtsVirtualChannel,
		isdbtBtsChannel,
		isdbtBtsAreaCode,
		isdbtBts188BInputLocked,
		isdbtBts204BOutputLocked,
		isdbtDeletePids,
		isdbtPidIn,
		isdbtPidOut,
		isdbtConstellationLB,
		isdbtPidsLB,
		geralOn,
		isdbtCurrentNetworkDelay,
		isdbtTimeIntervalLengthLB,
		geralWarning,
		synchronization1p1,
		synchronizationAlarmStatus,
		synchronizationLed,
		synchronizationOn,
		ldmosTransistor1Current,
		ldmosTransistor2Current,
		localIp,
		localNetmask,
		localMacAddr,
		localTime,
		synchronizationAntennaStatus,
		synchronizationHoldoverStatus,
		synchronizationHwErrorStatus,
		fan2Status,
		isdbtBitrateLC,
		isdbtBerLC,
		isdbtPidFiltering,
		isdbtServicesA,
		isdbtServicesB,
		isdbtServicesC,
		isdbtCountry,
		isdbtRegionId,
		isdbtAvailablePrograms,
		isdbtAffiliationId,
		isdbtNetworkId,
		isdbtNetworkName,
		isdbtTransportStreamId,
		isdbtOriginalNetworkId,
		isdbtAreaCode,
		isdbtOverwriteAreaCode,
		isdbtFrequency,
		isdbtOverwriteFrequency,
		isdbtRemoteControlIdKey,
		isdbtVirtualChannelBypass,
		isdbtOverwriteRemoteControlIdKey,
		isdbtTSName,
		fan3Status,
		isdbtCodeRateLC,
		isdbtPidsLC,
		dvbtFft,
		dvbtAutoconfigurationFromDttRcv,
		isdbtConstellationLC,
		isdbtCodeRateLB,
		isdbtInputBufferDelay,
		isdbtTimeOffset,
		latitude,
		ipInputLed,
		isdbtTransmitterId,
		isdbtMaximumNetworkDelay,
		ipInputOn,
		macAddr,
		dnsServer,
		synchronizationUnlockStatus,
		synchronizationModuleStatus,
		ipInput1p1,
		ipInputAlarmStatus,
		ipInputExt2,
		ipInputTrap,
		--localModeTimeoutStatus,
		name,
		fanStatus,
		synchronizationAlarmName,
		satellitesAntenna,
		input1pps,
		synchronizationDate,
		synchronizationExt1,
		synchronizationExt2,
		synchronizationTrap,
		synchronizationFault,
		synchronizationHoldover,
		synchronizationHoldoverThreshold,
		endlessHoldoverThresholdEnable,
		input10Mhz,
		antennaStatus,
		ppsStatus,
		synchronizationLog,
		longitude,
		altitude,
		satellite01Info,
		satellite02Info,
		satellite03Info,
		satellite04Info,
		satellite05Info,
		satellite06Info,
		satellite07Info,
		satellite08Info,
		synchronizationReady,
		synchronizationWarning,
		input1Priority,
		input1Status,
		input1Pat,
		input2Priority,
		input2Status,
		input2Pat,
		input3Priority,
		input3Status,
		input3Pat,
		input4Priority,
		dttReceiver1Enable,
		dttReceiver1Standard,
		dttReceiver1Bandwidth,
		dttReceiver1InputFrequencyMode,
		dttReceiver1PlpId,
		dttReceiver1BerMute, 
		dttReceiver1Channel,
		dttReceiver1ChannelOffset,
		dttReceiver1ChannelResolution,
		dttReceiver1Frequency,
		dttReceiver1StatusReceiver,
		dttReceiver1InputFrequency,
		dttReceiver1Constellation,
		dttReceiver1Fec,
		dttReceiver1GuardInterval,
		dttReceiver1Fft,
		dttReceiver1CellId,
		dttReceiver1Cber,
		dttReceiver1Vber,
		dttReceiver1T2Profile,
		dttReceiver1T2Version,
		dttReceiver1T2CellId,
		dttReceiver1T2NetworkId,
		dttReceiver1T2SystemId,
		dttRx1T2L1SignallingModulation,
		dttRx1T2L1PostScrambling,
		dttRx1T2PreambleFormat,
		dttRx1T2ExtendedCarrierMode,
		dttRx1T2FftSize,
		dttRx1T2GuardInterval,
		dttRx1T2PaprReduction,
		dttRx1T2PilotPattern,
		dttRx1T2FramesPerSuperframe,
		dttRx1T2OfdmSymbolsPerSuperframe,
		dttRx1NumberOfPlps,
		dttRx1PlpId,
		dttRx1T2PlpType,
		dttRx1T2PlpMode,
		dttRx1T2PlpGroupId,
		dttRx1T2PlpConstellation,
		dttRx1T2PlpRotatedConstellation,
		dttRx1T2FecType,
		dttRx1T2CodeRate,
		dttRx1T2NumberOfFecBlocks,
		dttRx1T2TypeOfTimeInvervaling,
		dttRx1T2LengthOfTimeInvervaling,
		dttRx1T2InBandSignalling,
		dttRx1T2BerBeforeLdpc,
		dttRx1T2BerBeforeBch,
		dttRx1T2BbframeErrorRatio,
		dttRx1IsdbtSystem,
		dttRx1IsdbtMode,
		dttRx1IsdbtGuard,
		dttRx1IsdbtEws,
		dttRx1IsdbtPartialRx,
		dttRx1IsdbtLASegments,
		dttRx1IsdbtLAInterleaveLength,
		dttRx1IsdbtLAConstellation,
		dttRx1IsdbtLACodeRate,
		dttRx1IsdbtLACber,
		dttRx1IsdbtLABERbeforeRS,
		dttRx1IsdbtLBSegments,
		dttRx1IsdbtLBInterleaveLength,
		dttRx1IsdbtLBConstellation,
		dttRx1IsdbtLBCodeRate,
		dttRx1IsdbtLBCber,
		dttRx1IsdbtLBBERbeforeRS,
		dttRx1IsdbtLCSegments,
		dttRx1IsdbtLCInterleaveLength,
		dttRx1IsdbtLCConstellation,
		dttRx1IsdbtLCCodeRate,
		dttRx1IsdbtLCCber,
		dttRx1IsdbtLCBERbeforeRS,
		dttRx1Mer,
		dttRx1Snr,
		dttRx1Level,
		dstReceiver1Enable,
		dstReceiver1Status,
		dstReceiver1Temperature,
		dstReceiver1Band,
		dstReceiver1Frequency,
		dstReceiver1Polarization,
		dstReceiver1Satellite,
		dstReceiver1DvbMode,
		dstReceiver1SymbolRateMode,
		dstReceiver1ConfiguredSymbolRate,
		dstReceiver1MeasuredSymbolRate,
		dstReceiver1Rolloff,
		dstReceiver1Pilots,
		dstReceiver1FrameLength,
		dstReceiver1Modulation,
		dstReceiver1Fec,
		dstReceiver1PlsMode,
		dstReceiver1Pls,
		dstReceiver1Cber,
		dstReceiver1Vber,
		dstReceiver1Ldpc,
		dstReceiver1Per,
		dstReceiver1CN,
		--dstReceiver1Bch,
		dstReceiver1LinkMarginThreshold,
		dstReceiver1LinkMargin,
		dstReceiver1Attenuation,
		dstReceiver1Level,
		dstReceiver1Mode,
		dstReceiver1LnbStatus,
		dstReceiver1LnbOlLow,
		dstReceiver1LnbBandSwitchingFreq,
		dstReceiver1LnbOlHigh,
		dstReceiver1Voltage,
		dstReceiver1Tone22kHz,
		dstReceiver1OlManual,
		dstReceiver1TsAvailableIsis,
		dstReceiver1TsIsi,
		dstReceiver1TsRate,
		dstReceiver1TsMode,
		dstReceiver1TsBissEnable,
		dstReceiver1TsBissMode,
		dstReceiver1TsBissPass,
		dstReceiver1TsBissInjectId,
		dstReceiver1TsCamEnable,
		dstReceiver1TsCamStatus,
		dstReceiver1TsCamReset,
		dstDecryptEnable,
		dstProgramId,
		dstServiceName,
		dstServiceStatus,
		dstR1TsEtiOutputPid, 
		dstR1TsEtiOutputType, 
		dstR1TsEtiOutputStreamTo,
		dstR1TsEtiOutputLayer, 
		dstR1TsEtiOutputInputBitrate,
		dstR1TsEOCorrectedRsCodewords,
		dstR1TsEONotCorrectedRsCodewords,
		dstR1TsEtiOutputWithouService,
		dstR1TsEOResetCounters,
		inputChannel,
		inputChannelOffset,
		inputChannelResolution,
		inputChannelChannel,
		inputFrequency,
		inputFrequencyMode,
		inputCentralFrequency,
		inputCentralFrequencyMHz,
		inputLevel,
		inputLevelThreshold,
		inputFrequencyFlt, 
		modulatorInputOn,
		modulatorLog,
		muteMpegOverflow,
		muteSfnReference,
		modInBandLevelVariation,
		muteT2miError,
		newPassword,
		--guiOperationStatus,
		inBandSignalling,
		plpBer,
		input01Status,
		input02Description,
		input02Duration,
		input02Mode,
		input02StandByStatus,
		input02Status,
		input4Status,
		input4Pat,
		asi1Enable,
		asi2Enable,
		eti1Enable,
		eti1DetectedLayer,
		eti1InputBitrate,
		eti1CorrectedRSCodewords,
		eti1NotCorrectedRSCodewords,
		eti1TimeWithoutService,
		eti1RxStatisticsReset,
		eti2Enable,
		eti2DetectedLayer,
		eti2InputBitrate,
		eti2CorrectedRSCodewords,
		eti2NotCorrectedRSCodewords,
		eti2TimeWithoutService,
		eti2RxStatisticsReset,
		ipInputAlarmName,
		ldmosTransistor3Current,
		isdbtNumberOfSegmentsLC,
		ldmosTransistor4Current,
		amStControlStatus,
		amStHwStatus,
		amStMuteSelfProtection,
		amStForwardPower,
		amStReversePower,
		amStRfPhase,
		amStTemperature,
		amStCurrent1,
		amStCurrent2,
		amStCurrent3,
		amStCurrent4,
		amStCurrent5,
		amStCurrent6,
		amStReversePowerFlt,
		amStDcLineVoltage1,
		amStDcLineVoltage2,
		amStPsuAStatus,
		amStPsuBStatus,
		amStPsuCStatus,
		lengthOfTimeInvervaling,
		-- maximumLatency,
		asiBypassEqualizers,
		nonSeamlessHysteresis,
		higherPriorityHysteresis,
		muteCauses,
		muteOutputStatus,
		muteSfnMargin,
		muteGainMarginThreshold,
		muteGainMargin,
		muteErrorMip,
		tsErrorMuteHysteresis,
		muteCausesBinary,
		mute10MHz,
		mutesRf,
		isdbtNetworkDelayMargin,
		isdbtDelay,
		isdbtRfDelay,
		ntpRefresh,
		ntpServer,
		ntpClient,
		ntpServerStatus,
		ntpServerAlternative,
		timezone,
		output01Description,
		output01Duration,
		output01Mode,
		output01StandByStatus,
		output01Status,
		output02Description,
		output02Duration,
		output02Mode,
		output02StandByStatus,
		output02Status,
		outputFrequencyMode,
		publicUserPassword,
		r1p1AutoVDailyTime,
		r1p1AutoVDailyMode,
		r1p1AutoVDailyWindow,
		r1p1AutoVAlarmEnable,
		r1p1PriorityInversionEnable,
		r1p1PriorityInversionPeriod,
		r1p1PriorityInversionTime,
		r1p1Reset,
		r1p1SyncWeb,
		r1p1SyncDate,
		r1p1SyncSnmp,
		r1p1SyncEvents,
		r1p1SyncIO,
		r1p1SyncInput,
		r1p1SyncRfInput,
		r1p1SyncCanceller,
		r1p1SyncModulator,
		r1p1SyncRfConfiguration,
		r1p1SyncMutes,
		r1p1SyncAmplifier,
		r1p1SyncExternalAmplifier,
		r1p1SyncReference,
		r1p1AutoVMaxVerifications,
		r1p1AutoVNexVerification,
		r1p1AutoVPerformedVerifications,
		r1p1AutoVReiteratedEnable,
		r1p1EnableNCB,
		rPrDdSystemIp,
		rPrDdSwitchToAntenna,
		r1p1PriorityAB,
		r1p1AutoReturn,
		rPrDdDeviceIdentifier,
		rPrDdControlBusStatus,
		r1p1Mode,
		r1p1priorityNCB,
		r1p1StatusNCB,
		r1p1StatusWhenLoad,
		readCommunity1,
		readCommunity2,
		remoteGateway,
		remoteIp,
		remoteNetmask,
		rfOut1p1,
		isdbtBitrateLA,
		isdbtBerLA,
		rfOutAlarmStatus,
		isdbtCodeRateLA,
		rfOutExt1,
		isdbtConstellationLA,
		modLowerShoulder,
		rfOutExt2,
		rfOutTrap,
		isdbtFft,
		-- modLinearPrecorrectionAdaptative,
		-- isdbtFftWindowing,
		dabTransmitterId,
		dabMode,
		dabNetworkType,
		dabSynchronizationType,
		dabRelativeSfnReference,
		dabAbsoluteSfnReference,
		dabAvailableTimestampType,
		dabBufferingTime,
		dabProcessingDelay,
		dabMinimumProcessingDelay, 
		--dabAdditionalProcessingDelay,
		dabProcessingDelayCfg,
		-- dabCompensationDelayCfg,
		dabDynamicCompensationDelay,
		dabCompensationDelay,
		dabMargin,
		dabMaximumBitrateOffset,
		dabBitrateOffset,
		dabTimestampLevel,
		dabTistFct,
		dabFct0AsReference,
		dabLocalDelay,
		dabOffsetDelayAutoconfigure,
		dabTiiCodeConfiguration,
		dabMainId,
		dabSubId,
		dabReceivedInformationTime,
		dabDateAndTime,
		dabTimeAccurary,
		dabSynchronizationToFrame,
		dabReceivedTSC,
		dabSavedTSC,
		dabOffsetDelayTSC,
		dabMainIdTSC,
		dabSubIdTSC,
		dabControlFlagsTSC,
		--dabTotalDelay,
		dabStcNumberOfServices,
		dabStcSubChId,
		dabStcSubChSa,
		dabStcTpl,
		dabStcBitrate,
		modLinearPrecorrectionEnable,
		-- isdbtFftWindowRate,
		rfOutInputOn,
		isdbtNumberOfSegmentsLA,
		-- isdbt1ppsActiveEdge,
		-- modNonLinearPrecorrectionAdap,
		isdbtGuardInterval,
		modNonLinearPrecorrectionEnable,
		modNonLinearStoredPrecorrection,
		modNonLinearPrecorrectorFeedback,
		rfReset,
		isdbtPartialReception,
		modPrecorrectorFeedback,
		isdbtTimeIntervalLengthLA,
		modPrecorrectorOutput,
		modPrecorrectorInput,
		rxDtt11p1,
		modPrecorrectorStatus,
		isdbtBandwidth,
		rxDtt1AlarmStatus,
		rxDtt1Ext1,
		rxDtt1Ext2,
		rxDtt1Trap,
		rxDtt1InputOn,
		rxDtt1Log,
		rxDtt21p1,
		rxDtt2AlarmName,
		isdbtNetworkType,
		isdbtStaticDelay,
		isdbtInputMode,
		muteBtsError,
		rxDtt2AlarmStatus,
		rxDtt2Trap,
		rxDtt2InputOn,
		isdbtLocalDelay,
		isdbtBufferDuration,
		rxDtt2Log,
		rfInAlarmName,
		rfInAlarmStatus,
		rfInInputOn,
		rfInLog,
		rfInFault,
		rfInWarning,
		rfInLed,
		rfIn1p1,
		rfInExt1,
		rfInExt2,
		rfInTrap,
		cancellerAlarmName,
		cancellerAlarmStatus,
		cancellerInputOn,
		cancellerLog,
		cancellerFault,
		cancellerWarning,
		cancellerLed,
		canceller1p1,
		cancellerExt1,
		numberOfPlps,
		cancellerExt2,
		cancellerTrap,
		rxSat1Log,
		sendTestTrap,
		lastUpdate,
		ipInputStatus,
		ipSocket1ErrorStatus,
		ipSocket2ErrorStatus,
		rackCoolingStatus,
		rackCoolingTemperatureStatus,
		pressureDifferenceStatus,
		rackCoolingHwErrorStatus,
		hwErrorStatus,
		ipInputExt1,
		ipInputFault,
		ipInputLog,
		--inputSourceSelectedStatus,
		modulator1p1,
		modulatorAlarmName,
		modulatorAlarmStatus,
		r1p1AutoVReiteratedPeriod,
		r1p1Switchings,
		referenceSourceStatus,
		referenceSwitchMode,
		rfOutLed,
		rfOutLog,
		rxDtt1Led,
		rxDtt2Fault,
		rxDtt2Warning,
		rxSat1Fault,
		rxSat1InputOn,
		rxSat2Ext2,
		rxSat2Trap,
		rxSat2InputOn,
		rxSat2Led,
		rxSat2Log,
		serialNumber,
		partNumber,
		internalDcSupplyVoltageStatus,
		nonLinearSenseFeedback,
		amplifierOutputSample,
		ipInputWarning,
		modulatorExt1,
		modulatorExt2,
		modulatorTrap,
		modulatorFault,
		modulatorLed,
		numberOfFecBlocks,
		rxSat11p1,
		rxSat1AlarmName,
		rxSat1AlarmStatus,
		inputStatusCalibration,
		inputLevelMeasureCalibration,
		powerStatusCalibration,
		powerLevelMeasureCalibration,
		automaticRfPhaseAdjustment,
		nonLinearStatusPrecorrection,
		cancelNonLinearPrecorrection,
		startNonLinearPrecorrection,
		linearStatusPrecorrection,
		startLinearPrecorrectionBBPF,
		startLinearPrecorrectionABPF,
		acApparentPower,
		acEfficiency,
 		efficiencyStatusCalibration,
		cancelEfficiencyCalibration,
--		efficiencyShoulderCalibration, 
		efficiencyShoulderMeasure,
		efficiencyShoulderTarget,
		efficiencyMerMeasure,
		efficiencyMerTarget,
		sfnMargin,
		softwareVersion,
		softwareId,
		ctrlBoard,
		ctrlCBoard,
		ctrlMBoard,
		signalBoardGf,
		signalBoardTx,
		extraDigitalDacModulator,
		satelliteBoard,
		dabBoard,
		dabEti2,
		dabGfBoard,
		terrestialReceiver1Board,
		terrestialReceiver2Board,
		satelliteReceiver1Board,
		satelliteReceiver2Board,
		onePlusOneRedundancy,
		externalFeedback,
		relay1p1Interface,
		i2o8Interface,
		externalInterlock,
		i4o10Interface,
		dcConnector,
		rfBooster,
		ctrlBusInterface,
		amplifierHw,
		amplifierHwRevision,
		amplifierStageType,
		amplifierStageSN,
		gnssReceiverHw,
		externalReferenceHw,
		redundantPsuHw,
		ocxoReferenceHw,
		referenceHwSerialNumber,
		rackCooling1Hw,
		rackCooling2Hw,
		rackCooling3Hw,
		rackCooling4Hw,
		asi1Matrix1Hw,
		asi1Matrix2Hw,
		asi2Matrix1Hw,
		asi2Matrix2Hw,
		rackCooling5Hw, 
		rackCooling6Hw, 
		rfMatrix1Hw,
		rfMatrix2Hw,
		rackCooling7Hw, 
		eti1Matrix1Hw,
		eti1Matrix2Hw,
		eti2Matrix1Hw,
		eti2Matrix2Hw,
		snmpSw,
		dvbtSw,
		dvbt2Sw,
		isdbtSw,
		deecSw,
		isdbtRemuxSw,
		onePlusOneSw,
		dualDriveSw,
		atsc1Sw,
		dabSw,
		unlimitedPowerSw,
		monitoringSw,
		np1Sw,
		bissDecription,
		btsDecompressionRma,
		internalErrorStatus,
		modulatorWarning,
		muteTsError,
		--muteStatus,
		rfOutAlarmName,
		rfOutFault,
		rfOutWarning,
		rxSat1Ext1,
		rxSat1Ext2,
		rxSat1Trap,
		rxSat1Warning,
		rxSat21p1,
		rxSat2AlarmStatus,
		rxSat2Ext1,
		selected10Mhz,
		externalReferenceOutputs,
		selected1Pps,
		receiverType,
		receiverSerial,
		synchronizationStatus,
		synchronizationTemperature,
		socket1InputBitrate,
		socket1Latency,
		socket1MulticastIp,
		socket1Port,
		socket1Protocol,
		socket1SourceIp,
		socket1TransmissionMode,
		socket1UnicastIp,
		socket1VlanEnable,
		socket1Content,
		socket1Jitter,
		socket1DabFec,
		socket1RxPackets,
		socket1RxDisorderedPkts,
		socket1RxDuplicatedPkts,
		socket1RxReorderedPkts,
		socket1RxLostPkts,
		socket1RxOutOfRangePackets,
		socket1RxFixedPackets,
		socket1CorrectedRSCodewords,
		socket1NotCorrectedRSCodewords,
		socket1TimeWithoutService,
		socket1RxStatisticsReset,
		socket1UnicastNetmask,
		socket1MacAddr,
		socket2Content,
		socket2Jitter,
		socket2DabFec,
		socket2RxPackets,
		socket2RxDisorderedPkts,
		socket2RxDuplicatedPkts,
		socket2RxReorderedPkts,
		socket2RxLostPkts,
		socket2RxOutOfRangePackets,
		socket2RxFixedPackets,
		socket2CorrectedRSCodewords,
		socket2NotCorrectedRSCodewords,
		socket2TimeWithoutService,
		socket2RxStatisticsReset,
		socket2UnicastNetmask,
		socket2MacAddr,
		socket2BufferDuration,
		socket2Enable,
		socket2Fec,
		socket2InputBitrate,
		isdbtTimeIntervalLengthLC,
		isdbtNumberOfSegmentsLB,
		socket2Latency,
		-- socket2MaximumBuffer,
		socket2MulticastIp,
		socket2Protocol,
		socket2SourceIp,
		isdbtPidsLA,
		socket2TransmissionMode,
		socket2UnicastIp,
		socket2VlanEnable,
		socket2VlanId,
		sourceSelected,
		switchingMode,
		monitorOutput,
		mipErrorStatus,
		modulatorOutputStatus,
		modulatorShouldersStatus,
		modulatorMerStatus,
		modulatorExternalFeedbackStatus,
		modulatorBerStatus,
		mpegOverflowStatus,
		modulatorStatus,
		--outputRelay1Status,
		ldmosTransistorsStatus,
		isdbtProcessingDelay,
		--outputRelay2Status,
		amplifierAlarmStatus,
		outputChannel,
		outputFrequency,
		outputFrequencyFlt,
		plpConstellation,
		plpGroupId,
		plpId,
		plpMode,
		plpType,
		r1p1AutoVDailyEnable,
		r1p1AutoVerificationsStatus,
		r1p1AutoVDuration,
		r1p1AutoVReiteratedCadence,
		r1p1MaximumSwitchings,
		r1p1InputTest,
		r1p1InputValidation,
		r1p1PowerValidation,
		r1p1SwitchingHysteresis,
		r1p1RfSwitchStatus,
		r1p1StatusA,
		switchingCausesA,
		r1p1StatusB,
		switchingCausesB,
		r1p1SwitchingCausesNCB,
		r1p1StatusWhenAntenna,
		rNp1DeviceIdentifier,
		rNp1ControlBusStatus,
		rNp1SystemIp,
		rNp1NValue,
		rNp1ManualSwitching,
		rNp1Mode,
		rNp1AutoReturn,
		rNp1MaximumRestorations,
		rNp1Window,
		rNp1InputErrorTest,
		rNp1SwitchingHysteresis,
		rNp1ConfigurationDeviceB,
		rNp1DeviceBStatusValue,
		rNp1SwitchingCauses,
		deviceAStatusValue,
		deviceAStatusSwitchingCauses,
		deviceAStatusRestorations,
		deviceARfSwitchStatus,
		rNp1DeviceToLoad,
		rNp1PriorityManagement,
		deviceAPriority,
		deviceARf,
		rNp1AutoVerificationsStatus,
		rNp1AutoVDuration,
		rNp1AutoVPerformedVerifications,
		rNp1AutoVMaxVerifications,
		rNp1AutoVNexVerification,
		rNp1AutoVReiteratedEnable,
		rNp1AutoVReiteratedPeriod,
		rNp1AutoVReiteratedCadence,
		rNp1AutoVDailyEnable,
		rNp1AutoVDailyWindow,
		rNp1AutoVDailyMode, 
		rNp1AutoVDailyTime,
		rNp1VerificationAlarm,
		rNp1Reset,
		rNp1SyncAllConfigurations,
		deviceBConfigurationA,
		deviceBSynchronizeA,
		asiMatrixControlStatus,
		asiMatrixHwStatus,
		asiMatrixSelected,
		asi1InputStatus,
		asi2InputStatus,
		asi1InputLoopStatus,
		asi2InputLoopStatus,
		etiMatrixControlStatus,
		etiMatrixHwStatus,
		etiMatrixSelected,
		eti1InputLoopStatus,
		eti2InputLoopStatus,
		eti1InputStatus,
		eti2InputStatus,
		decreasedPowerThreshold,
		reverserPowerThreshold,
		decreasedPowerThresholdNonCrit,
		reversePowerFlt,
		automaticPowerCompensationEnable, 
		compensationPerStage,
		--redundancySwitchStatus,
		reversePower,
		rotatedConstellation,
		rxDtt1AlarmName,
		rxDtt1Fault,
		rxDtt1Warning,
		rxDtt2Ext1,
		rxDtt2Ext2,
		rxDtt2Led,
		rxSat1Led,
		rxSat2AlarmName,
		rxSat2Fault,
		systemReset,
		temperature,
		trapKeepaliveEnable,
		trapSinkEnable,
		trapSinkInformRetry,
		trapSinkCommunity,
		trapSinkInformTimeout,
		user,
		trapKeepalive,
		warningSummationStatus,
		writeCommunity1,
		writeCommunity2,
		trapsLocalMode,
		trapsInitialStatus,
		sendAllTraps,
		localOscillatorStatus,
		exceededOutputPower,
		decreasedOutputPower,
		reflectPowerStatus,
		rxSat2Warning,
		--selectedReferenceStatus,
		psuAstatus,
		psuAacInputVoltage,
		psuAdcOutputVoltage,
		psuAtemperature,
		psuBstatus,
		psuBacInputVoltage,
		psuBdcOutputVoltage,
		psuBtemperature,
		serviceSwUpgradeMode,
		serviceSwUpgradeServer,
		serviceSwUpgradeUser,
		serviceSwUpgradePassword,
		serviceSwDaily,
		--serviceSwPeriodic,
		serviceSwUpgradingFile, 
		serviceSwVersionFile,
		serviceSwStatus,
		serviceSwDownload, 
		serviceSwCheckNow,
		serviceSwDownloadNow,
		serviceSwUpgradeNow,
		serviceInstallSyncBoard,
		serviceRedundantPsu,
		serviceInput2,
		serviceTypeOfRedundancy,
		serviceCanBusIdentifier,
		serviceDualDriveRelay,
		--coaxialRelay,
		serviceNumberOfAmplifierStages,
		rfPowerSample,
		servicePsuAAmplifierStage, 
		servicePsuBAmplifierStage, 
		servicePsuCAmplifierStage, 
		serviceDetectedCoolingBoard,
		serviceAssignAddressCoolingBoard,
		serviceDeleteAddressCoolingBoard,
		serviceRackCooling1Board,
		serviceRackCooling2Board,
		serviceRackCooling3Board,
		serviceRackCooling4Board,
		serviceRackCooling5Board,
		serviceRackCooling6Board,
		serviceRackCooling7Board,
		--serviceAsiInputsEnabled,
		serviceDetectedAsiMatrix,
		serviceAssingAddressAsiMatrix,
		serviceDeleteAddressAsiMatrix,
		serviceInstalledAsiMatrix1,
		serviceInstalledAsiMatrix2,
		--serviceIdentifyAsiMatrix,
		serviceDetectedRfMatrix,
		serviceAssingAddressRfMatrix,
		serviceDeleteAddressRfMatrix,
		serviceInstalledRfMatrix,
		--serviceIdentifyRfMatrix,
		serviceDetectedEtiMatrix,
		--serviceEtiInputsEnabled,
		serviceAssingAddressEtiMatrix,
		serviceDeleteAddressEtiMatrix,
		serviceInstalledEtiMatrix1,
		serviceInstalledEtiMatrix2,
		--serviceIdentifyEtiMatrix,
		serviceInstallSwActivationCode,
		socket1Enable,
		socket1Fec,
		socket1VlanId,
		temperatureAmplifierStatus,
		decreasedOutputPowerNonCritical,
		trapSinkIpAddress,
		tsErrorStatus,
		t2miErrorStatus,
		temperatureSynchronizationStatus,
		input1ppsStatus,
		sfnErrorStatus,
		temperatureModulatorStatus,
		rfInputStatus,
		echoCancellerStatus,
		inputLevelStatus,
		reference10MHzStatus,
		temperatureECStatus,
		outputLevelStatus,
		cancellerShouldersStatus,
		cancellerMerStatus,
		gainMarginStatus,
		cancExternalFeedbackStatus,
		inputDabErrorStatus,
		etiInputStatus,
		eti1ErrorStatus,
		eti2ErrorStatus,
		rfOutputStatus,
		--systemInitStatus,
		satReceiver1Status,
		unlockSatReceiver1Status,
		rfSignalSatReceiver1Status,
		lnbOverloadSatReceiver1Status,
		socket2Port,
		temperatureSatReceiver1Status,
		camSatReceiver1Status,
		smartCardSatReceiver1Status,
		smartCardRightsSatReceiver1Stat,
		asiOutputSatReceiver1Status,
		dttReceiver1AlarmStatus,
		socket1BufferDuration,
		unlockDttReceiver1Status,
		modulatorStandard,
		rfSignalDttReceiver1Status,
		modulatorTestMode,
		modulatorStandardAutoConfig,
		modulatorPrbsType,
		modulatorPrbsPid,
		modulatorPrbsIn,
		modulatorTemperature,
		-- socket1MaximumBuffer,
		--startOfVerificationStatus,
		temperatureDttReceiver1Status,
		trapSinkVersion,
		satReceiver2Status,
		unlockSatReceiver2Status,
		rfSignalSatReceiver2Status,
		lnbOverloadSatReceiver2Status,
		temperatureSatReceiver2Status,
		dttReceiver2AlarmStatus,
		trapSinkPort,
		unlockDttReceiver2Status,
		rfSignalDttReceiver2Status,
		temperatureDttReceiver2Status,
		modUpperShoulder,
		typeOfTimeInvervaling,
		geralDD,
		geralTrapHysteresis,
		amplifierDD,
		amplifierStage1DD,
		amplifierStage2DD,
		amplifierStage3DD,
		amplifierStage4DD,
		amplifierStagesDD,
		asiDD,
		etiAlarmName,
		etiAlarmStatus,
		etiOn,
		etiLog,
		etiFault,
		etiWarning,
		etiLed,
		eti1p1,
		etiExt1,
		etiExt2,
		etiTrap,
		etiDD,
		ipInputDD,
		rxSat1DD,
		rxSat2DD,
		rxDtt1DD,
		rxDtt2DD,
		rfInDD,
		rackCoolingAlarmName,
		rackCoolingAlarmStatus,
		rackCoolingInputOn,
		rackCoolingLog,
		rackCoolingFault,
		rackCoolingWarning,
		rackCoolingLed,
		rackCooling1p1,
		rackCoolingExt1,
		rackCoolingExt2,
		rackCoolingTrap,
		rackCoolingDD,
		cancellerDD,
		modulatorDD,
		rfOutDD,
		errorHwDD,
		fanDD,
		externalDD,
		powerSupplyDD,
		dcInputAlarmName,
		dcInputAlarmStatus,
		dcInputOn,
		dcInputLog,
		dcInputFault,
		dcInputWarning,
		dcInputLed,
		dcInput1p1,
		dcInputExt1,
		dcInputExt2,
		dcInputTrap,
		dcInputDD,
		synchronizationDD,
		redundancySysAlarmName,
		redundancySysAlarmStatus,
		redundancySysOn,
		redundancySysLog,
		redundancySysFault,
		redundancySysWarning,
		redundancySysLed,
		redundancySys1p1,
		redundancySysExt1,
		redundancySysExt2,
		redundancySysTrap,
		redundancySysDD,
		geralTrapHysteresis,
		amplifierTrapHysteresis,
		amplifierStage1TrapHysteresis,
		amplifierStage2TrapHysteresis,
		amplifierStage3TrapHysteresis,
		amplifierStage4TrapHysteresis,
		amplifierStagesTrapHysteresis,
		asiTrapHysteresis,
		etiTrapHysteresis,
		ipInputTrapHysteresis,
		rxSat1TrapHysteresis,
		rxSat2TrapHysteresis,
		rxDtt1TrapHysteresis,
		rxDtt2TrapHysteresis,
		rfInTrapHysteresis,
		rackCoolingTrapHysteresis,
		cancellerTrapHysteresis,
		modulatorTrapHysteresis,
		rfOutTrapHysteresis,
		synchronizationTrapHysteresis,
		errorHwTrapHysteresis,
		fanTrapHysteresis,
		externalTrapHysteresis,
		powerSupplyTrapHysteresis,
		dcInputTrapHysteresis,
		redundancySysTrapHysteresis
		 }
	STATUS     current
	DESCRIPTION
		"Group of objects of transmitter"
	::= { objectGroups 1 }

-- echoCancellationEnable,
-- echoCancellerEnable,

groupEvents  OBJECT-GROUP
	OBJECTS { eventAdditionalText,
		eventFinalStatus,
		eventInitialStatus,
		eventTimeStamp,
		eventTrapLogId,
	 	redundancyId }
	STATUS     current
	DESCRIPTION
		"Contains all the objects from test branch of the MIB"
	::= { objectGroups 2 }

groupFSevents  NOTIFICATION-GROUP
	NOTIFICATIONS { amplifierSumTrap,
		asi1ErrorTrap,
		asi2ErrorTrap,
		asiInputTrap,
		dttReceiver1Trap,
		dttReceiver2Trap,
		btsErrorTrap,
		nonLinearSenseFeedbackTrap,
		modulatorShouldersTrap,
		systemShutdownEventTrap,
		outputLevelTrap,
		amplifierOutputSampleTrap,
		temperatureECTrap,
		rfInputTrap,
		inputLevelTrap,
		echoCancellerTrap,
		configurationFromBackupEventTrap,
		input10MhzTrap,
		input1ppsTrap,
		externalAlarm2Trap,
		externalAlarmTrap,
		cancellerShouldersTrap,
		fan2Trap,
		fan3Trap,
		fanSumTrap,
		faultSummationTrap,
		exceededOutputPowerTrap,
		externalAlarm1Trap,
		fan1Trap,
		forcedMfnEventTrap,
		synchronizationAntennaTrap,
		synchronizationHoldoverTrap,
		synchronizationHwErrorTrap,
		synchronizationModuleTrap,
		synchronizationUnlockTrap,
		guiOperationEventTrap,
		hwErrorTrap,
		inputSourceSelectedEventTrap,
		internalDcSupplyVoltageTrap,
		internalErrorTrap,
		ipInputSumTrap,
		ipSocket1ErrorTrap,
		ipSocket2ErrorTrap,
		keepaliveTrap,
		ldmosTransistorsTrap,
		lnbOverloadSatReceiver1Trap,
		lnbOverloadSatReceiver2Trap,
		localModeTimeoutEventTrap,
		localOscillatorTrap,
		mipErrorTrap,
		modulatorOutputTrap,
		modulatorSumTrap,
		mpegOverflowTrap,
		muteEventTrap,
		outputRelay1Trap,
		outputRelay2Trap,
		decreasedOutputPowerTrap,
		decreasedOuputPowerNonCritTrap,
		lockingStart1ppsEventTrap,
		rackCoolingEventTrap,
		rackCoolingTemperatureEventTrap,
		rackCPressureDifferenceTrap,
		rackCoolingHwErrorEventTrap,
		dcInputEventTrap,
		externalDcPowerSupplyEventTrap,
		redundancySysEventTrap,
		redundancySysComEventTrap,
		redundancySysSwitchEventTrap,
		redundancySysReserveEventTrap,
		redundancyInputAsiMatrixTrap,
		redundancyHwMatrixEventTrap,
		inputDabErrorStatusEventTrap,
		etiInputTrap,
		eti1ErrorTrap,
		camSatReceiver1Trap,
		smartCardSatReceiver1Trap,
		smartCardRightsSatReceiver1Trap,
		asiOutputSatReceiver1Trap,
		ioInterfaceInputEventTrap,
		ioInterfaceOutputEventTrap,
		redundancyEventTrap,
		reflectedPowerTrap,
		rfOutputTrap,
		rfSignalDttReceiver1Trap,
		rfSignalDttReceiver2Trap,
		rfSignalSatReceiver1Trap,
		rfSignalSatReceiver2Trap,
		satReceiver1Trap,
		satReceiver2Trap,
		selectedReferenceEventTrap,
		sfnMarginTrap,
		sfnReferenceTrap,
		systemInitEventTrap,
		t2miErrorTrap,
		temperatureAmplifierTrap,
		temperatureDttReceiver1Trap,
		temperatureDttReceiver2Trap,
		temperatureSynchronizationTrap,
		reference10MHzTrap,
		dateAndTimeReferenceEventTrap,
		acPowerSupplyTrap,
		psuATrap,
		psuBTrap,
		temperatureModulatorTrap,
		temperatureSatReceiver1Trap,
		temperatureSatReceiver2Trap,
		cancellerMerStatusTrap,
		standardAutoConfigurationTrap,
		gainMarginStatusTrap,
		cancExternalFeedbackStatusTrap,
		modulatorMerStatusTrap,
		modExternalFeedbackStatusTrap,
		modBerStatusTrap,
		tsErrorTrap,
		unlockDttReceiver1Trap,
		unlockDttReceiver2Trap,
		unlockSatReceiver1Trap,
		unlockSatReceiver2Trap,
		warningSummationTrap,
		amplifierStage1SumTrap,
		aS1InputLevelTrap,
		aS1ExceededPowerTrap,
		aS1DecreasedPowerTrap,
		aS1ReflectedPowerTrap,
		aS1TemperatureTrap,
		aS1HwErrorTrap,
		amplifierStage2SumTrap,
		aS2InputLevelTrap,
		aS2ExceededPowerTrap,
		aS2DecreasedPowerTrap,
		aS2ReflectedPowerTrap,
		aS2TemperatureTrap,
		aS2HwErrorTrap,
		amplifierStage3SumTrap,
		aS3InputLevelTrap,
		aS3ExceededPowerTrap,
		aS3DecreasedPowerTrap,
		aS3ReflectedPowerTrap,
		aS3TemperatureTrap,
		aS3HwErrorTrap,
		amplifierStage4SumTrap,
		aS4InputLevelTrap,
		aS4ExceededPowerTrap,
		aS4DecreasedPowerTrap,
		aS4ReflectedPowerTrap,
		aS4TemperatureTrap,
		aS4HwErrorTrap,
		amplifierStagesSumTrap,
		aSsInputLevelTrap,
		aSsExceededPowerTrap,
		aSsDecreasedPowerTrap,
		aSsReflectedPowerTrap,
		aSsTemperatureTrap,
		aSsHwErrorTrap,
		aSsPsusErrorTrap,
		aS1PsusErrorTrap,
		aS2PsusErrorTrap,
		aS3PsusErrorTrap,
		aS4PsusErrorTrap,
		redundancyHwRfMatrixEventTrap,
		redundancyInputEtiMatrixTrap,
		redundancyHwEtiMatrixEventTrap,
		shortTermMonitoringEventTrap,
		autoconfFromInputEventTrap,
		channelAdaptationEventTrap,
		dttReceiver1BerMuteTrap,
		dttReceiver2BerMuteTrap,
		automaticPowerCompensationTrap,
		eti2ErrorTrap,
		testTrap
	 }
	STATUS     current
	DESCRIPTION
		"Traps group "
	::= { objectGroups 10 }

-- groupTest  OBJECT-GROUP
-- 	OBJECTS { oidTest }
-- 	STATUS     current
-- 	DESCRIPTION
-- 		"Test group "
-- 	::= { objectGroups 100 }

groupObsoleted  OBJECT-GROUP
	OBJECTS { satellite01,
		satellite02,
		satellite03,
		satellite04,
		satellite05,
		satellite06,
		satellite07,
		satellite08,
		--isdbtPidFilteringLA,
		--isdbtPidFilteringLB,
		--isdbtPidFilteringLC,
		dvbtRateAdaptation,
		cancelInputCalibration
	}
	STATUS		obsolete
	DESCRIPTION
		"Obsoleted OIDs"
	::= { objectGroups 3 }

fsBasicCompilance  MODULE-COMPLIANCE
	STATUS     current
	DESCRIPTION
		"Contains all groups"
	MODULE
		MANDATORY-GROUPS { groupFS,
				groupEvents,
--				groupTest,
				groupFSevents }
	::= { groupCompilance 1 }
END
